/*
 * Copyright (c) 2021 Juniper Networks, Inc.
 * All rights reserved.
 */
 module junos-es-conf-chassis {
   namespace "http://yang.juniper.net/junos-es/conf/chassis";

   prefix jc-chassis;

   import junos-common-types {
     prefix jt;
     revision-date 2019-01-01;
   }

   import junos-es-conf-root {
     prefix jc;
     revision-date 2019-01-01;
   }

   organization "Juniper Networks, Inc.";

   contact "yang-support@juniper.net";

   description "Junos chassis configuration module";

   revision 2019-01-01 {
     description "Junos: 21.2R1.10";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container psu {
       description "Power Supply Unit redundancy configuration";
       uses apply-advanced;
       container redundancy {
         description "PSU Redundancy settings";
         uses apply-advanced;
         leaf n-plus-n {
           description "PSU redundancy: N+N configuration";
           type empty;
         }
       }
     }
     leaf craft-lockout {
       description "Disable craft interface input";
       type empty;
     }
     container config-button {
       description "Config button behavior settings";
       leaf no-rescue {
         description "Don't reset to rescue configuration";
         type empty;
       }
       leaf no-clear {
         description "Don't reset to factory-default configuration";
         type empty;
       }
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     container icmp {
       description "ICMP protocol";
       uses apply-advanced;
       leaf per-iff-rate-limit {
         description "Configure icmp per iff rate limit value in the range 50-500";
         default "50";
         type union {
           type string {
             pattern "<.*>|$.*";
           }
           type uint32 {
             range "50 .. 500";
           }
         }
       }
     }
     container icmp6 {
       description "ICMP version 6 protocol";
       uses apply-advanced;
       leaf per-iff-rate-limit {
         description "Configure icmp6 per iff rate limit value in the range 50-500";
         default "50";
         type union {
           type string {
             pattern "<.*>|$.*";
           }
           type uint32 {
             range "50 .. 500";
           }
         }
       }
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container redundancy {
       description "Redundancy settings";
       uses chassis_redundancy_type;
     }
     container routing-engine {
       description "Routing Engine settings";
       uses chassis_routing_engine_type;
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container pseudowire-service {
       description "Pseudowire L3 termination device configuration";
       presence "enable pseudowire-service";
       uses chassis-pw-type;
     }
     container fabric {
       description "Switch fabric settings";
       uses chassis_fabric_type;
     }
     list fpc {
       key name;
       description "Flexible PIC Concentrator parameters";
       uses chassis_fpc_type;
     }
     leaf disable-power-management {
       description "Disable Power Management in this chassis";
       type empty;
     }
     leaf dedicated-ukern-cpu {
       description "Run Microkernel on a dedicated CPU core";
       type empty;
     }
     leaf realtime-ukern-thread {
       description "Run Microkernel on a realtime CPU thread";
       type empty;
     }
     container fpc-feb-connectivity {
       description "Connectivity between Flexible PIC Concentrators and Forwarding Engine Boards";
       uses apply-advanced;
       list fpc {
         key name;
         leaf name {
           description "FPC slot number";
           type union {
             type string {
               pattern "<.*>|$.*";
             }
             type uint32;
           }
         }
         uses apply-advanced;
         container feb {
           description "FEB slot number";
           choice feb-slot-choice {
             case case_1 {
               leaf none {
                 description "FPC not connected to any FEB";
                 type empty;
               }
             }
             case case_2 {
               leaf feb-slot {
                 description "FEB slot number";
                 type union {
                   type string {
                     pattern "<.*>|$.*";
                   }
                   type uint32;
                 }
               }
             }
           }
         }
       }
     }
     container ioc-npc-connectivity {
       description "Connectivity between IOC and NPC";
       uses apply-advanced;
       list ioc {
         key name;
         leaf name {
           description "IOC-FPC slot number";
           type union {
             type string {
               pattern "<.*>|$.*";
             }
             type uint32;
           }
         }
         uses apply-advanced;
         container npc {
           description "NPC-FPC slot number";
           choice npc-slot-choice {
             case case_1 {
               leaf none {
                 description "IOC not connected to any NPC";
                 type empty;
               }
             }
             case case_2 {
               leaf npc-slot {
                 description "NPC-FPC slot number";
                 type union {
                   type string {
                     pattern "<.*>|$.*";
                   }
                   type uint32;
                 }
               }
             }
           }
         }
       }
     }
     container pem {
       description "Power supply (PEM) parameters";
       uses chassis_pem_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf onbox-av-load-flavor {
       description "Select onbox anti-virus traffic load flavor";
       type enumeration {
         enum "heavy" {
           description "Allocates additional resources for improved performance";
         }
       }
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     container resource-watch {
       description "Chassis routing engine resource watch configuration";
       uses apply-advanced;
       leaf resource-watch-enable {
         description "Enable resource watch";
         type empty;
       }
       leaf cpu-statistics {
         description "Set statistics collection, 0 disable";
         units "seconds";
         type union {
           type string {
             pattern "<.*>|$.*";
           }
           type uint32 {
             range "0 .. 604800";
           }
         }
       }
       leaf junos-statistics {
         description "Set statistics collection, 0 disable";
         units "seconds";
         type union {
           type string {
             pattern "<.*>|$.*";
           }
           type uint32 {
             range "0 .. 604800";
           }
         }
       }
       leaf orange-zone-enable {
         description "Enable orange zone";
         type empty;
       }
       leaf orange-zone-threshold {
         description "Set orange zone value (CPU idle %), default 20";
         type union {
           type string {
             pattern "<.*>|$.*";
           }
           type uint32 {
             range "1 .. 99";
           }
         }
       }
       leaf red-zone-enable {
         description "Enable red zone";
         type empty;
       }
       leaf red-zone-cpu-threshold {
         description "Set red zone value (CPU idle %), default 10";
         type union {
           type string {
             pattern "<.*>|$.*";
           }
           type uint32 {
             range "1 .. 99";
           }
         }
       }
       leaf red-zone-jkl-threshold {
         description "Set red zone value (Junos load %), default 50";
         type union {
           type string {
             pattern "<.*>|$.*";
           }
           type uint32 {
             range "1 .. 99";
           }
         }
       }
       leaf red-zone-snmp-enable {
         description "Enable red zone snmp";
         type empty;
       }
     }
     leaf network-services {
       description "Chassis network services configuration";
       type enumeration {
         enum "ip" {
           description "IP network services";
         }
         enum "ethernet" {
           description "Ethernet network services";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     container usb {
       description "USB control flags";
       uses apply-advanced;
       container storage {
         description "USB storage flags";
         uses apply-advanced;
         leaf disable {
           description "Disable USB storage";
           type empty;
         }
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         uses chassis_fpc_type;
       }
       container pem {
         description "Power supply (PEM) parameters";
         uses chassis_pem_type;
       }
       choice state {
         case case_1 {
           leaf online-expected {
             description "LCC is expected to be online";
             type empty;
           }
         }
         case case_2 {
           leaf offline {
             description "LCC is expected to be offline";
             type empty;
           }
         }
       }
     }
     container lcd {
       description "Chassis LCD";
       status deprecated;
       uses apply-advanced;
       choice menu-item {
         case case_1 {
           leaf maintenance-menu {
             description "LCD maintenance menu";
             type empty;
           }
         }
       }
       choice enable-disable {
         case case_1 {
           leaf disable {
             description "Disable maintenance-menu";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewall-optimization {
       description "Optimal TCAM use,restarts PFE(for IP rsrved multicast dest & IP ttl=0/1,config explicitly)";
       type empty;
     }
     leaf epacl-firewall-optimization {
       description "Maximizes Egress Port ACLs TCAM use and restarts PFE";
       type empty;
     }
     leaf fru-poweron-sequence {
       description "FRUs power on sequence like 0 1 2 3 ... within double quotes";
       type string {
       }
     }
     leaf auto-image-upgrade {
       description "Auto image upgrade using DHCP";
       type empty;
     }
     container error {
       description "Error level configuration for all FPC";
       presence "enable error";
       uses chassis_fpc_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     list satellite {
       key name;
       ordered-by user;
       description "List of available satellite configurations";
       leaf name {
         description "Satellite name";
         type string {
         }
       }
       uses apply-advanced;
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
       }
       container traceoptions {
         description "Protected system domain traceoptions";
         uses juniper-protected-system-domain-traceoptions;
       }
     }
     container cluster {
       description "Chassis cluster configuration";
       uses apply-advanced;
       container traceoptions {
         description "Set chassis cluster traceoptions";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       leaf control-link-recovery {
         description "Enable automatic control link recovery";
         type empty;
       }
       leaf health-monitoring {
         description "Enable ha health monitoring";
         type empty;
       }
       leaf reth-count {
         description "Number of redundant ethernet interfaces";
         type union {
           type string {
             pattern "<.*>|$.*";
           }
           type uint16;
         }
       }
       container control-interface {
         description "Disable/enable HA control-link interface";
         uses apply-advanced;
         list node {
           key name;
           ordered-by user;
           description "Set node specific parameters";
           leaf name {
             description "Node identifier";
             type union {
               type string {
                 pattern "<.*>|$.*";
               }
               type uint32 {
                 range "0 .. 1";
               }
             }
           }
           leaf disable {
             description "Disable HA control interface";
             type empty;
           }
         }
       }
       list control-ports {
         key "fpc port";
         ordered-by user;
         description "Enable specific chassis cluster control ports";
         leaf fpc {
           description "FPC slot number";
           type union {
             type string {
               pattern "<.*>|$.*";
             }
             type uint32;
           }
         }
         leaf port {
           description "Port number";
           type union {
             type string {
               pattern "<.*>|$.*";
             }
             type uint32 {
               range "0 .. 2";
             }
           }
         }
       }
       leaf heartbeat-interval {
         description "Interval between successive heartbeats";
         default "1000";
         units "milliseconds";
         type union {
           type string {
             pattern "<.*>|$.*";
           }
           type uint32;
         }
       }
       leaf heartbeat-threshold {
         description "Number of consecutive missed heartbeats to indicate device failure";
         default "3";
         type union {
           type string {
             pattern "<.*>|$.*";
           }
           type uint32;
         }
       }
       container network-management {
         description "Define parameters for network management";
         uses apply-advanced;
         leaf cluster-master {
           description "Enable in-band management on cluster-master";
           type empty;
         }
       }
       list node {
         key name;
         ordered-by user;
         description "Set the list of nodes in the cluster";
         status deprecated;
         leaf name {
           description "Node identifier";
           type enumeration {
             enum "0" {
               description "Node identifier 0";
             }
             enum "1" {
               description "Node identifier 1";
             }
           }
         }
         uses apply-advanced;
       }
       list redundancy-group {
         key name;
         ordered-by user;
         description "Set redundancy-group parameters";
         leaf name {
           description "Redundancy-group number";
           type union {
             type string {
               pattern "<.*>|$.*";
             }
             type uint8;
           }
         }
         uses apply-advanced;
         list node {
           key name;
           ordered-by user;
           description "Set node specific parameters";
           leaf name {
             description "Node identifier";
             type enumeration {
               enum "0" {
                 description "Node identifier 0";
               }
               enum "1" {
                 description "Node identifier 1";
               }
             }
           }
           leaf priority {
             description "Priority of the node in the redundancy-group";
             type union {
               type string {
                 pattern "<.*>|$.*";
               }
               type uint8 {
                 range "1 .. 254";
               }
             }
           }
         }
         container preempt {
           presence "enable preempt";
           description "Allow preemption of primaryship based on priority";
           uses apply-advanced;
           leaf delay {
             description "Time to wait before taking over mastership";
             units "seconds";
             type union {
               type string {
                 pattern "<.*>|$.*";
               }
               type uint16 {
                 range "1 .. 21600";
               }
             }
           }
           leaf limit {
             description "Max number of preemptive failovers allowed";
             type union {
               type string {
                 pattern "<.*>|$.*";
               }
               type uint16 {
                 range "1 .. 50";
               }
             }
           }
           leaf period {
             description "Time period during which the limit is applied";
             units "seconds";
             type union {
               type string {
                 pattern "<.*>|$.*";
               }
               type uint16 {
                 range "1 .. 1400";
               }
             }
           }
         }
         leaf gratuitous-arp-count {
           description "Number of gratuitous ARPs to send on an active interface after failover";
           type union {
             type string {
               pattern "<.*>|$.*";
             }
             type uint8 {
               range "1 .. 16";
             }
           }
         }
         leaf hold-down-interval {
           description "RG failover interval. RG0(300-1800) RG1+(0-1800)";
           units "seconds";
           type union {
             type string {
               pattern "<.*>|$.*";
             }
             type uint16 {
               range "0 .. 1800";
             }
           }
         }
         list interface-monitor {
           key name;
           ordered-by user;
           description "Define interfaces to monitor";
           leaf name {
             description "Name of the interface to monitor";
             type union {
               type jt:interface-device;
               type string {
                 pattern "<.*>|$.*";
               }
             }
           }
           leaf weight {
             description "Weight assigned to this interface that influences failover";
             type union {
               type string {
                 pattern "<.*>|$.*";
               }
               type uint16 {
                 range "0 .. 255";
               }
             }
           }
         }
         container ip-monitoring {
           description "Define parameters for IP monitoring feature";
           uses apply-advanced;
           leaf global-weight {
             description "Define global weight for IP monitoring";
             default "255";
             type union {
               type string {
                 pattern "<.*>|$.*";
               }
               type uint16 {
                 range "0 .. 255";
               }
             }
           }
           leaf global-threshold {
             description "Define global threshold for IP monitoring";
             default "0";
             type union {
               type string {
                 pattern "<.*>|$.*";
               }
               type uint16 {
                 range "0 .. 255";
               }
             }
           }
           leaf retry-interval {
             description "Define the time interval in seconds between retries.";
             default "1";
             type union {
               type string {
                 pattern "<.*>|$.*";
               }
               type uint16 {
                 range "1 .. 30";
               }
             }
           }
           leaf retry-count {
             description "Number of retries needed to declare reachablity failure";
             default "5";
             type union {
               type string {
                 pattern "<.*>|$.*";
               }
               type uint16 {
                 range "5 .. 15";
               }
             }
           }
           container family {
             description "Define protocol family";
             uses apply-advanced;
             container inet {
               description "Define IPv4 related parameters";
               uses apply-advanced;
               list address {
                 key name;
                 description "Define IP address related parameters";
                 uses ip-monitoring-address-type;
               }
             }
           }
         }
       }
       container configuration-synchronize {
         description "Cluster configuration action";
         uses apply-advanced;
         leaf no-secondary-bootup-auto {
           description "Disable auto configuration synchronize on secondary bootup";
           type empty;
         }
       }
       leaf use-actual-mac-on-physical-interfaces {
         description "Use Hypervisor provided MAC for physical interfaces on virtual platforms";
         type empty;
       }
       leaf use-active-child-mac-on-reth {
         description "Copy Child's physical MAC on RETH parent's current MAC";
         type empty;
       }
     }
     container high-availability {
       presence "enable high-availability";
       description "Enable High Availability mode";
       uses apply-advanced;
       container local-id {
         description "Local Identifier";
         leaf id {
           description "Local identifier number";
           type union {
             type string {
               pattern "<.*>|$.*";
             }
             type uint8 {
               range "1 .. 10";
             }
           }
         }
         leaf local-ip {
           description "Local IPv4 address";
           type jt:ipv4addr;
         }
       }
       list peer-id {
         key name;
         ordered-by user;
         description "Peer related information";
         leaf name {
           description "Peer Identifier";
           type union {
             type string {
               pattern "<.*>|$.*";
             }
             type uint8 {
               range "1 .. 10";
             }
           }
         }
         uses apply-advanced;
         leaf desc {
           description "Peer Description";
           type string {
             length "1 .. 255";
           }
         }
         leaf peer-ip {
           description "Peer IPV4 address";
           type jt:ipv4addr;
         }
         leaf interface {
           description "Name of the interface";
           type union {
             type jt:interface-name;
             type string {
               pattern "<.*>|$.*";
             }
           }
         }
         leaf routing-instance {
           description "Routing instance to locate the peer route";
           type string {
           }
         }
         leaf vpn-profile {
           description "VPN Profile name for HA link Encryption";
           type string {
             length "1 .. 255";
           }
         }
         container liveness-detection {
           presence "enable liveness-detection";
           description "Bidirectional Forwarding Detection options for the peer";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       container traceoptions {
         description "Set chassis l3-ha traceoptions";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "cli" {
                 description "Trace CLI events";
               }
               enum "configuration" {
                 description "Trace configuration events";
               }
               enum "eventlib" {
                 description "Trace event library events";
               }
               enum "fsm" {
                 description "Trace finite state machine events";
               }
               enum "heartbeat" {
                 description "Trace JSRPD heartbeats";
               }
               enum "interface" {
                 description "Trace interface related events";
               }
               enum "routing-socket" {
                 description "Trace routing socket events";
               }
               enum "uspipc" {
                 description "Trace USP IPC events";
               }
               enum "init" {
                 description "Trace initialization events";
               }
               enum "socket" {
                 description "Trace socket events";
               }
               enum "snmp" {
                 description "Trace snmp events";
               }
               enum "ip-monitoring" {
                 description "Trace IP monitoring events";
               }
               enum "hw-monitoring" {
                 description "Trace HW  monitoring events";
               }
               enum "fabric-monitoring" {
                 description "Trace fabric monitoring events";
               }
               enum "health-monitoring" {
                 description "Trace health monitoring events";
               }
               enum "schedule-monitoring" {
                 description "Trace schedule monitoring events";
               }
               enum "heartbeat-tlv" {
                 description "Trace TLV based heart-beat";
               }
               enum "ha-peer" {
                 description "Trace HA peer related info";
               }
               enum "srg" {
                 description "Trace HA srg related info";
               }
               enum "all" {
                 description "Trace all events";
               }
             }
           }
         }
         leaf level {
           description "Set level of tracing";
           default "info";
           type enumeration {
             enum "emergency" {
               description "Match emergency conditions";
             }
             enum "alert" {
               description "Match alert conditions";
             }
             enum "critical" {
               description "Match critical conditions";
             }
             enum "error" {
               description "Match error conditions";
             }
             enum "warning" {
               description "Match warning messages";
             }
             enum "notice" {
               description "Match notice level messages";
             }
             enum "info" {
               description "Match informational messages";
             }
             enum "debug" {
               description "Match debug messages";
             }
             enum "all" {
               description "Match all levels";
             }
           }
         }
       }
       list services-redundancy-group {
         key name;
         ordered-by user;
         description "Define the services level failover domain";
         leaf name {
           description "Services redundancy group identifier";
           type union {
             type string {
               pattern "<.*>|$.*";
             }
             type uint16 {
               range "0 .. 256";
             }
           }
         }
         uses apply-advanced;
         list shutdown-on-failure {
           key name;
           ordered-by user;
           description "Interfaces to be shut down in case of internal failures";
           leaf name {
             description "Name of the interface";
             type union {
               type jt:interface-device;
               type string {
                 pattern "<.*>|$.*";
               }
             }
           }
           uses apply-advanced;
         }
         container peer-id {
           presence "enable peer-id";
           description "Peer related information";
           uses apply-advanced;
           leaf id {
             description "Peer Identifier";
             type union {
               type string {
                 pattern "<.*>|$.*";
               }
               type uint8 {
                 range "1 .. 10";
               }
             }
           }
         }
         container floating-ip {
           description "Designated floating IP for activeness probe";
           uses apply-advanced;
           leaf ip-address {
             description "IPv4 address";
             type jt:ipv4addr;
           }
         }
         container activeness-probe {
           description "The probe destination IP for activeness determination";
           uses apply-advanced;
           container dest-ip {
             description "Destination IPV4 address";
             uses apply-advanced;
             leaf ip-address {
               description "Destination IPV4 address";
               type jt:ipv4addr;
             }
             leaf routing-instance {
               description "Routing instance";
               type string {
               }
             }
           }
         }
         container monitor {
           description "Configure the BFD and IP monitoring";
           uses apply-advanced;
           list ip {
             key name;
             ordered-by user;
             description "Destination IPV4 address for monitoring";
             leaf name {
               description "Destination IPV4 address";
               type jt:ipv4addr;
             }
             uses apply-advanced;
             leaf routing-instance {
               description "Routing instance to locate the destination route";
               type string {
               }
             }
           }
           list bfd-liveliness {
             key name;
             ordered-by user;
             description "Configure BFD monitoring";
             leaf name {
               description "Destination IPV4 address for BFD monitoring";
               type jt:ipv4addr;
             }
             uses apply-advanced;
             leaf src-ip {
               description "Source IPV4 address for BFD monitoring";
               type jt:ipv4addr;
             }
             leaf routing-instance {
               description "Routing instance to locate the route";
               type string {
               }
             }
             leaf session-type {
               description "BFD Mon Session Type";
               type enumeration {
                 enum "singlehop" {
                   description "Single hop";
                 }
                 enum "multihop" {
                   description "Multihop";
                 }
               }
             }
             leaf interface {
               description "Name of the interface for single-hop sessions";
               type union {
                 type jt:interface-name;
                 type string {
                   pattern "<.*>|$.*";
                 }
               }
             }
           }
         }
         container active-signal-route {
           description "Configure the active signal route";
           uses apply-advanced;
           leaf ip-address {
             description "Active IPv4 address";
             type jt:ipv4addr;
           }
           leaf routing-instance {
             description "Routing instance to install the active signal route";
             type string {
             }
           }
         }
         container backup-signal-route {
           description "Configure the backup signal route";
           uses apply-advanced;
           leaf ip-address {
             description "Backup IPv4 address";
             type jt:ipv4addr;
           }
           leaf routing-instance {
             description "Routing instance to install the backup signal route";
             type string {
             }
           }
         }
         leaf process-packet-on-backup {
           description "Enable PFE to process packets on backup node";
           type empty;
         }
         leaf activeness-priority {
           description "Activeness Priority of the node for this SRG";
           type union {
             type string {
               pattern "<.*>|$.*";
             }
             type uint8 {
               range "1 .. 254";
             }
           }
         }
       }
     }
     list node {
       key name;
       description "Set node specific parameters";
       leaf name {
         description "Node identifier";
         type union {
           type string {
             pattern "<.*>|$.*";
           }
           type uint32 {
             range "0 .. 1";
           }
         }
       }
       uses apply-advanced;
       list fpc {
         key name;
         description "Flexible PIC Concentrator parameters";
         uses chassis_fpc_type;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_agg_dev_type {
     uses apply-advanced;
     container ethernet {
       description "Aggregated device options for Ethernet";
       uses chassisd_agg_enet_type;
     }
     container sonet {
       description "Aggregated device options for SONET";
       uses chassisd_agg_pos_type;
     }
     leaf maximum-links {
       description "Maximum links limit for aggregated devices (16, 32, or 64)";
       type union {
         type int32;
         type string {
           pattern "<.*>|$.*";
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container l2-chan-err-ethernet {
       description "L2 channel error ethernet alarms";
       uses chassis_alarm_l2_chan_err_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     leaf pem-absence {
       description "Power supply module absence";
       type enumeration {
         enum "ignore" {
           description "Ignore the power supply module absence alarm";
         }
       }
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_l2_chan_err_type {
     uses apply-advanced;
     leaf l2-channel-errors {
       description "Received L2 channel error";
       type enumeration {
         enum "red" {
           description "Assert red system alarm";
         }
         enum "yellow" {
           description "Assert yellow system alarm";
         }
         enum "ignore" {
           description "Do not assert any alarm signals";
         }
       }
     }
     leaf l2-channel-error-threshold {
       description "L2 channel error threshold - 50,000 as default";
       type union {
         type string {
           pattern "<.*>|$.*";
         }
         type uint32 {
           range "1 .. 4294967295";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_fabric_type {
     uses apply-advanced;
     container link-autoheal {
       presence "enable link-autoheal";
       description "Link-autoheal fabric configuration";
       uses apply-advanced;
     }
     container oam {
       description "Fabric OAM configuration";
       uses apply-advanced;
     }
     container degraded {
       presence "enable degraded";
       description "Degraded fabric configuration";
       uses apply-advanced;
       leaf action-fpc-restart-disable {
         description "Limit degraded fabric actions to Plane restart only";
         type empty;
       }
     }
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
   }
   grouping chassis_feb_type {
     uses apply-advanced;
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "offline-pic" {
             description "Offline PICs associated with PFE on FPC";
           }
           enum "trap" {
             description "Raise FPC trap";
           }
         }
       }
       uses apply-advanced;
     }
   }
   grouping chassis_fpc_type {
     leaf name {
       description "FPC slot number";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     leaf power {
       description "Power FPCs on or off";
       type enumeration {
         enum "off" {
           description "Do not provide power to FPCs";
         }
         enum "on" {
           description "Provide power to FPCs";
         }
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
       }
       case case_2 {
       }
     }
     leaf services-offload {
       description "Enable services offload on fpc";
       status deprecated;
       type empty;
     }
     leaf cfp-to-et {
       description "Enable ET interface and remove CFP client";
       type empty;
     }
     leaf np-cache {
       description "Enable NP cache and services offload on fpc";
       status deprecated;
       type empty;
     }
     leaf np-cache-disable {
       description "Disable NP cache and services offload on fpc";
       type empty;
     }
     leaf offline {
       description "Keep FPC offline";
       type empty;
     }
     leaf offline-on-fabric-bandwidth-reduction {
       description "Bring FPC offline when running with reduced fabric bandwidth";
       type empty;
     }
     container fabric {
       presence "enable fabric";
       uses apply-advanced;
       leaf blackhole-action {
         description "Action taken upon fabric plane blackhole involving the FPC";
         type enumeration {
           enum "log-only" {
             description "Log the detected blackhole condition";
           }
           enum "offline" {
             description "Offline the FPC";
           }
           enum "restart" {
             description "Restart the FPC";
           }
           enum "restart-then-offline" {
             description "Restart the FPC and offline in subsequent action. ";
           }
         }
       }
       container bandwidth-degradation {
         description "Take FPC recovery action when FPC running with reduced fabric bandwidth";
         uses apply-advanced;
         leaf percentage {
           description "The percentage of PFE bandwidth degradation to trigger action";
           type union {
             type string {
               pattern "<.*>|$.*";
             }
             type uint32 {
               range "1 .. 99";
             }
           }
         }
         leaf no-fabric-switchover {
           description "Do not perform switchover to spare CB";
           type empty;
         }
         leaf action {
           description "Type of action to trigger";
           type enumeration {
             enum "log-only" {
               description "Log the bandwidth degradation only";
             }
             enum "offline" {
               description "Offline the FPC, default action";
             }
             enum "restart" {
               description "Restart the FPC";
             }
             enum "restart-then-offline" {
               description "Restart the FPC and offline in subsequent action";
             }
           }
         }
       }
     }
     list port-mirror-instance {
       key name;
       ordered-by user;
       max-elements 2;
       leaf name {
         description "Associate a port mirroring instance with the FPC";
         type string {
           length "1 .. 64";
         }
       }
       uses apply-advanced;
     }
     list sampling-instance {
       key name;
       ordered-by user;
       max-elements 1;
       leaf name {
         description "Associate a sampling instance with the FPC";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         type empty;
       }
       leaf use-extended-flow-memory {
         description "Use extended memory for flow records";
         type empty;
       }
       container flow-table-size {
         uses apply-advanced;
         leaf ipv4-flow-table-size {
           description "IPv4 flow table size in units of 256k";
           type union {
             type string {
               pattern "<.*>|$.*";
             }
             type uint32 {
               range "1 .. 245";
             }
           }
         }
         leaf ipv6-flow-table-size {
           description "IPv6 flow table size in units of 256k";
           type union {
             type string {
               pattern "<.*>|$.*";
             }
             type uint32 {
               range "1 .. 245";
             }
           }
         }
         leaf vpls-flow-table-size {
           description "VPLS flow table size in units of 256k";
           status deprecated;
           type union {
             type string {
               pattern "<.*>|$.*";
             }
             type uint32 {
               range "1 .. 245";
             }
           }
         }
         leaf bridge-flow-table-size {
           description "BRIDGE flow table size in units of 256k";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           type union {
             type string {
               pattern "<.*>|$.*";
             }
             type uint32 {
               range "1 .. 245";
             }
           }
         }
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container slamon-services {
       description "SLA monitoring services";
       uses apply-advanced;
     }
     list pfe {
       key name;
       description "Packet forwarding engine parameters";
       uses chassis_pfe_type;
     }
     container error {
       description "Error level configuration for FPC";
       uses chassis_fpc_error_type;
     }
   }
   grouping chassis_pem_type {
     uses apply-advanced;
     leaf minimum {
       description "Minimum number of power supplies required for normal operation";
       type union {
         type string {
           pattern "<.*>|$.*";
         }
         type uint32;
       }
     }
     leaf input-current {
       description "Input current (Amps) in each feed ";
       default "60";
       type enumeration {
         enum "40" {
           description "40 Amps in each Feed";
         }
         enum "60" {
           description "60 Amps in each Feed";
         }
       }
     }
   }
   grouping chassis_pfe_type {
     description "PFE(Packet forwarding engine)";
     leaf name {
       description "PFE(Packet forwarding engine) identifier";
       type union {
         type string {
           pattern "<.*>|$.*";
         }
         type uint32;
       }
     }
     uses apply-advanced;
     container forwarding-packages {
       description "Associated forwarding package configuration";
       uses apply-advanced;
       container mobility {
         description "Mobility related PFE configuration";
         uses apply-advanced;
         choice package-type {
           case case_1 {
             leaf user-plane {
               description "User plane function";
               type empty;
             }
           }
         }
       }
     }
     leaf power {
       description "Power PFEs on or off";
       type enumeration {
         enum "off" {
           description "Power off PFE";
         }
         enum "on" {
           description "Power on PFE";
         }
       }
     }
     leaf tunnel-services {
       description "Tunnel services configuration";
       type empty;
     }
   }
   grouping chassis_pic_type {
     leaf name {
       description "PIC slot number";
       type union {
         type string {
           pattern "<.*>|$.*";
         }
         type uint32;
       }
     }
     uses apply-advanced;
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
       }
     }
     choice adaptive-or-monitoring {
       case case_1 {
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf speed {
       description "Port speed";
       type enumeration {
         enum "1G" {
           description "1GE-Gigabit Ethernet";
         }
       }
     }
     leaf aggregate-ports {
       description "Aggregate multiple ports on a PIC as a single port";
       type empty;
     }
     leaf number-of-ports {
       description "Number of physical ports to enable on PIC";
       type union {
         type string {
           pattern "<.*>|$.*";
         }
         type uint32;
       }
     }
     leaf power {
       description "Power off PIC";
       type enumeration {
         enum "off" {
           description "Do not provide power to PIC";
         }
       }
     }
     leaf sparse-dlcis {
       description "Run in sparse data-link connection identifier mode";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf queue-buffer-size {
         description "Set the buffer size of output queue";
         type enumeration {
           enum "small" {
             description "Use small buffer size";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     container services-offload {
       presence "enable services-offload";
       description "Enable services offload";
       uses apply-advanced;
       leaf per-session-statistics {
         description "Keep per session statistics in NP";
         type empty;
       }
       leaf low-latency {
         description "Bypass Traffic Management stage to achieve low latency";
         type empty;
       }
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     container shdsl {
       description "SHDSL chassis configuration";
       uses apply-advanced;
       leaf pic-mode {
         description "PIC mode";
         default "2-port-atm";
         type enumeration {
           enum "1-port-atm" {
             description "Single port ATM, 4 wire mode";
           }
           enum "2-port-atm" {
             description "Two port ATM, 2 wire mode";
           }
           enum "4-port-atm" {
             description "Four port ATM, 2 wire mode";
           }
           enum "efm" {
             description "Single port EFM, 2 wire mode";
           }
         }
       }
     }
     container ethernet {
       description "J-series Ethernet PIM mode configuration";
       uses apply-advanced;
       leaf pic-mode {
         description "PIC mode";
         default "routing";
         type enumeration {
           enum "switching" {
             description "Switched mode of operation";
           }
           enum "routing" {
             description "Routing mode of operation";
           }
           enum "enhanced-switching" {
             description "Enhanced switching mode of operation";
           }
         }
       }
     }
     leaf tunnel-queuing {
       description "Enable queueing for GRE/IPIP tunnels";
       type empty;
     }
     list port-mirror-instance {
       key name;
       ordered-by user;
       max-elements 2;
       leaf name {
         description "Associate a port mirroring instance with the PIC";
         type string {
           length "1 .. 64";
         }
       }
       uses apply-advanced;
     }
     list port {
       key name;
       description "Port number";
       uses chassis_pic_port_framing;
     }
     container fibre-channel {
       description "Fibre channel configuration option";
       uses chassis_fibre_channel_type;
     }
     leaf ingress-policer-overhead {
       description "Number of policer overhead bytes in ingress";
       units "bytes";
       type union {
         type string {
           pattern "<.*>|$.*";
         }
         type uint32 {
           range "0 .. 255";
         }
       }
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     description "Fibre channel configuration option";
     uses apply-advanced;
     list port-range {
       key "port-range-low port-range-high";
       ordered-by user;
       description "Fibre channel port range";
       leaf port-range-low {
         description "Port range low number";
         type union {
           type string {
             pattern "<.*>|$.*";
           }
           type uint32 {
             range "0 .. 47";
           }
         }
       }
       leaf port-range-high {
         description "Port range high number";
         type union {
           type string {
             pattern "<.*>|$.*";
           }
           type uint32 {
             range "0 .. 47";
           }
         }
       }
       uses apply-advanced;
     }
   }
   grouping chassis_pic_port_framing {
     leaf name {
       description "Port number";
       type union {
         type string {
           pattern "<.*>|$.*";
         }
         type uint32;
       }
     }
     uses apply-advanced;
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf speed {
       description "Port speed";
       type enumeration {
         enum "oc3-stm1" {
           description "OC3 or STM1";
         }
         enum "oc12-stm4" {
           description "OC12 or STM4";
         }
         enum "oc48-stm16" {
           description "OC48 or STM16";
         }
         enum "1G" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
   }
   grouping chassis_redundancy_type {
     uses apply-advanced;
     list routing-engine {
       key name;
       description "Redundancy options for Routing Engines";
       uses chassis_rdd_re_type;
     }
     container failover {
       description "Failover to other Routing Engine";
       uses chassis_rdd_failover_type;
     }
     leaf keepalive-time {
       description "Time before Routing Engine failover";
       units "seconds";
       type union {
         type string {
           pattern "<.*>|$.*";
         }
         type uint32 {
           range "2 .. 10000";
         }
       }
     }
     container graceful-switchover {
       description "Enable graceful switchover on supported hardware";
       presence "enable graceful-switchover";
       uses chassis_non_stop_forwarding_type;
     }
   }
   grouping chassis_non_stop_forwarding_type {
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_failover_type {
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_routing_engine_type {
     uses apply-advanced;
     container on-disk-failure {
       description "Action to take when Routing Engine disk fails";
       uses chassis_re_on_disk_failure;
     }
     container control-interface {
       presence "enable control-interface";
       description "Configure recovery method and pause frame for control interface";
       uses apply-advanced;
       leaf recovery-method {
         description "Select the recovery method";
         type enumeration {
           enum "disable-recovery" {
             description "Don't enable recovery";
           }
           enum "socket" {
             description "Recovery by using socket";
           }
           enum "counter" {
             description "Recovery by using BCM-Counters";
           }
         }
       }
       leaf pause-frame {
         description "Enable or disable Pause frame generation";
         type empty;
       }
     }
     container bios {
       description "Routing Engine BIOS";
       uses apply-advanced;
       leaf no-auto-upgrade {
         description "Disable routing-engine BIOS auto-upgrade";
         type empty;
       }
       leaf uninterrupt {
         description "Set routing-engine BIOS uninterruptable";
         type empty;
       }
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           type string {
             length "1 .. 40";
           }
         }
         uses apply-advanced;
         list id {
           key name;
           ordered-by user;
           description "Attribute ids to monitor of this series type";
           max-elements 30;
           leaf name {
             description "SSD smart attribute id";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
     container usb-wwan {
       description "Enable WWAN (3G) access on the USB port";
       uses apply-advanced;
       leaf port {
         description "Select the port";
         type enumeration {
           enum "0" {
             description "Select port 0 to enable WWAN access";
           }
           enum "1" {
             description "Select port 1 to enable WWAN access";
           }
         }
       }
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
     leaf failover {
       description "Redundancy group 0 failover on disk failure";
       type empty;
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping ip-monitoring-address-type {
     description "Define IP address related parameters";
     leaf name {
       description "Define IPv4 address to be monitored";
       type jt:ipv4addr;
     }
     uses apply-advanced;
     leaf weight {
       description "Define weight for this IP address";
       type union {
         type string {
           pattern "<.*>|$.*";
         }
         type uint16 {
           range "0 .. 255";
         }
       }
     }
     list interface {
       key name;
       ordered-by user;
       description "Logical interface through which to monitor this IP address";
       max-elements 1;
       leaf name {
         description "Logical interface name";
         type union {
           type jt:interface-name;
           type string {
             pattern "<.*>|$.*";
           }
         }
       }
       uses apply-advanced;
       leaf secondary-ip-address {
         description "Define source address for monitoring packets on secondary link";
         type jt:ipv4addr;
       }
     }
   }
   grouping juniper-protected-system-domain {
     description "Protected system domain configuration";
     leaf name {
       description "Name of protected system domain (psd[1-31], ex. psd2)";
       type string {
       }
     }
     uses apply-advanced;
     leaf description {
       description "Description of protected system domain";
       type string;
     }
     list lcc {
       key name;
       leaf name {
         description "Specific LCC";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       ordered-by user;
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     leaf name {
       description "Keyword part of the keyword-value pair";
       type string;
     }
     leaf value {
       description "Value part of the keyword-value pair";
       type string;
     }
   }
 }
