/*
 * Copyright (c) 2021 Juniper Networks, Inc.
 * All rights reserved.
 */
 module junos-conf-unified-edge {
   namespace "http://yang.juniper.net/junos/conf/unified-edge";

   prefix jc-unified-edge;

   import junos-common-ddl-extensions {
     prefix junos;
     revision-date 2019-01-01;
   }

   import junos-common-types {
     prefix jt;
     revision-date 2019-01-01;
   }

   import junos-conf-root {
     prefix jc;
     revision-date 2019-01-01;
   }

   organization "Juniper Networks, Inc.";

   contact "yang-support@juniper.net";

   description "Junos unified-edge configuration module";

   revision 2019-01-01 {
     description "Junos: 21.2R1.10";
   }

   augment /jc:configuration {
     uses unified-edge-group;
   }
   augment /jc:configuration/jc:groups {
     uses unified-edge-group;
   }
   grouping unified-edge-group {
     container unified-edge {
       description "Unified edge configuration";
       uses apply-advanced;
       container cos-cac {
         description "Unified Edge COS configuration";
         status deprecated;
         uses juniper-unified-edge-cos-options;
       }
       list local-policies {
         key name;
         ordered-by user;
         description "Local policy profiles";
         status deprecated;
         max-elements 8001;
         leaf name {
           description "Local policy profile name";
           type string {
             junos:posix-pattern "^.{1,64}$";
             junos:pattern-message "Must be string of 64 characters or less";
           }
         }
         uses apply-advanced;
         leaf description {
           description "Text description of local policy";
           type string;
         }
         leaf resource-threshold-profile {
           description "Resource threshold profile associated with the local policy";
           type string;
         }
         leaf classifier-profile {
           description "QoS class profile associated with the local policy";
           type string;
         }
         leaf cos-policy-profile {
           description "QoS policy profile associated with the local policy";
           type string;
         }
         leaf roamer-classifier-profile {
           description "QoS classifier profile for roamers";
           type string;
         }
         leaf roamer-cos-policy-profile {
           description "QoS policy profile for roamers";
           type string;
         }
         leaf visitor-classifier-profile {
           description "QoS classifier profile for visitor";
           type string;
         }
         leaf visitor-cos-policy-profile {
           description "QoS policy profile for visitor";
           type string;
         }
         leaf traffic-class-qci-mapping-profile {
           description "Traffic class to qci mapping profile";
           type string {
             length "1 .. 128";
           }
         }
         leaf ul-bandwidth-pool {
           description "Bandwidth pool associated with the local policy";
           type string;
         }
         leaf dl-bandwidth-pool {
           description "Bandwidth pool associated with the local policy";
           type string;
         }
       }
       container aaa {
         description "AAA configuration";
         uses apply-advanced;
         container traceoptions {
           uses aaa-traceoptions;
         }
         list profiles {
           key name;
           ordered-by user;
           description "AAA profile configuration";
           uses aaa-profile;
         }
       }
       container diameter-profiles {
         description "Unified Edge Diameter application configurations";
         uses mobile-diameter-profiles;
       }
       container gateways {
         junos:must "(!(\"system services subscriber-management enable\"))";
         junos:must-message "unified-edge gateway is not allowed when subscriber-management is configured";
         description "Gateways configuration";
         uses apply-advanced;
         list ggsn-pgw {
           key name;
           ordered-by user;
           description "GGSN-PGW Configuration";
           status deprecated;
           max-elements 16;
           leaf name {
             description "Gateway name";
             type string {
               length "1 .. 63";
             }
           }
           uses apply-advanced;
           leaf service-mode {
             description "Service mode";
             type enumeration {
               enum "maintenance" {
                 description "Maintenance mode";
               }
             }
           }
           leaf maximum-bearers {
             description "Maximum bearers for the GW";
             type union {
               type string {
                 pattern "<.*>|$.*";
               }
               type uint32 {
                 range "100000 .. 12000000";
               }
             }
           }
           leaf session-timeout-check-interval {
             description "Session timeout checking interval in minutes";
             default "15";
             units "in minutes";
             type union {
               type string {
                 pattern "<.*>|$.*";
               }
               type uint32 {
                 range "5 .. 600";
               }
             }
           }
           leaf redirect-timeout {
             description "Delay before a redirected session is deleted";
             default "15";
             units "in seconds";
             type union {
               type string {
                 pattern "<.*>|$.*";
               }
               type uint32 {
                 range "15 .. 120";
               }
             }
           }
           leaf local-policy-profile {
             description "Local profile for the system level";
             type string;
           }
           container pfes {
             presence "enable pfes";
             description "PFE Configuration";
             uses apply-advanced;
             leaf guaranteed-bandwidth {
               description "PFE guaranteed bandwidth";
               default "40";
               units "gigabits per second";
               type union {
                 type string {
                   pattern "<.*>|$.*";
                 }
                 type uint32 {
                   range "10 .. 100";
                 }
               }
             }
             leaf maximum-bearers {
               description "PFE maximum bearers";
               default "510";
               units "in thousands";
               type union {
                 type string {
                   pattern "<.*>|$.*";
                 }
                 type uint32 {
                   range "100 .. 510";
                 }
               }
             }
             leaf default-bearers-percentage {
               description "PFE default bearer percentage";
               default "100";
               units "percentage of maximum pfe bearers";
               type union {
                 type string {
                   pattern "<.*>|$.*";
                 }
                 type uint32 {
                   range "10 .. 100";
                 }
               }
             }
             leaf ipv4-nbm-prefixes {
               description "PFE IPv4 prefixes limit for NBM";
               default "64";
               units "number of prefixes in multiples of 1K";
               type union {
                 type string {
                   pattern "<.*>|$.*";
                 }
                 type uint32 {
                   range "16 .. 128";
                 }
               }
             }
             leaf ipv6-nbm-prefixes {
               description "PFE IPv6 prefixes limit for NBM";
               default "16";
               units "number of prefixes in multiples of 1K";
               type union {
                 type string {
                   pattern "<.*>|$.*";
                 }
                 type uint32 {
                   range "4 .. 128";
                 }
               }
             }
             leaf maximum-sdfs {
               description "PFE maximum SDFs";
               default "510";
               units "in thousands";
               type union {
                 type string {
                   pattern "<.*>|$.*";
                 }
                 type uint32 {
                   range "100 .. 510";
                 }
               }
             }
           }
           leaf anchor-pfe-guaranteed-bandwidth {
             description "PFE guaranteed bandwidth";
             status deprecated;
             default "40";
             units "gigabits per second";
             type union {
               type string {
                 pattern "<.*>|$.*";
               }
               type uint32 {
                 range "10 .. 100";
               }
             }
           }
           leaf anchor-pfe-maximum-bearers {
             description "PFE maximum bearers";
             status deprecated;
             default "510";
             units "in thousands";
             type union {
               type string {
                 pattern "<.*>|$.*";
               }
               type uint32 {
                 range "100 .. 510";
               }
             }
           }
           leaf anchor-pfe-default-bearers-percentage {
             description "PFE default bearer percentage";
             status deprecated;
             default "100";
             units "percentage of maximum pfe bearers";
             type union {
               type string {
                 pattern "<.*>|$.*";
               }
               type uint32 {
                 range "10 .. 100";
               }
             }
           }
           leaf anchor-pfe-ipv4-nbm-prefixes {
             description "PFE IPv4 prefixes limit for NBM";
             status deprecated;
             default "64";
             units "number of prefixes in multiples of 1K";
             type union {
               type string {
                 pattern "<.*>|$.*";
               }
               type uint32 {
                 range "16 .. 128";
               }
             }
           }
           leaf anchor-pfe-ipv6-nbm-prefixes {
             description "PFE IPv6 prefixes limit for NBM";
             status deprecated;
             default "16";
             units "number of prefixes in multiples of 1K";
             type union {
               type string {
                 pattern "<.*>|$.*";
               }
               type uint32 {
                 range "4 .. 128";
               }
             }
           }
           container preemption {
             presence "enable preemption";
             description "Pre-Emption configuration";
             uses apply-advanced;
             leaf enable {
               description "Preemption-enabled - default is disabled";
               type empty;
             }
             leaf gtpv1-pvi-disable {
               description "Preemption Vulnerability indicator disabled - default is Enabled";
               type empty;
             }
             leaf gtpv1-pci-disable {
               description "Preemption Capability indicator disabled - default is Enabled";
               type empty;
             }
           }
           container gtp {
             description "GTP configuration";
             uses mobile-gateway-config-gtp;
           }
           container home-plmn {
             description "Configure home PLMN MCC MNC values";
             uses apply-advanced;
             list mcc {
               key "mcc mnc";
               ordered-by user;
               description "Enter MCC value";
               leaf mcc {
                 description "Mobile country code";
                 type string {
                   length 3;
                   junos:posix-pattern "^[0-9]*$";
                 }
               }
               leaf mnc {
                 description "Mobile network code";
                 type string {
                   length "2 .. 3";
                   junos:posix-pattern "^[0-9]*$";
                 }
               }
               uses apply-advanced;
             }
           }
           container traceoptions {
             description "Trace options related to mobile subscriber management";
             uses mobile-smd-traceoptions;
           }
           container call-rate-statistics {
             presence "enable call-rate-statistics";
             description "Call-rate-statistics options";
             uses apply-advanced;
             leaf interval {
               description "Time interval in minutes";
               default "60";
               units "minutes";
               type union {
                 type string {
                   pattern "<.*>|$.*";
                 }
                 type uint32 {
                   range "5 .. 120";
                 }
               }
             }
             leaf history {
               description "Number of intervals";
               default "1";
               type union {
                 type string {
                   pattern "<.*>|$.*";
                 }
                 type uint32 {
                   range "1 .. 20";
                 }
               }
             }
           }
           list service-selection-profiles {
             key name;
             ordered-by user;
             description "Profile definition";
             leaf name {
               description "Name of service selection profile";
               type string {
                 length "1 .. 63";
               }
             }
             uses apply-advanced;
             list term {
               key name;
               ordered-by user;
               description "Define a selection term";
               max-elements 64;
               leaf name {
                 description "Term name";
                 type string {
                   length "1 .. 63";
                 }
               }
               uses apply-advanced;
               container from {
                 description "Define match criteria";
                 uses apply-advanced;
                 leaf imsi {
                   description "Match IMSI";
                   type string {
                     length "1 .. 15";
                     junos:posix-pattern "^[0-9]*$";
                   }
                 }
                 leaf msisdn {
                   description "Match MSISDN";
                   type string {
                     length "1 .. 15";
                     junos:posix-pattern "^[0-9]*$";
                   }
                 }
                 leaf imei {
                   description "Match IMEI";
                   type string {
                     length "1 .. 16";
                     junos:posix-pattern "^[0-9]*$";
                   }
                 }
                 leaf anonymous-user {
                   description "Match anonymous users";
                   type empty;
                 }
                 leaf domain-name {
                   description "Match domain name";
                   type string {
                     length "1 .. 63";
                   }
                 }
                 leaf roaming-status {
                   description "Match roaming status";
                   type enumeration {
                     enum "home" {
                       description "Home subscribers";
                     }
                     enum "roamer" {
                       description "Roaming subscribers";
                     }
                     enum "visitor" {
                       description "Visiting subscribers";
                     }
                   }
                 }
                 container plmn {
                   description "Match PLMN MCC MNC values";
                   uses apply-advanced;
                   list mcc {
                     key "mcc mnc";
                     ordered-by user;
                     description "Enter MCC value";
                     max-elements 8;
                     leaf mcc {
                       description "Mobile country code";
                       type string {
                         length 3;
                         junos:posix-pattern "^[0-9]*$";
                       }
                     }
                     leaf mnc {
                       description "Mobile network code";
                       type string {
                         length "2 .. 3";
                         junos:posix-pattern "^[0-9]*$";
                       }
                     }
                     uses apply-advanced;
                   }
                   leaf except {
                     description "Except the specified plmns";
                     junos:must "(\".. mcc\")";
                     junos:must-message "MCC-MNC should be defined";
                     type empty;
                   }
                 }
                 leaf charging-characteristics {
                   description "Match charging characteristics";
                   type union {
                     type string {
                       pattern "<.*>|$.*";
                     }
                     type uint32 {
                       range "1 .. 65535";
                     }
                   }
                 }
                 leaf maximum-bearers {
                   description "Maximum bearers in the gateway";
                   type union {
                     type string {
                       pattern "<.*>|$.*";
                     }
                     type uint32 {
                       range "1 .. 10000000";
                     }
                   }
                 }
                 leaf peer {
                   description "IP address of the peer creating the session";
                   type jt:ipaddr;
                 }
                 leaf peer-routing-instance {
                   description "Routing instance of the peer creating the session";
                   junos:must "(\"routing-instances $$\")";
                   junos:must-message "Routing instance not present";
                   type string {
                     junos:posix-pattern "!^((__.*__)|(all)|(.*[ ].*)|(\"\")|(.{129,}))$";
                     junos:pattern-message "Must be a non-reserved string of 128 characters or less with no spaces.";
                   }
                 }
                 leaf pdn-type {
                   description "Match pdn type";
                   type enumeration {
                     enum "ipv4" {
                       description "IPv4 Data type";
                     }
                     enum "ipv6" {
                       description "IPv6 Data type";
                     }
                     enum "ipv4v6" {
                       description "IPv4v6 Data type";
                     }
                   }
                 }
                 leaf rat-type {
                   description "Radio Access Technology  Type";
                   type enumeration {
                     enum "geran" {
                       description "RAT type is GERAN";
                     }
                     enum "utran" {
                       description "RAT type is UTRAN";
                     }
                     enum "eutran" {
                       description "RAT type is EUTRAN";
                     }
                     enum "wlan" {
                       description "RAT type is WLAN";
                     }
                     enum "hspa" {
                       description "RAT type is HSPA";
                     }
                   }
                 }
               }
               container then {
                 description "Action to take if the 'from' condition is matched";
                 uses apply-advanced;
                 list redirect-peer {
                   key name;
                   ordered-by user;
                   description "IP address of the redirect peer";
                   junos:must "((!(\".. apn-name\") && (!(\".. pcef-profile\") && !(\".. charging-profile\"))))";
                   junos:must-message "Redirect peer cannot be combined with other actions";
                   max-elements 8;
                   leaf name {
                     description "Peer IP address";
                     type jt:ipaddr;
                   }
                 }
                 leaf accept {
                   description "Stop matching futher terms and accept";
                   junos:must "((!(\".. apn-name\") && (!(\".. redirect-peer\") && (!(\".. pcef-profile\") && !(\".. charging-profile\")))))";
                   junos:must-message "Accept can not be combined with other actions";
                   type empty;
                 }
                 leaf reject {
                   description "Reject the connection attempt";
                   junos:must "((!(\".. apn-name\") && (!(\".. redirect-peer\") && (!(\".. accept\") && (!(\".. pcef-profile\") && !(\".. charging-profile\"))))))";
                   junos:must-message "Reject can not be combined with other actions";
                   type empty;
                 }
                 leaf apn-name {
                   description "Real APN name";
                   junos:must "((\".. .. .. .. apn-services apns $$\" && (!(\".. .. .. .. apn-services apns $$ apn-type virtual\") && !(\".. .. .. .. apn-services apns $$ apn-type virtual-pre-authenticate\"))))";
                   junos:must-message "Referenced apn must be configured";
                   type string {
                     length "1 .. 100";
                   }
                 }
                 leaf pcef-profile {
                   description "PCEF profile for service selection profile";
                   junos:must "(\".. .. .. .. .. .. pcef profiles $$\")";
                   junos:must-message "Referenced PCEF profile must be defined";
                   type string {
                     length "1 .. 63";
                   }
                 }
                 leaf charging-profile {
                   description "Charging profile for service selection profile";
                   junos:must "(\".. .. .. ..  charging charging-profiles $$\")";
                   junos:must-message "Referenced Charging Profile must be defined";
                   type string {
                     length "1 .. 128";
                   }
                 }
               }
             }
           }
           container apn-services {
             description "Apn services configuration";
             uses ggsn-pgw-apn-services;
           }
           container system {
             description "System parameters";
             uses unified-edge-ggsn-pgw-system;
           }
           container diameter {
             description "Diameter protocol parameters specific to gateway";
             uses unified-edge-gateway-diameter;
           }
           container charging {
             presence "enable charging";
             description "PGW charging profile definitions";
             uses apply-advanced;
             container traceoptions {
               description "Charging trace options";
               uses charging-traceoptions;
             }
             container charging-profiles {
               description "Charging profile";
               uses apply-advanced;
               list charging-profile {
                 key name;
                 max-elements 255;
                 uses juniper-charging-profiles;
               }
             }
             container transport-profiles {
               description "Transport profile definition";
               uses apply-advanced;
               list transport-profile {
                 key name;
                 max-elements 8;
                 uses juniper-transport-profiles;
               }
             }
             container cdr-profiles {
               description "CDR profiles definition";
               uses apply-advanced;
               list cdr-profile {
                 key name;
                 description "CDR profile definition";
                 max-elements 255;
                 uses juniper-cdr-profiles;
               }
             }
             container trigger-profiles {
               description "Trigger profile definition";
               uses apply-advanced;
               list trigger-profile {
                 key name;
                 ordered-by user;
                 max-elements 16;
                 uses juniper-trigger-profiles;
               }
             }
             container local-persistent-storage-options {
               description "Local persistent storage configuration";
               uses juniper-charged-configuraton;
             }
             container gtpp {
               description "Configuration for GTPP protocol for charging";
               uses apply-advanced;
               container source-interface {
                 description "Source interface from which GTPP packets will be sent";
                 leaf interface-name {
                   description "Interface name";
                   junos:must "(\"interfaces $$\")";
                   junos:must-message "Interface must be defined";
                   type union {
                     type jt:interface-name;
                     type string {
                       pattern "<.*>|$.*";
                     }
                   }
                 }
                 leaf ipv4-address {
                   description "Source IPv4 address to be used";
                   type jt:ipv4addr;
                 }
               }
               leaf destination-port {
                 description "Destination port number of the CGF Server";
                 type union {
                   type string {
                     pattern "<.*>|$.*";
                   }
                   type uint32 {
                     range "1 .. 65535";
                   }
                 }
               }
               leaf n3-requests {
                 description "Number of retries of GTPP messages upon timeout";
                 default "3";
                 type union {
                   type string {
                     pattern "<.*>|$.*";
                   }
                   type uint16 {
                     range "1 .. 5";
                   }
                 }
               }
               leaf transport-protocol {
                 description "Default Transport protocol(udp/tcp) used";
                 type enumeration {
                   enum "udp" {
                     description "GTPP over udp";
                   }
                   enum "tcp" {
                     description "GTPP over tcp";
                   }
                 }
               }
               leaf version {
                 description "GTPP version V0|V1|V2";
                 type enumeration {
                   enum "v0" {
                     description "GTPP version V0";
                   }
                   enum "v1" {
                     description "GTPP version V1";
                   }
                   enum "v2" {
                     description "GTPP version V2";
                   }
                 }
               }
               leaf echo-interval {
                 description "GTPP echo-interval in seconds";
                 default "60";
                 units "seconds";
                 type union {
                   type string {
                     pattern "<.*>|$.*";
                   }
                   type uint32 {
                     range "60 .. 255";
                   }
                 }
               }
               leaf no-path-management {
                 description "Disables path management";
                 junos:must "(!(\".. echo-interval\"))";
                 junos:must-message "no-path-management option can not be used with echo-interval";
                 type empty;
               }
               leaf t3-response {
                 description "Response timeout value for GTPP request message";
                 default "5";
                 units "seconds";
                 type union {
                   type string {
                     pattern "<.*>|$.*";
                   }
                   type uint16 {
                     range "1 .. 5";
                   }
                 }
               }
               leaf header-type {
                 description "GTPP protocol header type short|long";
                 type enumeration {
                   enum "short" {
                     description "GTPP short header";
                   }
                   enum "long" {
                     description "GTPP long (20-byte) header";
                   }
                 }
               }
               leaf pending-queue-size {
                 description "Maximum number of DRT messages awaiting an ack";
                 default "1024";
                 type union {
                   type string {
                     pattern "<.*>|$.*";
                   }
                   type uint32 {
                     range "1 .. 4096";
                   }
                 }
               }
               leaf down-detect-time {
                 description "Time (in sec) to wait before declaring a CGF as Down";
                 default "10";
                 units "seconds";
                 type union {
                   type string {
                     pattern "<.*>|$.*";
                   }
                   type uint32 {
                     range "0 .. 255";
                   }
                 }
               }
               leaf reconnect-time {
                 description "Time (in sec) after which connection to the CGF server should be retried";
                 default "60";
                 units "seconds";
                 type union {
                   type string {
                     pattern "<.*>|$.*";
                   }
                   type uint32 {
                     range "60 .. 255";
                   }
                 }
               }
               list peer {
                 key name;
                 description "GTPP peer object";
                 max-elements 24;
                 uses gtpp-peer;
               }
             }
           }
           container ip-reassembly-profile {
             description "IP reassembly profile for mobile gateways";
             uses apply-advanced;
             leaf profile-name {
               description "IP reassembly profile name";
               junos:must "(\"services ip-reassembly profile $$\")";
               junos:must-message "Referenced profile must be defined";
               type string {
                 length "1 .. 32";
               }
             }
           }
           container ipv6-router-advertisement {
             description "IPv6 router advertisement configuration for GGSN/PGW";
             presence "enable ipv6-router-advertisement";
             uses mobile-gateways-ipv6-router-advertisement;
           }
           container software-datapath {
             presence "enable software-datapath";
             description "Mobility software datapath options";
             uses apply-advanced;
             container traceoptions {
               description "Mobility software datapath trace options";
               uses software-datapath-traceoptions;
             }
           }
           container inline-services {
             description "Inline services";
             uses apply-advanced;
             container ip-reassembly {
               presence "enable ip-reassembly";
               description "IP reassembly";
               uses apply-advanced;
               container service-set {
                 description "Inline IP reassembly service set for mobile gateways";
                 uses apply-advanced;
                 leaf service-set-name {
                   description "Inline IP reassembly service-set name";
                   junos:must "(\"services service-set $$\")";
                   junos:must-message "Service set name must be defined in the [edit services service-set] hierarchy";
                   type string {
                     length "1 .. 63";
                   }
                 }
               }
             }
           }
         }
         list sgw {
           key name;
           ordered-by user;
           description "Serving Gateway Configuration";
           status deprecated;
           max-elements 16;
           leaf name {
             description "Gateway name";
             type string {
               length "1 .. 63";
             }
           }
           uses apply-advanced;
           leaf service-mode {
             description "Service mode";
             type enumeration {
               enum "maintenance" {
                 description "Maintenance mode";
               }
             }
           }
           leaf maximum-bearers {
             description "Maximum bearers for the GW";
             type union {
               type string {
                 pattern "<.*>|$.*";
               }
               type uint32 {
                 range "100000 .. 12000000";
               }
             }
           }
           leaf local-policy-profile {
             description "Local profile for the system level";
             type string;
           }
           container pfes {
             presence "enable pfes";
             description "PFE Configuration";
             uses apply-advanced;
             leaf guaranteed-bandwidth {
               description "PFE guaranteed bandwidth";
               default "40";
               units "gigabits per second";
               type union {
                 type string {
                   pattern "<.*>|$.*";
                 }
                 type uint32 {
                   range "10 .. 100";
                 }
               }
             }
             leaf maximum-bearers {
               description "PFE maximum bearers";
               default "510";
               units "in thousands";
               type union {
                 type string {
                   pattern "<.*>|$.*";
                 }
                 type uint32 {
                   range "100 .. 510";
                 }
               }
             }
             leaf default-bearers-percentage {
               description "PFE default bearer percentage";
               default "100";
               units "percentage of maximum pfe bearers";
               type union {
                 type string {
                   pattern "<.*>|$.*";
                 }
                 type uint32 {
                   range "10 .. 100";
                 }
               }
             }
           }
           leaf anchor-pfe-guaranteed-bandwidth {
             description "PFE guaranteed bandwidth";
             status deprecated;
             default "40";
             units "gigabits per second";
             type union {
               type string {
                 pattern "<.*>|$.*";
               }
               type uint32 {
                 range "10 .. 100";
               }
             }
           }
           leaf anchor-pfe-maximum-bearers {
             description "PFE maximum bearers";
             status deprecated;
             default "510";
             units "in thousands";
             type union {
               type string {
                 pattern "<.*>|$.*";
               }
               type uint32 {
                 range "100 .. 510";
               }
             }
           }
           leaf anchor-pfe-default-bearers-percentage {
             description "PFE default bearer percentage";
             status deprecated;
             default "100";
             units "percentage of maximum pfe bearers";
             type union {
               type string {
                 pattern "<.*>|$.*";
               }
               type uint32 {
                 range "10 .. 100";
               }
             }
           }
           container preemption {
             presence "enable preemption";
             description "Pre-Emption configuration";
             uses apply-advanced;
             leaf enable {
               description "Preemption-enabled - default is disabled";
               type empty;
             }
           }
           leaf remote-delete-on-peer-fail {
             description "Send delete towards remote peer if other peer fails";
             type empty;
           }
           container gtp {
             description "GTP configuration";
             uses sgw-config-gtp;
           }
           container home-plmn {
             description "Configure home PLMN MCC MNC values";
             uses apply-advanced;
             list mcc {
               key "mcc mnc";
               ordered-by user;
               description "Enter MCC value";
               leaf mcc {
                 description "Mobile country code";
                 type string {
                   length 3;
                   junos:posix-pattern "^[0-9]*$";
                 }
               }
               leaf mnc {
                 description "Mobile network code";
                 type string {
                   length "2 .. 3";
                   junos:posix-pattern "^[0-9]*$";
                 }
               }
               uses apply-advanced;
             }
           }
           container traceoptions {
             description "Trace options related to mobile subscriber management";
             uses mobile-smd-traceoptions;
           }
           container call-rate-statistics {
             presence "enable call-rate-statistics";
             description "Call rate statistics options";
             uses apply-advanced;
             leaf interval {
               description "Time interval in minutes";
               default "60";
               units "minutes";
               type union {
                 type string {
                   pattern "<.*>|$.*";
                 }
                 type uint32 {
                   range "5 .. 120";
                 }
               }
             }
             leaf history {
               description "Number of intervals";
               default "1";
               type union {
                 type string {
                   pattern "<.*>|$.*";
                 }
                 type uint32 {
                   range "1 .. 20";
                 }
               }
             }
           }
           container system {
             description "System parameters";
             uses unified-edge-sgw-system;
           }
           container charging {
             presence "enable charging";
             description "SGW charging profile definitions";
             uses apply-advanced;
             container traceoptions {
               description "Charging trace options";
               uses charging-traceoptions;
             }
             container charging-profiles {
               description "Charging profile";
               uses apply-advanced;
               list charging-profile {
                 key name;
                 max-elements 255;
                 uses juniper-charging-profiles;
               }
             }
             container transport-profiles {
               description "Transport profile definition";
               uses apply-advanced;
               list transport-profile {
                 key name;
                 max-elements 8;
                 uses juniper-transport-profiles;
               }
             }
             container cdr-profiles {
               description "CDR profiles definition";
               uses apply-advanced;
               list cdr-profile {
                 key name;
                 description "CDR profile definition";
                 max-elements 255;
                 uses juniper-cdr-profiles;
               }
             }
             container trigger-profiles {
               description "Trigger profile definition";
               uses apply-advanced;
               list trigger-profile {
                 key name;
                 ordered-by user;
                 max-elements 16;
                 uses juniper-trigger-profiles;
               }
             }
             container local-persistent-storage-options {
               description "Local persistent storage configuration";
               uses juniper-charged-configuraton;
             }
             container gtpp {
               description "Configuration for GTPP protocol for charging";
               uses apply-advanced;
               container source-interface {
                 description "Source interface from which GTPP packets will be sent";
                 leaf interface-name {
                   description "Interface name";
                   junos:must "(\"interfaces $$\")";
                   junos:must-message "Interface must be defined";
                   type union {
                     type jt:interface-name;
                     type string {
                       pattern "<.*>|$.*";
                     }
                   }
                 }
                 leaf ipv4-address {
                   description "Source IPv4 address to be used";
                   type jt:ipv4addr;
                 }
               }
               leaf destination-port {
                 description "Destination port number of the CGF Server";
                 type union {
                   type string {
                     pattern "<.*>|$.*";
                   }
                   type uint32 {
                     range "1 .. 65535";
                   }
                 }
               }
               leaf n3-requests {
                 description "Number of retries of GTPP messages upon timeout";
                 default "3";
                 type union {
                   type string {
                     pattern "<.*>|$.*";
                   }
                   type uint16 {
                     range "1 .. 5";
                   }
                 }
               }
               leaf transport-protocol {
                 description "Default Transport protocol(udp/tcp) used";
                 type enumeration {
                   enum "udp" {
                     description "GTPP over udp";
                   }
                   enum "tcp" {
                     description "GTPP over tcp";
                   }
                 }
               }
               leaf version {
                 description "GTPP version V0|V1|V2";
                 type enumeration {
                   enum "v0" {
                     description "GTPP version V0";
                   }
                   enum "v1" {
                     description "GTPP version V1";
                   }
                   enum "v2" {
                     description "GTPP version V2";
                   }
                 }
               }
               leaf echo-interval {
                 description "GTPP echo-interval in seconds";
                 default "60";
                 units "seconds";
                 type union {
                   type string {
                     pattern "<.*>|$.*";
                   }
                   type uint32 {
                     range "60 .. 255";
                   }
                 }
               }
               leaf no-path-management {
                 description "Disables path management";
                 junos:must "(!(\".. echo-interval\"))";
                 junos:must-message "no-path-management option can not be used with echo-interval";
                 type empty;
               }
               leaf t3-response {
                 description "Response timeout value for GTPP request message";
                 default "5";
                 units "seconds";
                 type union {
                   type string {
                     pattern "<.*>|$.*";
                   }
                   type uint16 {
                     range "1 .. 5";
                   }
                 }
               }
               leaf header-type {
                 description "GTPP protocol header type short|long";
                 type enumeration {
                   enum "short" {
                     description "GTPP short header";
                   }
                   enum "long" {
                     description "GTPP long (20-byte) header";
                   }
                 }
               }
               leaf pending-queue-size {
                 description "Maximum number of DRT messages awaiting an ack";
                 default "1024";
                 type union {
                   type string {
                     pattern "<.*>|$.*";
                   }
                   type uint32 {
                     range "1 .. 4096";
                   }
                 }
               }
               leaf down-detect-time {
                 description "Time (in sec) to wait before declaring a CGF as Down";
                 default "10";
                 units "seconds";
                 type union {
                   type string {
                     pattern "<.*>|$.*";
                   }
                   type uint32 {
                     range "0 .. 255";
                   }
                 }
               }
               leaf reconnect-time {
                 description "Time (in sec) after which connection to the CGF server should be retried";
                 default "60";
                 units "seconds";
                 type union {
                   type string {
                     pattern "<.*>|$.*";
                   }
                   type uint32 {
                     range "60 .. 255";
                   }
                 }
               }
               list peer {
                 key name;
                 description "GTPP peer object";
                 max-elements 24;
                 uses gtpp-peer;
               }
             }
             container global-profile {
               description "Global charging profiles";
               uses apply-advanced;
               leaf default-profile {
                 description "Global charging profile for SGW";
                 junos:must "(\"unified-edge gateways sgw ${sgw} charging charging-profiles $$\")";
                 junos:must-message "Charging profile must be defined before it can be used";
                 type string;
               }
               leaf home-profile {
                 description "Global home profile for SGW";
                 junos:must "(\"unified-edge gateways sgw ${sgw} charging charging-profiles $$\")";
                 junos:must-message "Charging profile must be defined before it can be used";
                 type string;
               }
               leaf roamer-profile {
                 description "Global roamer profile for SGW";
                 junos:must "(\"unified-edge gateways sgw ${sgw} charging charging-profiles $$\")";
                 junos:must-message "Charging profile must be defined before it can be used";
                 type string;
               }
               leaf visitor-profile {
                 description "Global visitor profile for SGW";
                 junos:must "(\"unified-edge gateways sgw ${sgw} charging charging-profiles $$\")";
                 junos:must-message "Charging profile must be defined before it can be used";
                 type string;
               }
               leaf-list profile-selection-order {
                 ordered-by user;
                 description "Global charging profile selection order";
                 type enumeration {
                   enum "static" {
                     description "Select charging profile locally configured";
                   }
                   enum "serving" {
                     description "Select charging profile sent by MME";
                   }
                   enum "pgw-cg-addr" {
                     description "Select charging profile based on PGW's CG Address";
                   }
                 }
               }
             }
           }
           container ip-reassembly-profile {
             description "IP reassembly profile for mobile gateways";
             uses apply-advanced;
             leaf profile-name {
               description "IP reassembly profile name";
               junos:must "(\"services ip-reassembly profile $$\")";
               junos:must-message "Referenced profile must be defined";
               type string {
                 length "1 .. 32";
               }
             }
           }
           container idle-mode-buffering {
             description "Idle mode buffering";
             uses sgw-idle-mode-buffering;
           }
           container software-datapath {
             presence "enable software-datapath";
             description "Mobility software datapath options";
             uses apply-advanced;
             container traceoptions {
               description "Mobility software datapath trace options";
               uses software-datapath-traceoptions;
             }
           }
           container inline-services {
             description "Inline services";
             uses apply-advanced;
             container ip-reassembly {
               presence "enable ip-reassembly";
               description "IP reassembly";
               uses apply-advanced;
               container service-set {
                 description "Inline IP reassembly service set for mobile gateways";
                 uses apply-advanced;
                 leaf service-set-name {
                   description "Inline IP reassembly service-set name";
                   junos:must "(\"services service-set $$\")";
                   junos:must-message "Service set name must be defined in the [edit services service-set] hierarchy";
                   type string {
                     length "1 .. 63";
                   }
                 }
               }
             }
           }
         }
         list tdf {
           key name;
           ordered-by user;
           description "Traffic Detection Function Configuration";
           max-elements 1;
           uses unified-edge-tdf;
         }
       }
       container mobile-options {
         description "Mobile options";
         uses unified-edge-mobile-options;
       }
       container pcef {
         description "PCEF configuration";
         junos:must "(!(\"system services subscriber-management enable\"))";
         junos:must-message "unified-edge pcef is not allowed only when enhanced-ip is configured";
         uses unified-edge-pcef;
       }
       container resource-management {
         description "Configure Resource Mangement Packet Steering Daemon";
         uses apply-advanced;
         container server {
           description "Configure Resource Mangement Packet Steering Daemon";
           uses apply-advanced;
           container traceoptions {
             description "Resource Management Packet Steering Daemon trace options";
             uses rmpsd-traceoptions-type;
           }
         }
         container client {
           description "Configure Resource Mangement Packet Steering Client";
           uses apply-advanced;
           container traceoptions {
             description "Resource Management Packet Steering Client trace options";
             uses rmps-clnt-traceoptions-type;
           }
         }
       }
     }
   }
   grouping aaa-profile {
     description "AAA profile configuration";
     leaf name {
       description "AAA profile name";
       type string {
         length "1 .. 32";
       }
     }
     uses apply-advanced;
     container radius {
       description "Specify RADIUS options";
       junos:must "((\".. radius authentication network-element\" || (\".. radius accounting network-element\" || \".. radius accounting network-element-group\")))";
       junos:must-message "authentication or accounting network element or network element group must be defined";
       uses aaa-profile-radius;
     }
   }
   grouping aaa-profile-radius {
     uses apply-advanced;
     container authentication {
       description "Specify RADIUS authentication parameters";
       uses apply-advanced;
       leaf network-element {
         description "The network-element used for authentication";
         junos:must "(\"access radius network-elements $$\")";
         junos:must-message "referenced network-element must be defined";
         type string {
           length "1 .. 31";
         }
       }
     }
     container accounting {
       description "Specify RADIUS accounting parameters";
       uses apply-advanced;
       leaf network-element {
         description "The network-element used for accounting";
         junos:must "(!(\".. network-element-group\"))";
         junos:must-message "only one of accounting network-element or network-element-group can be specified";
         junos:must "(\"access radius network-elements $$\")";
         junos:must-message "referenced network-element must be defined";
         type string {
           length "1 .. 31";
         }
       }
     }
     container policy {
       description "Specify RADIUS policy parameters";
       uses apply-advanced;
       container activation-attribute {
         description "Configure the attribute used for policy activation";
         uses apply-advanced;
         leaf code {
           description "Attribute code";
           type union {
             type string {
               pattern "<.*>|$.*";
             }
             type uint8 {
               range "0 .. 255";
             }
           }
         }
         leaf vendor-id {
           description "Attribute vendor-id";
           type union {
             type string {
               pattern "<.*>|$.*";
             }
             type uint32 {
               range "0 .. 65534";
             }
           }
         }
       }
       container deactivation-attribute {
         description "Configure the attribute used for policy deactivation";
         uses apply-advanced;
         leaf code {
           description "Attribute code";
           type union {
             type string {
               pattern "<.*>|$.*";
             }
             type uint8 {
               range "0 .. 255";
             }
           }
         }
         leaf vendor-id {
           description "Attribute vendor-id";
           type union {
             type string {
               pattern "<.*>|$.*";
             }
             type uint32 {
               range "0 .. 65534";
             }
           }
         }
       }
       leaf coa-accounting {
         description "Allow/disallow accounting to the CoA server";
         type enumeration {
           enum "allow" {
             description "Enable accounting to the CoA server";
             junos:must "(\".. .. accounting network-element\")";
             junos:must-message "Accounting network-element must be configured";
           }
           enum "disallow" {
             description "Disable accounting to the CoA server";
           }
         }
       }
     }
   }
   grouping aaa-traceoptions {
     description "Trace options related to AAA operation";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "request" {
             description "Trace requests";
           }
           enum "response" {
             description "Trace response";
           }
           enum "high-availability" {
             description "Trace high availability events";
           }
           enum "debug" {
             description "Trace debug internal events";
           }
           enum "request-in" {
             description "Trace Incoming Diameter request events";
           }
           enum "request-out" {
             description "Trace Outgoing Diameter request events";
           }
           enum "response-in" {
             description "Trace Incoming Radius Client response events";
           }
           enum "response-out" {
             description "Trace Outgoing Radius Client response events";
           }
           enum "client-request-in" {
             description "Trace Incoming Radius Client request events";
           }
           enum "client-request-out" {
             description "Trace Outgoing Radius Client request events";
           }
           enum "all" {
             description "Trace everything";
           }
         }
       }
     }
     list protocol {
       key name;
       ordered-by user;
       description "AAA Protocol to trace";
       leaf name {
         type enumeration {
           enum "radius" {
             description "Trace radius protocols only";
           }
           enum "diameter" {
             description "Trace diameter protocols only";
           }
           enum "all" {
             description "Trace both radius and protocols";
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping charging-traceoptions {
     description "Trace options related to charging operation";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "critical" {
           description "Match critical error conditions";
         }
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "triggers" {
             description "Trace trigger information";
           }
           enum "cdr-encoding" {
             description "Trace CDR encoding";
           }
           enum "transport" {
             description "Trace transport group";
           }
           enum "path-management" {
             description "Trace path management module";
           }
           enum "fsm" {
             description "Trace FSM";
           }
           enum "ipc" {
             description "Trace IPC";
           }
           enum "resource" {
             description "Trace resources";
           }
           enum "group-fsm" {
             description "Trace group FSM";
           }
           enum "client-fsm" {
             description "Trace client FSM";
           }
           enum "timers" {
             description "Trace resources";
           }
           enum "online" {
             description "Trace Gy ASM module";
           }
           enum "tpm" {
             description "Trace online processing module";
           }
           enum "all" {
             description "Trace everything";
           }
         }
       }
     }
   }
   grouping ggsn-pgw-apn-services {
     description "Apn services configuration";
     uses apply-advanced;
     container apns {
       description "Apn configuration";
       uses apply-advanced;
       list apn {
         key name;
         uses ggsn-pgw-apn;
       }
     }
   }
   grouping ggsn-pgw-apn {
     description "Configure Access Point Names for ggsn and pgw";
     leaf name {
       description "Access Point Name";
       type string {
         junos:posix-pattern "^[.0-9A-Za-z-]{1,100}$";
         junos:pattern-message "Must be a string of 100 or fewer characters and may contain letters, numbers, decimals and dashes.";
       }
     }
     uses apply-advanced;
     leaf maximum-bearers {
       description "Maximum bearers for the APN";
       type union {
         type string {
           pattern "<.*>|$.*";
         }
         type uint32 {
           range "100000 .. 12000000";
         }
       }
     }
     leaf wait-accounting {
       description "Wait for accounting response for session creation";
       type empty;
     }
     leaf block-visitors {
       description "Do not allow visitors connect to the APN";
       type empty;
     }
     leaf allow-network-behind-mobile {
       description "Allow routing behind MS";
       type empty;
     }
     leaf local-policy-profile {
       description "Local profile for the apn";
       type string;
     }
     leaf apn-type {
       description "Specify APN type";
       default "real";
       type enumeration {
         enum "real" {
           description "Real APN";
           junos:must "(\".. address-assignment\")";
           junos:must-message "address-assignment must be specified for a real apn-type";
           junos:must "(\".. mobile-interface\")";
           junos:must-message "mobile-interface must be specified for a real apn-type";
         }
         enum "virtual" {
           description "Virtual APN";
         }
         enum "virtual-pre-authenticate" {
           description "Virtual APN pre authenticate";
         }
       }
     }
     leaf description {
       description "Text description of APN";
       type string {
         junos:posix-pattern "^.{1,80}$";
         junos:pattern-message "Must be 80 characters or less";
       }
     }
     leaf apn-data-type {
       description "Specify APN data type";
       default "ipv4";
       type enumeration {
         enum "ipv4" {
           description "IPv4 Data type";
         }
         enum "ipv6" {
           description "IPv6 Data type";
         }
         enum "ipv4v6" {
           description "IPv4v6 Data type";
         }
       }
     }
     leaf mobile-interface {
       junos:must "(\"interfaces $$\")";
       junos:must-message "referenced mif interface must be defined in the interfaces hierarchy";
       junos:must "(!(\".. apn-type virtual-pre-authenticate\"))";
       junos:must-message "mobile-interface cannot be specified for a virtual-pre-authenticate apn-type";
       junos:must "(!(\".. apn-type virtual\"))";
       junos:must-message "mobile-interface cannot be specified for a virtual apn-type";
       type union {
         type jt:interface-unit;
         type string {
           pattern "<.*>|$.*";
         }
       }
     }
     container address-assignment {
       presence "enable address-assignment";
       junos:must "(!(\".. apn-type virtual-pre-authenticate\"))";
       junos:must-message "address-assignment cannot be specified for a virtual-pre-authenticate apn-type";
       junos:must "(!(\".. apn-type virtual\"))";
       junos:must-message "address-assignment cannot be specified for a virtual apn-type";
       description "Specify address assignment options";
       uses apply-advanced;
       choice address-assignment-choice {
         case case_1 {
           leaf aaa {
             description "AAA assigns addresses";
             junos:must "(\".. .. aaa-profile\")";
             junos:must-message "AAA address assignment method is allowed only if AAA profile is configured under this APN";
             type empty;
           }
         }
         case case_2 {
           container local {
             presence "enable local";
             description "Gateway assigns addresses locally";
             uses apply-advanced;
             leaf aaa-override {
               description "Override local address by address from AAA";
               type empty;
             }
           }
         }
         case case_3 {
           container dhcp-proxy-client {
             presence "enable dhcp-proxy-client";
             description "Gateway assigns address received when acting as DHCP proxy client";
             uses apply-advanced;
             leaf aaa-override {
               description "Override address received from DHCP proxy client mechanism by address from AAA";
               type empty;
             }
           }
         }
       }
       container inet-pool {
         junos:must "((!(\".. dhcp-proxy-client\") || \".. dhcp-proxy-client aaa-override\"))";
         junos:must-message "inet-pool can be configured with dhcp-proxy-client only if aaa-override is configured";
         description "Specify address group name or pool name for IPv4";
         uses apply-advanced;
         leaf group {
           junos:must "(!(\".. pool\"))";
           junos:must-message "only one of pool or group can be specified";
           type string {
             length "1 .. 64";
           }
         }
         leaf pool {
           junos:must "(!(\".. group\"))";
           junos:must-message "only one of pool or group can be specified";
           type string {
             length "1 .. 64";
           }
         }
         leaf-list exclude-pools {
           ordered-by user;
           description "Names of pool to exclude";
           junos:must "(\".. group\")";
           junos:must-message "exclude-pools can be configured only if group is configured";
           type string {
             length "1 .. 64";
           }
         }
       }
       container inet6-pool {
         junos:must "((!(\".. dhcp-proxy-client\") || \".. dhcp-proxy-client aaa-override\"))";
         junos:must-message "inet6-pool can be configured with dhcp-proxy-client only if aaa-override is configured";
         description "Specify address group name or pool name for IPv6";
         uses apply-advanced;
         leaf group {
           junos:must "(!(\".. pool\"))";
           junos:must-message "only one of pool or group can be specified";
           type string {
             length "1 .. 64";
           }
         }
         leaf pool {
           junos:must "(!(\".. group\"))";
           junos:must-message "only one of pool or group can be specified";
           type string {
             length "1 .. 64";
           }
         }
         leaf-list exclude-v6pools {
           ordered-by user;
           description "Names of pool to exclude";
           junos:must "(\".. group\")";
           junos:must-message "exclude-v6pools can be configured only if group is configured";
           type string {
             length "1 .. 64";
           }
         }
       }
       container dhcpv4-proxy-client-profile {
         presence "enable dhcpv4-proxy-client-profile";
         junos:must "(\".. dhcp-proxy-client\")";
         junos:must-message "dhcpv4-proxy-client-profile can only be configured if address-assignment option is dhcp-proxy-client";
         description "DHCPv4 proxy client profile for this APN";
         uses apply-advanced;
         leaf logical-system {
           description "Logical system where this DHCP proxy client profile is defined. If this option is not specified, default logical-system will be used";
           default "default";
           type string {
             junos:posix-pattern "^[a-zA-Z0-9_-]{1,63}$";
             junos:pattern-message "Logical-system name is a string consisting of up to 63 letters, numbers, dashes and underscores";
           }
         }
         leaf routing-instance {
           description "Routing-instance where this DHCP proxy client profile is defined. If this option is not specified, default routing-instance will be used";
           default "default";
           type string {
             junos:posix-pattern "!^((__.*__)|(all)|(.*[ ].*)|(\"\")|(.{129,}))$";
             junos:pattern-message "Must be a non-reserved string of 128 characters or less with no spaces.";
           }
         }
         leaf profile-name {
           description "Name of DHCP proxy client profile";
           type string {
             length "1 .. 63";
           }
         }
         leaf pool-name {
           description "Name of the pool to be sent to DHCP server. It is optional";
           type string {
             length "1 .. 63";
           }
         }
       }
       container dhcpv6-proxy-client-profile {
         presence "enable dhcpv6-proxy-client-profile";
         junos:must "(\".. dhcp-proxy-client\")";
         junos:must-message "dhcpv6-proxy-client-profile can only be configured if address-assignment option is dhcp-proxy-client";
         description "DHCPv6 proxy client profile for this APN";
         uses apply-advanced;
         leaf logical-system {
           description "Logical system where this DHCP proxy client profile is defined. If this option is not specified, default logical-system will be used";
           default "default";
           type string {
             junos:posix-pattern "^[a-zA-Z0-9_-]{1,63}$";
             junos:pattern-message "Logical-system name is a string consisting of up to 63 letters, numbers, dashes and underscores";
           }
         }
         leaf routing-instance {
           description "Routing-instance where this DHCP proxy client profile is defined. If this option is not specified, default routing-instance will be used";
           default "default";
           type string {
             junos:posix-pattern "!^((__.*__)|(all)|(.*[ ].*)|(\"\")|(.{129,}))$";
             junos:pattern-message "Must be a non-reserved string of 128 characters or less with no spaces.";
           }
         }
         leaf profile-name {
           description "Name of DHCP proxy client profile";
           type string {
             length "1 .. 63";
           }
         }
         leaf pool-name {
           description "Name of the pool to be sent to DHCP server. It is optional";
           type string {
             length "1 .. 63";
           }
         }
       }
       container allow-static-ip-address {
         presence "enable allow-static-ip-address";
         description "Allow user equipment provided static address";
         uses apply-advanced;
         leaf no-aaa-verify {
           description "Do not verify the address provided by user equipment through AAA";
           type empty;
         }
       }
     }
     leaf session-timeout {
       description "Session timeout value";
       default "0";
       units "hours";
       type union {
         type string {
           pattern "<.*>|$.*";
         }
         type uint32 {
           range "0 .. 720";
         }
       }
     }
     leaf idle-timeout {
       description "Idle timeout value";
       default "0";
       units "minutes";
       type union {
         type string {
           pattern "<.*>|$.*";
         }
         type uint32 {
           range "0 .. 300";
         }
       }
     }
     leaf idle-timeout-direction {
       description "Specific idle timeout direction";
       type enumeration {
         enum "uplink" {
           description "Enable idle timeout for data traffic flowing in uplink only";
         }
         enum "both" {
           description "Enable idle timeout for data traffic flowing in both directions";
         }
       }
     }
     leaf restriction-value {
       description "Restriction value";
       default "0";
       type union {
         type string {
           pattern "<.*>|$.*";
         }
         type uint32 {
           range "0 .. 4";
         }
       }
     }
     leaf aaa-profile {
       description "Specify AAA profile for Authorization and Accounting";
       junos:must "(\"unified-edge aaa mobile-profiles $$\")";
       junos:must-message "referenced AAA name must be defined";
       type string {
         length "1 .. 32";
       }
     }
     container user-options {
       description "Specify user options";
       uses apply-advanced;
       choice user-name-choice {
         case case_1 {
           leaf user-name {
             description "Default user name for user authentication";
             type string {
               junos:posix-pattern "^[A-Za-z.0-9_@-]{1,63}$";
               junos:pattern-message "Must be in the form user or user@foo.com consisting up to 63 letters, numbers, periods underscores and dashes";
             }
           }
         }
         case case_2 {
           leaf use-msisdn {
             description "Use msisdn for user authentication";
             type empty;
           }
         }
         case case_3 {
           leaf use-imsi {
             description "Use imsi for user authentication";
             type empty;
           }
         }
         case case_4 {
           leaf use-apnname {
             description "Use APN name for user authentication";
             type empty;
           }
         }
       }
       leaf password {
         description "Default user password for user authentication";
         type jt:unreadable;
       }
       leaf override-pco {
         description "Override the username and password received in PCO";
         junos:must "(((\".. user-name\" || (\".. use-imsi\" || (\".. use-msisdn\" || \".. use-apnname\"))) && \".. password\"))";
         junos:must-message "Overriding PCO is only possible if default username and password is set";
         type empty;
       }
     }
     container charging {
       description "Default charging profiles";
       uses apply-advanced;
       leaf default-profile {
         description "Default charging profile for the APN";
         junos:must "(\".. .. .. .. ..  charging charging-profiles $$\")";
         junos:must-message "Charging profile must be defined";
         type string;
       }
       leaf home-profile {
         description "Default home profile for the APN";
         junos:must "(\".. .. .. .. ..  charging charging-profiles $$\")";
         junos:must-message "Charging profile must be defined";
         type string;
       }
       leaf roamer-profile {
         description "Default roamer profile for the APN";
         junos:must "(\".. .. .. .. ..  charging charging-profiles $$\")";
         junos:must-message "Charging profile must be defined";
         type string;
       }
       leaf visitor-profile {
         description "Default visitor profile for the APN";
         junos:must "(\".. .. .. .. ..  charging charging-profiles $$\")";
         junos:must-message "Charging profile must be defined";
         type string;
       }
       leaf-list profile-selection-order {
         ordered-by user;
         description "Default charging profile selection order";
         type enumeration {
           enum "radius" {
             description "Select charging profile sent by RADIUS";
           }
           enum "static" {
             description "Select charging profile locally configured";
           }
           enum "serving" {
             description "Select charging profile sent by SGSN or SGW";
           }
         }
       }
     }
     container dns-server {
       presence "enable dns-server";
       description "Specify DNS servers ";
       uses apply-advanced;
       leaf primary-v4 {
         description "Primary IPv4 DNS server address";
         type jt:ipv4addr;
       }
       leaf secondary-v4 {
         description "Secondary IPv4 DNS server address";
         type jt:ipv4addr;
       }
       leaf primary-v6 {
         description "Primary IPv6 DNS server address";
         type jt:ipv6addr;
       }
       leaf secondary-v6 {
         description "Secondary IPv6 DNS server address";
         type jt:ipv6addr;
       }
     }
     container nbns-server {
       presence "enable nbns-server";
       description "Specify NBNS servers ";
       uses apply-advanced;
       leaf primary-v4 {
         description "Primary IPv4 NBNS server address";
         type jt:ipv4addr;
       }
       leaf secondary-v4 {
         description "Secondary IPv4 NBNS server address";
         type jt:ipv4addr;
       }
     }
     list p-cscf {
       key name;
       ordered-by user;
       description "Specify IPv4 or IPv6 P-CSCF server";
       max-elements 4;
       leaf name {
         description "IPv4 or IPv6 P-CSCF server address";
         type jt:ipaddr;
       }
       uses apply-advanced;
     }
     container selection-mode {
       presence "enable selection-mode";
       description "Specify APN access options";
       uses apply-advanced;
       leaf no-subscribed {
         description "Reject subscribed verified Users";
         type empty;
       }
       leaf from-ms {
         description "Admit MS provided APN, subscription not verified";
         type empty;
       }
       leaf from-sgsn {
         description "Admit Network provided APN, subscription not verified";
         type empty;
       }
     }
     leaf service-selection-profile {
       description "Service selection profile for this APN";
       junos:must "(\".. .. .. .. service-selection-profiles $$\")";
       junos:must-message "Referenced service selection profile must be configured";
       type string {
         length "1 .. 100";
       }
     }
     container network-behind-mobile {
       description "Specify IMSI nbm-address ";
       uses apply-advanced;
       list imsi {
         key name;
         ordered-by user;
         description "Prefixes for a given IMSI";
         leaf name {
           description "IMSI";
           type string {
             length "1 .. 15";
             junos:posix-pattern "^[0-9]*$";
           }
         }
         uses apply-advanced;
         leaf-list prefix-v4 {
           ordered-by user;
           description "IPv4 Prefix Address";
           type jt:ipv4prefix;
         }
         leaf-list prefix-v6 {
           ordered-by user;
           description "IPv6 Prefix Address";
           type jt:ipv6prefix;
         }
       }
     }
     leaf service-mode {
       description "Service mode";
       type enumeration {
         enum "maintenance" {
           description "Maintenance mode";
         }
       }
     }
     container call-rate-statistics {
       presence "enable call-rate-statistics";
       description "Call-rate-statistics options";
       uses apply-advanced;
       leaf interval {
         description "Time interval in minutes";
         default "60";
         units "minutes";
         type union {
           type string {
             pattern "<.*>|$.*";
           }
           type uint32 {
             range "5 .. 120";
           }
         }
       }
       leaf history {
         description "Number of intervals";
         default "1";
         type union {
           type string {
             pattern "<.*>|$.*";
           }
           type uint32 {
             range "1 .. 20";
           }
         }
       }
     }
     leaf pcef-profile {
       description "PCEF profile for the apn";
       junos:must "(\".. .. .. .. .. .. pcef profiles $$\")";
       junos:must-message "Referenced PCEF profile must be defined";
       type string {
         length "1 .. 63";
       }
     }
     container verify-source-address {
       presence "enable verify-source-address";
       description "UE address verification - default is enabled";
       uses apply-advanced;
       leaf disable {
         description "Disable UE address verification";
         type empty;
       }
     }
     container inter-mobile-traffic {
       description "Inter mobile traffic redirect options";
       uses apply-advanced;
       container redirect {
         presence "enable redirect";
         description "Redirect options";
         uses apply-advanced;
         leaf redirect-ip {
           description "Redirect destination address";
           junos:must "(!(\".. .. deny\"))";
           junos:must-message "redirect is not allowed when deny is present";
           type jt:ipv4addr;
         }
         choice instance {
           case case_1 {
             leaf routing-instance {
               description "Routing instance used for redirect";
               junos:must "(\"routing-instances $$\")";
               junos:must-message "referenced routing instance must be defined";
               type union {
                 type string {
                   pattern "default";
                 }
                 type string {
                   junos:posix-pattern "!^((__.*__)|(all)|(.*[ ].*)|(\"\")|(.{129,}))$";
                   junos:pattern-message "Must be a non-reserved string of 128 characters or less with no spaces.";
                 }
               }
             }
           }
         }
       }
       leaf deny {
         description "Do not allow inter mobile traffic";
         junos:must "(!(\".. redirect\"))";
         junos:must-message "deny is not allowed when redirect is present";
         type empty;
       }
     }
   }
   grouping gtpp-peer {
     leaf name {
       description "GTPP CGF name";
       type string;
     }
     uses apply-advanced;
     leaf destination-ipv4-address {
       description "CGF Server IP address";
       type jt:ipv4addr;
     }
     container source-interface {
       description "Source interface from which GTPP packets will be sent";
       leaf interface-name {
         description "Interface name";
         junos:must "(\"interfaces $$\")";
         junos:must-message "Interface must be defined";
         type union {
           type jt:interface-name;
           type string {
             pattern "<.*>|$.*";
           }
         }
       }
       leaf ipv4-address {
         description "Source IPv4 address to be used";
         type jt:ipv4addr;
       }
     }
     leaf destination-port {
       description "Destination port number of the CGF Server";
       type union {
         type string {
           pattern "<.*>|$.*";
         }
         type uint32 {
           range "1 .. 65535";
         }
       }
     }
     leaf transport-protocol {
       description "Default Transport protocol(udp/tcp) used";
       type enumeration {
         enum "udp" {
           description "GTPP over udp";
         }
         enum "tcp" {
           description "GTPP over tcp";
         }
       }
     }
     leaf version {
       description "GTPP version V0|V1|V2";
       type enumeration {
         enum "v0" {
           description "GTPP version V0";
         }
         enum "v1" {
           description "GTPP version V1";
         }
         enum "v2" {
           description "GTPP version V2";
         }
       }
     }
     leaf echo-interval {
       description "GTPP echo-interval in seconds";
       default "60";
       units "seconds";
       type union {
         type string {
           pattern "<.*>|$.*";
         }
         type uint32 {
           range "60 .. 255";
         }
       }
     }
     leaf n3-requests {
       description "Number of retries of GTPP messages upon timeout";
       default "3";
       type union {
         type string {
           pattern "<.*>|$.*";
         }
         type uint16 {
           range "1 .. 5";
         }
       }
     }
     leaf t3-response {
       description "Response timeout value for GTPP request message";
       default "5";
       units "seconds";
       type union {
         type string {
           pattern "<.*>|$.*";
         }
         type uint16 {
           range "1 .. 5";
         }
       }
     }
     leaf header-type {
       description "GTPP protocol header type short|long";
       type enumeration {
         enum "short" {
           description "GTPP short header";
         }
         enum "long" {
           description "GTPP long (20-byte) header";
         }
       }
     }
     leaf pending-queue-size {
       description "Maximum number of DRT messages awaiting an ack";
       default "1024";
       type union {
         type string {
           pattern "<.*>|$.*";
         }
         type uint32 {
           range "1 .. 4096";
         }
       }
     }
     leaf down-detect-time {
       description "Time (in sec) to wait before declaring a CGF as Down";
       default "10";
       units "seconds";
       type union {
         type string {
           pattern "<.*>|$.*";
         }
         type uint32 {
           range "0 .. 255";
         }
       }
     }
     leaf reconnect-time {
       description "Time (in sec) after which connection to the CGF server should be retried";
       default "60";
       units "seconds";
       type union {
         type string {
           pattern "<.*>|$.*";
         }
         type uint32 {
           range "60 .. 255";
         }
       }
     }
     leaf no-path-management {
       description "Disables path management";
       junos:must "(!(\".. echo-interval\"))";
       junos:must-message "no-path-management option can not be used with echo-interval";
       type empty;
     }
   }
   grouping juniper-cdr-profiles {
     description "CDR profiles";
     leaf name {
       description "CDR profile name";
       type string {
         length "1 .. 128";
       }
     }
     uses apply-advanced;
     leaf description {
       description "Text description of this profile";
       type string;
     }
     leaf enable-reduced-partial-cdrs {
       description "Enable reduced partial CDR's";
       type empty;
     }
     leaf report-requested-apn {
       description "Report requested/virtual APN in CDR's";
       type empty;
     }
     container exclude-attributes {
       description "Specify excluded IE options in CDRs";
       uses apply-advanced;
       leaf apn-ni {
         description "Exclude APN network identifier IE in the CDR";
         type empty;
       }
       leaf apn-selection-mode {
         description "Exclude APN selection mode IE in the CDR";
         type empty;
       }
       leaf cc-selection-mode {
         description "Exclude charging characteristic selection mode IE in the CDR";
         type empty;
       }
       leaf dynamic-address {
         description "Exclude dynamic address IE in the CDR";
         type empty;
       }
       leaf pgw-plmn-identifier {
         description "Exclude PGW PLMN identifier IE in the CDR";
         type empty;
       }
       leaf list-of-traffic-volumes {
         description "Exclude list of traffic volumes in the CDR";
         type empty;
       }
       leaf list-of-service-data {
         description "Exclude list of service data in the CDR";
         type empty;
       }
       leaf lrsn {
         description "Exclude local record sequece number IE in the CDR";
         type empty;
       }
       leaf ms-time-zone {
         description "Exclude MS time zone IE in the CDR";
         type empty;
       }
       leaf network-initiation {
         description "Exclude network initiation flag in the CDR";
         type empty;
       }
       leaf node-id {
         description "Exclude node ID IE in the CDR";
         type empty;
       }
       leaf pdn-connection-id {
         description "Exclude PDN connection ID IE in the CDR";
         type empty;
       }
       leaf pdppdn-type {
         description "Exclude PDP or PDN type IE in the CDR";
         type empty;
       }
       leaf rat-type {
         description "Exclude RAT type IE in the CDR";
         type empty;
       }
       leaf record-sequence-number {
         description "Exclude record sequence number IE in the CDR";
         type empty;
       }
       leaf served-imeisv {
         description "Exclude served IMEI IE in the CDR";
         type empty;
       }
       leaf served-msisdn {
         description "Exclude served MSISDN IE in the CDR";
         type empty;
       }
       leaf served-pdppdn-address {
         description "Exclude served PDP context or IP CAN bearer address IE in the CDR";
         type empty;
       }
       leaf serving-node-plmn-identifier {
         description "Exclude serving node PLMN identifier IE in the CDR";
         type empty;
       }
       leaf start-time {
         description "Exclude start time IE in the CDR";
         type empty;
       }
       leaf stop-time {
         description "Exclude stop time IE in the CDR";
         type empty;
       }
       leaf user-location-information {
         description "Exclude user location IE in the CDR";
         type empty;
       }
       leaf sgw-change {
         description "S-GW specific: Exclude S-GW change IE in the CDR";
         type empty;
       }
       leaf pgw-address-used {
         description "S-GW specific: Exclude P-GW address used IE in the CDR";
         type empty;
       }
       leaf ps-furnish-info {
         description "Exclude PS Furnish charging info ";
         type empty;
       }
       leaf served-pdp-address-extension {
         description "Exclude served pdp pdn address extension ";
         type empty;
       }
     }
     leaf node-id {
       description "Default node identifier";
       default "ipaddress-spic";
       type enumeration {
         enum "hostname" {
           description "Use host name";
         }
         enum "hostname-spic" {
           description "Use host name and SPIC id";
         }
         enum "ipaddress-spic" {
           description "Use IP address and SPIC id ";
         }
       }
     }
   }
   grouping juniper-charged-configuraton {
     description "Local persistent storage configuration";
     uses apply-advanced;
     container file-age {
       presence "enable file-age";
       description "Configures file age";
       leaf age {
         description "File age";
         default "120";
         units "minutes";
         type union {
           type string {
             pattern "<.*>|$.*";
           }
           type uint16 {
             range "20 .. 7200";
           }
         }
       }
       leaf disable {
         description "Disable file age trigger";
         type empty;
       }
     }
     container file-size {
       presence "enable file-size";
       description "Configures file size";
       leaf size {
         description "File size";
         default "10";
         units "megabytes";
         type union {
           type string {
             pattern "<.*>|$.*";
           }
           type uint32 {
             range "1 .. 1024";
           }
         }
       }
       leaf disable {
         description "Disable file size trigger";
         type empty;
       }
     }
     leaf cdrs-per-file {
       description "Number of CDRs per file";
       type union {
         type string {
           pattern "<.*>|$.*";
         }
         type uint32 {
           range "5000 .. 1000000";
         }
       }
     }
     leaf user-name {
       description "User authorized to access the files";
       type string {
         length "1 .. 32";
       }
     }
     leaf disable-replication {
       description "Disable replication of CDR log files to standby RE";
       type empty;
     }
     leaf world-readable {
       description "CDR log files can be accessed by all users";
       type empty;
     }
     leaf file-format {
       description "CDR file format";
       default "3gpp";
       type enumeration {
         enum "3gpp" {
           description "File data will be stored in 3gpp 32 297 format";
         }
         enum "raw-asn" {
           description "File data will be stored in raw ASN1 format";
         }
       }
     }
     leaf file-name-private-extension {
       description "File name private extension";
       type string {
         length "1 .. 16";
       }
     }
     leaf file-creation-policy {
       description "File creation policy (shared/unique)";
       default "shared-file";
       type enumeration {
         enum "shared-file" {
           description "File is shared across all SP nodes for a charging group";
         }
         enum "unique-file" {
           description "Unique file is created for charging group per SP node";
         }
       }
     }
     container disk-space-policy {
       presence "enable disk-space-policy";
       description "Policy on what should be done when disk runs out of space";
       uses apply-advanced;
       container water-mark-level1 {
         presence "enable water-mark-level1";
         description "Water mark level1 percentage and notification";
         uses apply-advanced;
         leaf percentage {
           description "The water mark level1 percentage, a value of 0 will disable it";
           default "70";
           type union {
             type string {
               pattern "<.*>|$.*";
             }
             type uint8 {
               range "0 .. 100";
             }
           }
         }
         leaf notification-level {
           description "Notification when water-mark-level is reached";
           default "syslog";
           type enumeration {
             enum "snmp-alarm" {
               description "Generate an snmp alaram";
             }
             enum "syslog" {
               description "Generate syslog";
             }
             enum "both" {
               description "Generate both syslog and snmp-alarm";
             }
           }
         }
       }
       container water-mark-level2 {
         presence "enable water-mark-level2";
         description "Water mark level2 percentage and notification";
         uses apply-advanced;
         leaf percentage {
           description "The water mark level2 percentage, a value of 0 will disable it";
           default "80";
           type union {
             type string {
               pattern "<.*>|$.*";
             }
             type uint8 {
               range "0 .. 100";
             }
           }
         }
         leaf notification-level {
           description "Notification when water-mark-leve2 is reached";
           default "syslog";
           type enumeration {
             enum "snmp-alarm" {
               description "Generate an snmp alaram";
             }
             enum "syslog" {
               description "Generate syslog";
             }
             enum "both" {
               description "Generate both syslog and snmp-alarm";
             }
           }
         }
       }
       container water-mark-level3 {
         presence "enable water-mark-level3";
         description "Water mark level3 percentage and notification";
         uses apply-advanced;
         leaf percentage {
           description "The water mark level3 percentage";
           default "90";
           type union {
             type string {
               pattern "<.*>|$.*";
             }
             type uint8 {
               range "1 .. 100";
             }
           }
         }
         leaf notification-level {
           description "Notification when water-mark-level3 is reached";
           default "syslog";
           type enumeration {
             enum "snmp-alarm" {
               description "Generate an snmp alaram";
             }
             enum "syslog" {
               description "Generate syslog";
             }
             enum "both" {
               description "Generate both syslog and snmp-alarm";
             }
           }
         }
       }
     }
     container traceoptions {
       description "Charged persistent local-storage CDR trace options";
       uses charged_traceoptions_type;
     }
   }
   grouping charged_traceoptions_type {
     description "Trace options for charged persistent local-storage for CDRs";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "critical" {
           description "Match critical error conditions";
         }
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Charged operations to include in debugging trace";
       leaf name {
         type enumeration {
           enum "general" {
             description "Charged miscellaneous operations";
           }
           enum "mirror" {
             description "Charged mirroring operations";
           }
           enum "connection" {
             description "Charged connection establishment with peers";
           }
           enum "file-operations" {
             description "Charged file open/write/close operations";
           }
           enum "journaling" {
             description "Charged file journaling operations";
           }
           enum "all" {
             description "All charged operations";
           }
         }
       }
     }
   }
   grouping juniper-charging-profiles {
     description "Charging profiles";
     leaf name {
       description "Charging profile name";
       type string {
         length "1 .. 128";
       }
     }
     uses apply-advanced;
     leaf description {
       description "Text description of this profile";
       type string {
         junos:posix-pattern "^.{1,255}$";
         junos:pattern-message "Must be a string of 255 characters or less";
       }
     }
     leaf profile-id {
       description "Profile id that is matched against GTP charging characteristic or  	     AAA charging profile number (applicable only in the case of ggsn-pgw)";
       type union {
         type string {
           pattern "<.*>|$.*";
         }
         type uint16 {
           range "1 .. 65534";
         }
       }
     }
     leaf default-service-id {
       description "Default service ID to be used for charging, applicable for GGSN/P-GW only";
       type union {
         type string {
           pattern "<.*>|$.*";
         }
         type uint32 {
           range "0 .. 4294967294";
         }
       }
     }
     leaf default-rating-group {
       description "Default rating group to be used for charging, applicable for GGSN/P-GW only";
       type union {
         type string {
           pattern "<.*>|$.*";
         }
         type uint32 {
           range "0 .. 4294967294";
         }
       }
     }
     leaf default-l7-rating-group {
       description "Default rating group to be used for L7 charging";
       type union {
         type string {
           pattern "<.*>|$.*";
         }
         type uint32 {
           range "1 .. 4294967294";
         }
       }
     }
     container transport-profile {
       description "Transport profile referred by this charging profile";
       uses apply-advanced;
       leaf transport-profile-name {
         description "Provide the transport profile name";
         junos:must "(\".. .. .. .. transport-profiles $$\")";
         junos:must-message "Transport profile has not been defined";
         type string {
           length "1 .. 128";
         }
       }
     }
     container cdr-profile {
       description "Transport profile referred by this charging profile";
       uses apply-advanced;
       leaf cdr-profile-name {
         description "Provide the CDR profile name";
         junos:must "(\".. .. .. .. cdr-profiles $$\")";
         junos:must-message "CDR profile should be defined before it can be used";
         type string {
           length "1 .. 128";
         }
       }
     }
     list trigger-profile {
       key name;
       description "Trigger profile referred by this charging profile";
       leaf name {
         description "Set the trigger profile name";
         junos:must "(\".. .. .. .. trigger-profiles $$\")";
         junos:must-message "Trigger profile should be defined before it can be used";
         type string {
           length "1 .. 128";
         }
       }
       uses apply-advanced;
       leaf-list rating-group {
         ordered-by user;
         description "Input rating-group identifier";
         type union {
           type string {
             pattern "<.*>|$.*";
           }
           type uint32 {
             range "0 .. 4294967294";
           }
         }
       }
     }
     leaf service-mode {
       description "Service mode";
       type enumeration {
         enum "maintenance" {
           description "Maintenance mode";
         }
       }
     }
   }
   grouping juniper-transport-profiles {
     description "Transport profiles";
     leaf name {
       description "Transport profile name";
       type string {
         length "1 .. 128";
       }
     }
     uses apply-advanced;
     leaf description {
       description "Text description of this profile";
       type string;
     }
     container online {
       presence "enable online";
       description "Online charging configuration in transport profile";
       uses apply-advanced;
       leaf tx-timeout {
         description "Timeout value waiting for response";
         default "5";
         type union {
           type string {
             pattern "<.*>|$.*";
           }
           type uint32 {
             range "0 .. 300";
           }
         }
       }
       leaf session-failover-not-supported {
         description "Disable online charging sessions failover to alternate server";
         type empty;
       }
       leaf diameter-profile {
         description "Gy diameter profile name";
         junos:must "(\"unified-edge diameter-profiles gy-profile $$\")";
         junos:must-message "Referenced DCCA profile must be defined";
         type string;
       }
       leaf service-context-id {
         description "Service Context ID . If not configured, default service-context-id is 9.32251@3gpp.org";
         type string {
           length "1 .. 100";
         }
       }
       leaf charging-function-name {
         description "Charging Function Name corresponds to PCRF referred online charging function name ";
         type string {
           length "1 .. 256";
         }
       }
       leaf single-mscc {
         description "Include only one MSCC AVP in CCR message";
         type empty;
       }
       leaf no-mscc-in-ccrt {
         description "Do not include MSCC AVP in CCR-T message";
         type empty;
       }
       leaf no-initiate-session-on-activation {
         description "Do not initiate diameter session on activation";
         type empty;
       }
       leaf quota-request-on-activation {
         description "Request quota only on activation";
         type empty;
       }
       leaf all-rgs-on-termination {
         description "Report all (active/non-active) RGs on termination to OCS";
         type empty;
       }
     }
     container offline {
       presence "enable offline";
       description "Offline charging in the transport profile";
       uses apply-advanced;
       container charging-gateways {
         presence "enable charging-gateways";
         description "Charging gateway group information";
         uses apply-advanced;
         leaf cdr-release {
           description "CDR Release type";
           type enumeration {
             enum "r99" {
               description "CDR release R99";
             }
             enum "r7" {
               description "CDR release R7";
             }
             enum "r8" {
               description "CDR release R8. For S-GW, R8 should only be configured";
             }
             enum "r9" {
               description "CDR release R9. ";
             }
           }
         }
         container peer-order {
           presence "enable peer-order";
           description "Charging servers order";
           uses apply-advanced;
           list peer {
             key name;
             ordered-by user;
             description "Charging server name";
             max-elements 3;
             leaf name {
               description "Name of the Charging Gateway Server";
               junos:must "(\".. .. .. .. .. .. .. gtpp peer $$\")";
               junos:must-message "GTPP Peer should be defined";
               type string {
                 length "1 .. 128";
               }
             }
             uses apply-advanced;
           }
         }
         container persistent-storage-order {
           presence "enable persistent-storage-order";
           description "Offline charging persistent storage order";
           uses apply-advanced;
           leaf local-storage {
             description "Local persistant storage";
             type empty;
           }
         }
         leaf switch-back-time {
           description "Switch back time interval value";
           default "10";
           units "seconds";
           type union {
             type string {
               pattern "<.*>|$.*";
             }
             type uint16 {
               range "0 .. 300";
             }
           }
         }
         leaf cdr-aggregation-limit {
           description "The number of CDRs in one DRT message, default value is 5";
           default "5";
           type union {
             type string {
               pattern "<.*>|$.*";
             }
             type uint16 {
               range "1 .. 16";
             }
           }
         }
         leaf mtu {
           description "The MTU of the DRT message";
           default "1500";
           type union {
             type string {
               pattern "<.*>|$.*";
             }
             type uint16 {
               range "300 .. 8000";
             }
           }
         }
       }
       leaf charging-function-name {
         description "Charging Function Name corresponds to PCRF referred offline charging function name ";
         type string {
           length "1 .. 256";
         }
       }
       leaf container-limit {
         description "The maximum number of container in each CDR";
         default "5";
         type union {
           type string {
             pattern "<.*>|$.*";
           }
           type uint16 {
             range "1 .. 15";
           }
         }
       }
       leaf sgsn-mme-change-limit {
         description "Number of SGSN or SGW changes before CDR is closed";
         default "4";
         junos:must "(!(\"unified-edge gateways ggsn-pgw ${ggsn-pgw} charging trigger-profiles ${trigger-profiles} offline exclude sgsn-sgw-change\"))";
         junos:must-message "Can not specify sgsn-mme-change-limit when sgsn-sgw-change is excluded in trigger profile";
         type union {
           type string {
             pattern "<.*>|$.*";
           }
           type uint16 {
             range "1 .. 5";
           }
         }
       }
     }
     leaf service-mode {
       description "Service mode";
       type enumeration {
         enum "maintenance" {
           description "Maintenance mode";
         }
       }
     }
   }
   grouping juniper-trigger-profiles {
     description "Trigger profiles";
     leaf name {
       description "Trigger profile name";
       type string {
         length "1 .. 128";
       }
     }
     uses apply-advanced;
     leaf description {
       description "Text description of this profile";
       type string;
     }
     list tariff-time-list {
       key name;
       description "Input a list of tariff time changes within a day in 15 minute increments (time in sec will be ignored)";
       max-elements 24;
       leaf name {
         description "Local time (hh:mm) in 15 minute increments";
         type jt:time-of-day;
       }
       uses apply-advanced;
     }
     container offline {
       presence "enable offline";
       description "Offline charging in the trigger profile";
       uses apply-advanced;
       container volume-limit {
         presence "enable volume-limit";
         description "Specify volume limit trigger for container closing";
         leaf vlimit {
           description "Volume limit in bytes";
           type string;
         }
         leaf direction {
           description "Specific volume trigger traffic direction";
           default "both";
           type enumeration {
             enum "uplink" {
               description "Enable volume trigger for data traffic flowing in uplink direction only";
             }
             enum "both" {
               description "Enable volume trigger for data traffic flowing in both directions";
             }
           }
         }
       }
       leaf time-limit {
         description "The time-limit for container closure";
         units "seconds";
         type union {
           type string {
             pattern "<.*>|$.*";
           }
           type uint32 {
             range "600 .. 65535";
           }
         }
       }
       container exclude {
         description "Specify excluded signal triggers";
         uses apply-advanced;
         leaf plmn-change {
           description "No charging data updates on PLMN change";
           type empty;
         }
         leaf qos-change {
           description "No charging data updates on QOS change";
           type empty;
         }
         leaf rat-change {
           description "No charging data updates on RAT change";
           type empty;
         }
         leaf sgsn-sgw-change {
           description "No charging data updates on SGW change";
           type empty;
         }
         leaf user-location-change {
           description "No charging data updates on user location information change";
           type empty;
         }
         leaf ms-timezone-change {
           description "No charging data updates on MS-timezone change";
           type empty;
         }
         leaf dcca-events {
           description "No CDR generation on dcca-events like quota-exhaustion, threshold, etc ";
           type empty;
         }
       }
     }
     leaf charging-method {
       description "Default charging method if not provided by PCEF";
       default "offline";
       type enumeration {
         enum "none" {
           description "Use no charging";
         }
         enum "online" {
           description "Use online charging method";
         }
         enum "offline" {
           description "Use offline charging method";
         }
         enum "both" {
           description "Use online and offline charging method";
         }
       }
     }
     container online {
       presence "enable online";
       uses apply-advanced;
       container reporting-level {
         presence "enable reporting-level";
         description "Default Reporting level for offline and online usage report";
         uses apply-advanced;
         choice rl-value {
           case case_1 {
             leaf rating-group {
               description "Rating group level reporting";
               type empty;
             }
           }
           case case_2 {
             leaf service-identifier {
               description "Service identifier level reporting";
               type empty;
             }
           }
         }
         leaf override {
           description "Override reporting level provided by PCEF";
           type empty;
         }
       }
       leaf measurement-method {
         description "Default measurement method to use if not provided by PCEF";
         default "volume-and-time";
         type enumeration {
           enum "none" {
             description "No measurement method to be used by default";
           }
           enum "volume" {
             description "Use volume based measurement method";
           }
           enum "time" {
             description "Use time based measurement method";
           }
           enum "volume-and-time" {
             description "Use volume and time based measurement method";
           }
         }
       }
       container quota-threshold {
         presence "enable quota-threshold";
         description "Calculate quota threshold value as a percentage of total quota allocated";
         uses apply-advanced;
         leaf threshold {
           units "percent";
           type union {
             type string {
               pattern "<.*>|$.*";
             }
             type uint32 {
               range "5 .. 95";
             }
           }
         }
         leaf override {
           description "Override threshold value provided by OCS";
           type empty;
         }
       }
       leaf quota-validity-time {
         description "Configure quota validity time if one is not provided by OCS";
         units "seconds";
         type union {
           type string {
             pattern "<.*>|$.*";
           }
           type uint32 {
             range "30 .. 864000";
           }
         }
       }
       leaf quota-holding-time {
         description "Configure quota holding time if one is not provided by OCS";
         units "seconds";
         type union {
           type string {
             pattern "<.*>|$.*";
           }
           type uint32 {
             range "10 .. 864000";
           }
         }
       }
       container grant-quota {
         presence "enable grant-quota";
         description "Configure grace-quota to be allocated in case of failure";
         uses apply-advanced;
         leaf cc-time {
           description "Configure time quota";
           units "seconds";
           type union {
             type string {
               pattern "<.*>|$.*";
             }
             type uint32 {
               range "300 .. 4294967294";
             }
           }
         }
         leaf cc-octet-uplink {
           description "Configure input volume quota";
           units "bytes";
           type union {
             type string {
               pattern "<.*>|$.*";
             }
             type uint64 {
               range "1048576 .. 18446744073709551614";
             }
           }
         }
         leaf cc-octet-downlink {
           description "Configure output volume quota";
           units "bytes";
           type union {
             type string {
               pattern "<.*>|$.*";
             }
             type uint64 {
               range "1048576 .. 18446744073709551614";
             }
           }
         }
         leaf cc-octet-both {
           description "Configure volume quota";
           units "bytes";
           type union {
             type string {
               pattern "<.*>|$.*";
             }
             type uint64 {
               range "1048576 .. 18446744073709551614";
             }
           }
         }
       }
       container requested-service-unit {
         presence "enable requested-service-unit";
         description "Determine the requested service unit AVP behavior";
         uses apply-advanced;
         leaf include-quota-holding-time {
           description "Include RSU when reporting reason is quota holding time";
           type empty;
         }
         leaf cc-time {
           description "Configure the time quota requested in CCR";
           units "seconds";
           type union {
             type string {
               pattern "<.*>|$.*";
             }
             type uint32 {
               range "300 .. 4294967294";
             }
           }
         }
         leaf cc-octet-uplink {
           description "Configure input volume quota";
           units "bytes";
           type union {
             type string {
               pattern "<.*>|$.*";
             }
             type uint64 {
               range "1048576 .. 18446744073709551614";
             }
           }
         }
         leaf cc-octet-downlink {
           description "Configure output volume quota";
           units "bytes";
           type union {
             type string {
               pattern "<.*>|$.*";
             }
             type uint64 {
               range "1048576 .. 18446744073709551614";
             }
           }
         }
         leaf cc-octet-both {
           description "Configure volume quota";
           units "bytes";
           type union {
             type string {
               pattern "<.*>|$.*";
             }
             type uint64 {
               range "1048576 .. 18446744073709551614";
             }
           }
         }
       }
       container cc-failure-handling {
         description "Configure MobileNext handling during credit-control failure";
         uses apply-advanced;
         leaf block-traffic-pending-reauth-no-quota {
           description "Block traffic for a RG pending re-auth during quota exhaustion";
           type empty;
         }
         leaf override {
           description "Overrides charging failure-method provided by OCS";
           type empty;
         }
         container result-code-based-action {
           description "Perform action based on diamter result-code AVP";
           uses apply-advanced;
           container authorization-rejected {
             description "Diameter-authorization-rejected - default Terminate";
             uses apply-advanced;
             choice cc-action {
               case case_1 {
                 container blacklist {
                   presence "enable blacklist";
                   description "Put rating-group in blacklist";
                   leaf retry-timer {
                     description "Time limit to retry with OCS once RG is in blacklist";
                     units "seconds";
                     type union {
                       type string {
                         pattern "<.*>|$.*";
                       }
                       type uint32 {
                         range "120 .. 3866040";
                       }
                     }
                   }
                 }
               }
             }
           }
           container credit-control-not-applicable {
             description "Diameter-credit-control-not-applicable - default disable online charging";
             uses apply-advanced;
             choice cc-action {
               case case_1 {
                 container convert-to-offline {
                   presence "enable convert-to-offline";
                   description "Convert to offline in case of failure";
                   uses apply-advanced;
                   leaf grant-grace-quota {
                     description "Use offline charging till grace quota period";
                     junos:must "(\".. .. .. .. .. grant-quota\")";
                     junos:must-message "Must configure grant-quota under online charging";
                     type empty;
                   }
                 }
               }
             }
           }
           container end-user-service-denied {
             description "Diameter-end-user-service-denied - default terminate";
             uses apply-advanced;
             choice cc-action {
               case case_1 {
                 leaf disable-online-charging {
                   description "Disable online charging. Continue to use offline charging if enabled otherwise no charging is applied";
                   type empty;
                 }
               }
               case case_2 {
                 container convert-to-offline {
                   presence "enable convert-to-offline";
                   description "Convert to offline in case of failure";
                   uses apply-advanced;
                   leaf grant-grace-quota {
                     description "Use offline charging till grace quota period";
                     junos:must "(\".. .. .. .. .. grant-quota\")";
                     junos:must-message "Must configure grant-quota under online charging";
                     type empty;
                   }
                 }
               }
             }
           }
           container user-unknown {
             description "User-unknown - default terminate";
             uses apply-advanced;
             choice cc-action {
               case case_1 {
                 leaf disable-online-charging {
                   description "Disable online charging. Continue to use offline charging if enabled otherwise no charging is applied";
                   type empty;
                 }
               }
               case case_2 {
                 container convert-to-offline {
                   presence "enable convert-to-offline";
                   description "Convert to offline in case of failure";
                   uses apply-advanced;
                   leaf grant-grace-quota {
                     description "Use offline charging till grace quota period";
                     junos:must "(\".. .. .. .. .. grant-quota\")";
                     junos:must-message "Must configure grant-quota under online charging";
                     type empty;
                   }
                 }
               }
             }
           }
           container credit-limit-reached {
             description "Diameter-credit-limit-reached - default terminate";
             uses apply-advanced;
             choice cc-action {
               case case_1 {
                 container blacklist {
                   presence "enable blacklist";
                   description "Put rating-group in blacklist";
                   leaf retry-timer {
                     description "Time limit to retry with OCS once RG is in blacklist";
                     units "seconds";
                     type union {
                       type string {
                         pattern "<.*>|$.*";
                       }
                       type uint32 {
                         range "120 .. 3866040";
                       }
                     }
                   }
                 }
               }
             }
           }
         }
         container initial-request {
           presence "enable initial-request";
           description "Failure action for initial cc request - default terminate";
           uses apply-advanced;
           choice cc-action {
             case case_1 {
               leaf grant-grace-quota {
                 description "Grant grace quota and continue online session";
                 junos:must "(\".. .. .. grant-quota\")";
                 junos:must-message "Must configure grant-quota under online charging";
                 type empty;
               }
             }
             case case_2 {
               leaf disable-online-charging {
                 description "Disable online charging. Continue to use offline charging if enabled otherwise no charging is applied";
                 type empty;
               }
             }
             case case_3 {
               container convert-to-offline {
                 presence "enable convert-to-offline";
                 description "Convert to offline in case of failure";
                 uses apply-advanced;
                 leaf grant-grace-quota {
                   description "Use offline charging till grace quota period";
                   junos:must "(\".. .. .. .. grant-quota\")";
                   junos:must-message "Must configure grant-quota under online charging";
                   type empty;
                 }
               }
             }
           }
         }
         container update-request {
           presence "enable update-request";
           description "Failure action for  update cc request - default terminate";
           uses apply-advanced;
           choice cc-action {
             case case_1 {
               leaf grant-grace-quota {
                 description "Grant grace quota and continue online session";
                 junos:must "(\".. .. .. grant-quota\")";
                 junos:must-message "Must configure grant-quota under online charging";
                 type empty;
               }
             }
             case case_2 {
               leaf disable-online-charging {
                 description "Disable online charging. Continue to use offline charging if enabled otherwise no charging is applied";
                 type empty;
               }
             }
             case case_3 {
               container convert-to-offline {
                 presence "enable convert-to-offline";
                 description "Convert to offline in case of failure";
                 uses apply-advanced;
                 leaf grant-grace-quota {
                   description "Use offline charging till grace quota period";
                   junos:must "(\".. .. .. .. grant-quota\")";
                   junos:must-message "Must configure grant-quota under online charging";
                   type empty;
                 }
               }
             }
           }
         }
       }
     }
   }
   grouping juniper-unified-edge-cos-options {
     uses apply-advanced;
     list classifier-profiles {
       key name;
       ordered-by user;
       description "Classifier tables for mobile subscribers (UMTS/EPS)";
       max-elements 8001;
       leaf name {
         description "Classification table name";
         type string {
           junos:posix-pattern "^.{1,64}$";
           junos:pattern-message "Must be string of 64 characters or less";
         }
       }
       uses apply-advanced;
       leaf description {
         description "Text description of classifier profile";
         type string;
       }
       list qos-class-identifier {
         key name;
         ordered-by user;
         description "QCI mapping to forwarding class and loss priority";
         leaf name {
           description "Qci value";
           type union {
             type string {
               pattern "<.*>|$.*";
             }
             type uint32 {
               range "1 .. 9";
             }
           }
         }
         leaf forwarding-class {
           description "Forwarding class";
           type string {
             junos:posix-pattern "^.{1,64}$";
             junos:pattern-message "Must be string of 64 characters or less";
           }
         }
         leaf loss-priority {
           description "Loss priority value";
           type enumeration {
             enum "low" {
               description "Loss priority low";
             }
             enum "high" {
               description "Loss priority high";
             }
           }
         }
       }
     }
     list gbr-bandwidth-pools {
       key name;
       ordered-by user;
       description "GBR bandwith pools configuration";
       max-elements 8001;
       leaf name {
         description "GBR Bandwidth pool name";
         type string {
           junos:posix-pattern "^.{1,64}$";
           junos:pattern-message "Must be string of 64 characters or less";
         }
       }
       uses apply-advanced;
       leaf maximum-bandwidth {
         description "Bandwidth for pool";
         units "mega-bits per second";
         type union {
           type string {
             pattern "<.*>|$.*";
           }
           type uint32 {
             range "50000 .. 500000";
           }
         }
       }
       leaf downgrade-gtp-v1-gbr-bearers {
         description "Downgrade GTPv1 GBR bearer traffic class to background traffic class";
         type empty;
       }
     }
     list resource-threshold-profiles {
       key name;
       ordered-by user;
       description "Resource threshold profiles";
       max-elements 8001;
       leaf name {
         description "Resource threshold profile name";
         type string {
           junos:posix-pattern "^.{1,64}$";
           junos:pattern-message "Must be string of 64 characters or less";
         }
       }
       uses apply-advanced;
       leaf description {
         description "Text description of resource threshold profile";
         type string;
       }
       container bearers-load {
         description "Number of bearers load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
       container memory {
         description "Memory load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
       container cpu {
         description "CPU load configurations";
         uses apply-advanced;
         container low {
           description "Low threshold configuration";
           uses apply-advanced;
           leaf percentage {
             description "Low threshold";
             units "Percentage";
             type union {
               type string {
                 pattern "<.*>|$.*";
               }
               type uint32 {
                 range "1 .. 100";
               }
             }
           }
           leaf priority-level {
             description "Priority level - default 10";
             default "10";
             type union {
               type string {
                 pattern "<.*>|$.*";
               }
               type uint32 {
                 range "1 .. 15";
               }
             }
           }
         }
         container high {
           description "High threshold configuration";
           uses apply-advanced;
           leaf percentage {
             description "High threshold";
             units "Percentage";
             type union {
               type string {
                 pattern "<.*>|$.*";
               }
               type uint32 {
                 range "1 .. 100";
               }
             }
           }
           leaf priority-level {
             description "Priority level - default 5";
             default "5";
             type union {
               type string {
                 pattern "<.*>|$.*";
               }
               type uint32 {
                 range "1 .. 15";
               }
             }
           }
         }
       }
     }
     list cos-policy-profiles {
       key name;
       ordered-by user;
       description "QoS policy profile";
       max-elements 8001;
       leaf name {
         description "QoS policy profile name";
         type string {
           junos:posix-pattern "^.{1,64}$";
           junos:pattern-message "Must be string of 64 characters or less";
         }
       }
       uses apply-advanced;
       leaf description {
         description "Text description of cos policy";
         type string;
       }
       container default-bearer-qci {
         description "Default bearer qci value";
         leaf qci-value {
           description "Default bearer qci value";
           type union {
             type string {
               pattern "<.*>|$.*";
             }
             type uint8 {
               range "5 .. 9";
             }
           }
         }
         leaf upgrade {
           description "Override qci value";
           type empty;
         }
         leaf reject {
           description "Reject calls with numerially lower qci";
           type empty;
         }
       }
       container allocation-retention-priority {
         description "ARP local policy";
         leaf priority-value {
           description "ARP policy configuration";
           type union {
             type string {
               pattern "<.*>|$.*";
             }
             type uint8 {
               range "1 .. 15";
             }
           }
         }
         leaf reject {
           description "Reject calls with higher priority value";
           type empty;
         }
       }
       container aggregated-qos-control {
         description "Aggregated qos control policy";
         uses apply-advanced;
         container maximum-bit-rate-uplink {
           description "Maximum bit rate uplink";
           leaf mbr-uplink {
             units "kbps";
             type union {
               type string {
                 pattern "<.*>|$.*";
               }
               type uint32 {
                 range "1 .. 1000000";
               }
             }
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 1000000";
               }
             }
           }
           leaf upgrade {
             description "Override maximum-bit-rate downlink value";
             type empty;
           }
           leaf reject {
             description "Reject calls with higher downlink maximum-bit-rate";
             type empty;
           }
         }
       }
       container pdp-qos-control {
         description "PDP qos control";
         uses apply-advanced;
         container maximum-bit-rate-uplink {
           description "Maximum bit rate uplink";
           leaf mbr-uplink {
             units "kbps";
             type union {
               type string {
                 pattern "<.*>|$.*";
               }
               type uint32 {
                 range "1 .. 10480000";
               }
             }
           }
           leaf upgrade {
             description "Override maximum-bit-rate uplink value";
             type empty;
           }
           leaf reject {
             description "Reject calls with higher uplink maximum-bit-rate";
             type empty;
           }
         }
         container maximum-bit-rate-downlink {
           description "Maximum bit rate downlink";
           leaf mbr-downlink {
             units "kbps";
             type union {
               type string {
                 pattern "<.*>|$.*";
               }
               type uint32 {
                 range "1 .. 10480000";
               }
             }
           }
           leaf upgrade {
             description "Override maximum-bit-rate downlink value";
             type empty;
           }
           leaf reject {
             description "Reject calls with higher downlink maximum-bit-rate";
             type empty;
           }
         }
         container guaranteed-bit-rate-uplink {
           description "Guaranteed bit rate uplink";
           leaf gbr-uplink {
             units "kbps";
             type union {
               type string {
                 pattern "<.*>|$.*";
               }
               type uint32 {
                 range "1 .. 10480000";
               }
             }
           }
           leaf upgrade {
             description "Override guaranteed-bit-rate uplink value";
             type empty;
           }
           leaf reject {
             description "Reject calls with higher uplink guaranteed-bit-rate";
             type empty;
           }
         }
         container guaranteed-bit-rate-downlink {
           description "Guaranteed bit rate downlink";
           leaf gbr-downlink {
             units "kbps";
             type union {
               type string {
                 pattern "<.*>|$.*";
               }
               type uint32 {
                 range "1 .. 10480000";
               }
             }
           }
           leaf upgrade {
             description "Override guaranteed-bit-rate downlink value";
             type empty;
           }
           leaf reject {
             description "Reject calls with higher downlink guaranteed-bit-rate";
             type empty;
           }
         }
         list qci {
           key name;
           ordered-by user;
           description "PDP qos control per qci";
           leaf name {
             type union {
               type string {
                 pattern "<.*>|$.*";
               }
               type uint8 {
                 range "5 .. 9";
               }
             }
           }
           uses apply-advanced;
           container maximum-bit-rate-uplink {
             description "Maximum bit rate uplink";
             leaf mbr-uplink {
               units "kbps";
               type union {
                 type string {
                   pattern "<.*>|$.*";
                 }
                 type uint32 {
                   range "1 .. 10480000";
                 }
               }
             }
             leaf upgrade {
               description "Override maximum-bit-rate uplink value";
               type empty;
             }
             leaf reject {
               description "Reject calls with higher uplink maximum-bit-rate";
               type empty;
             }
           }
           container maximum-bit-rate-downlink {
             description "Maximum bit rate downlink";
             leaf mbr-downlink {
               units "kbps";
               type union {
                 type string {
                   pattern "<.*>|$.*";
                 }
                 type uint32 {
                   range "1 .. 10480000";
                 }
               }
             }
             leaf upgrade {
               description "Override maximum-bit-rate downlink value";
               type empty;
             }
             leaf reject {
               description "Reject calls with higher downlink maximum-bit-rate";
               type empty;
             }
           }
         }
       }
       container policer-action {
         description "Policer actions";
         uses apply-advanced;
         container non-gbr-bearer {
           description "Policer actions for non gbr bearers";
           uses apply-advanced;
           leaf violate-action {
             description "PDP policer violate action";
             type enumeration {
               enum "set-loss-priority-high" {
                 description "Violate action set loss priority high";
               }
               enum "transmit" {
                 description "Violate action transmit";
               }
             }
           }
         }
         container gbr-bearer {
           description "Policer actions for gbr bearers";
           uses apply-advanced;
           leaf exceed-action {
             description "PDP policer exceed action";
             type enumeration {
               enum "drop" {
                 description "Exceed action drop";
               }
               enum "transmit" {
                 description "Exceed action transmit";
               }
             }
           }
           leaf violate-action {
             description "PDP policer violate action";
             type enumeration {
               enum "set-loss-priority-high" {
                 description "Violate action set loss priority high";
               }
               enum "transmit" {
                 description "Violate action transmit";
               }
             }
           }
         }
       }
     }
   }
   grouping macro-data-type {
     leaf name {
       description "Keyword part of the keyword-value pair";
       type string;
     }
     leaf value {
       description "Value part of the keyword-value pair";
       type string;
     }
   }
   grouping mobile-diameter-profiles {
     uses apply-advanced;
     list gy-profile {
       key name;
       ordered-by user;
       description "Diameter Gy application profile configuration";
       uses mobile-diameter-profile-type-gy;
     }
     list gx-profile {
       key name;
       ordered-by user;
       description "Diameter Gx application profile configuration";
       uses mobile-diameter-profile-type-gx;
     }
   }
   grouping mobile-diameter-profile-type-gx {
     leaf name {
       description "Diameter profile name";
       type string {
         length "1 .. 63";
       }
     }
     uses apply-advanced;
     list targets {
       key name;
       ordered-by user;
       description "Mobile diameter target configurations";
       uses mobile-diameter-target;
     }
     leaf request-timeout {
       description "Profile request timeout";
       units "seconds";
       type union {
         type string {
           pattern "<.*>|$.*";
         }
         type uint32 {
           range "0 .. 65535";
         }
       }
     }
     container attributes {
       description "Diameter AVP attributes for Gx application";
       uses mobile-diameter-gx-profile-attr-type;
     }
   }
   grouping mobile-diameter-gx-profile-attr-type {
     uses apply-advanced;
     container include {
       description "Specify AVP options to be included";
       uses apply-advanced;
       leaf gx-capability-list {
         description "Include Gx Capability list AVP";
         type union {
           type uint32;
           type string {
             pattern "<.*>|$.*";
           }
         }
       }
       leaf rule-suggestion {
         description "Include Rule-suggestion AVP";
         type string {
           length "1 .. 63";
         }
       }
       leaf rai {
         description "Include RAI AVP";
         type empty;
       }
       leaf qos-negotiation {
         description "Include QoS Negotiation AVP";
         type empty;
       }
       leaf qos-upgrade {
         description "Include QoS Upgrade AVP";
         type empty;
       }
     }
     container exclude {
       description "Specify AVP options to be excluded";
       uses apply-advanced;
       leaf packet-filter-information {
         description "Exclude Packet Filter Information AVP";
         type empty;
       }
       leaf packet-filter-operation {
         description "Exclude Packet Filter Operation AVP";
         type empty;
       }
       leaf rat-type {
         description "Exclude Rat-Type AVP";
         type empty;
       }
       leaf default-eps-bearer-qos {
         description "Exclude Default EPS Bearer QOS AVP";
         type empty;
       }
       leaf an-gw-address {
         description "Exclude AN-GW-Address AVP";
         type empty;
       }
       leaf network-request-support {
         description "Exclude Network Request Support AVP";
         type empty;
       }
       leaf event-trigger {
         description "Exclude Event Trigger AVP";
         type empty;
       }
       leaf threegpp-rat-type {
         description "Exclude 3GPP-RAT-Type AVP";
         type empty;
       }
       leaf offline {
         description "Exclude Offline AVP";
         type empty;
       }
       leaf qos-negotiation {
         description "Exclude QoS Negotiation AVP";
         type empty;
       }
       leaf qos-upgrade {
         description "Exclude QoS Upgrade AVP";
         type empty;
       }
     }
   }
   grouping mobile-diameter-profile-type-gy {
     leaf name {
       description "Diameter profile name";
       type string {
         length "1 .. 63";
       }
     }
     uses apply-advanced;
     list targets {
       key name;
       ordered-by user;
       description "Mobile diameter target configurations";
       uses mobile-diameter-target;
     }
     leaf request-timeout {
       description "Profile request timeout";
       units "seconds";
       type union {
         type string {
           pattern "<.*>|$.*";
         }
         type uint32 {
           range "0 .. 65535";
         }
       }
     }
     container attributes {
       description "Diameter AVP attributes for Gy application";
       uses mobile-diameter-gy-profile-attr-type;
     }
   }
   grouping mobile-diameter-gy-profile-attr-type {
     uses apply-advanced;
     container include {
       description "Specify AVP options to be included";
       uses apply-advanced;
       leaf cumulative-used-service-unit {
         description "Include cumulative-used-service-unit AVP";
         type empty;
       }
       leaf credit-instance-id {
         description "Include credit-instance-id AVP";
         type empty;
       }
       leaf service-start-timestamp {
         description "Include service-start-timestamp AVP";
         type empty;
       }
       leaf mscc-qos-information {
         description "Include mscc-qos-information AVP";
         type empty;
       }
       leaf framed-ip-address {
         description "Include framed ip address AVP";
         type empty;
       }
       leaf framed-ipv6-prefix {
         description "Include framed IPV6 Prefix AVP";
         type empty;
       }
       leaf gprs-negotiated-qos {
         description "Include GPRS negotiated QOS AVP";
         type empty;
       }
     }
     container exclude {
       description "Specify AVP options to be excluded";
       uses apply-advanced;
       leaf ps-information {
         description "Exclude PS Information AVP. If excluded, all the 3GPP AVPs will be sent at command level ";
         type empty;
       }
       leaf username {
         description "Exclude Username AVP";
         type empty;
       }
       leaf user-equipment-info {
         description "Exclude user equipment info AVP";
         type empty;
       }
       leaf all-3gpp-avps {
         description "Exclude all 3GPP AVPs";
         type empty;
       }
       leaf qos-information {
         description "Exclude QOS information AVP";
         type empty;
       }
       leaf pdn-connection-id {
         description "Exclude PDN connection id AVP";
         type empty;
       }
       leaf dynamic-address-flag {
         description "Exclude dynamic address flag AVP";
         type empty;
       }
       leaf serving-node-type {
         description "Exclude serving node type AVP";
         type empty;
       }
       leaf cc-selection-mode {
         description "Exclude charging characteristics selection mode AVP";
         type empty;
       }
       leaf start-time {
         description "Exclude start time AVP";
         type empty;
       }
       leaf stop-time {
         description "Exclude stop time AVP";
         type empty;
       }
       leaf user-location-information {
         description "Exclude user location information AVP";
         type empty;
       }
     }
   }
   grouping mobile-diameter-target {
     description "Diameter target configuration";
     leaf name {
       description "Diameter target name";
       type string {
         length "1 .. 31";
       }
     }
     uses apply-advanced;
     leaf destination-realm {
       description "Destination realm associated with this target";
       type string {
         length "1 .. 255";
       }
     }
     leaf destination-host {
       description "Destination host associated with this target";
       type string {
         length "1 .. 255";
       }
     }
     leaf priority {
       description "Target priority";
       type union {
         type string {
           pattern "<.*>|$.*";
         }
         type uint32 {
           range "1 .. 65535";
         }
       }
     }
     leaf network-element {
       description "Specify the diameter network element for this target";
       junos:must "(\"access diameter network-element $$\")";
       junos:must-message "Referenced DNE must be defined";
       type string {
         length "1 .. 31";
       }
     }
   }
   grouping mobile-gateway-config-gtp {
     description "GTP configuration";
     uses apply-advanced;
     leaf peer-history {
       description "Maximum number of peer stats stored in history";
       default "100";
       type union {
         type string {
           pattern "<.*>|$.*";
         }
         type uint16 {
           range "1 .. 1000";
         }
       }
     }
     container interface {
       description "Interface name used for all 3GPP interface";
       leaf intf-name {
         description "Interface name";
         junos:must "(\"interfaces $$-IFL family inet address\")";
         junos:must-message "Family inet address should be configured on this interface";
         type union {
           type jt:interface-name;
           type string {
             pattern "<.*>|$.*";
           }
         }
       }
       leaf v4-address {
         description "IPv4 address if multiple addresses configured on interface";
         type jt:ipv4addr;
       }
     }
     leaf echo-interval {
       description "Echo Request interval value for path management";
       units "seconds";
       type union {
         type string {
           pattern "<.*>|$.*";
         }
         type uint16 {
           range "60 .. 65535";
         }
       }
     }
     leaf path-management {
       description "Enable/disable path management";
       type enumeration {
         enum "enable" {
           description "Enable parameter";
         }
         enum "disable" {
           description "Disable parameter";
         }
       }
     }
     leaf echo-n3-requests {
       description "Number of retries of GTP echo messages upon timeout";
       type union {
         type string {
           pattern "<.*>|$.*";
         }
         type uint16 {
           range "1 .. 8";
         }
       }
     }
     leaf echo-t3-response {
       description "Response timeout value for GTP echo request message";
       units "seconds";
       type union {
         type string {
           pattern "<.*>|$.*";
         }
         type uint16 {
           range "1 .. 30";
         }
       }
     }
     leaf path-failure {
       description "Enable/disable path failure";
       type enumeration {
         enum "enable" {
           description "Enable parameter";
         }
         enum "disable" {
           description "Disable parameter";
         }
       }
     }
     leaf number-of-msgs-for-response-time {
       description "Number of msgs used for calculating peer response times";
       default "10000";
       type union {
         type string {
           pattern "<.*>|$.*";
         }
         type uint16 {
           range "1 .. 65535";
         }
       }
     }
     container control {
       description "Configure 3GPP GTP control plane options";
       uses apply-advanced;
       container interface {
         description "Interface name used for all 3GPP control interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       leaf forwarding-class {
         description "Classification of host traffic to forwarding engine";
         type string {
           junos:posix-pattern "^.{1,64}$";
           junos:pattern-message "Must be string of 64 characters or less";
         }
       }
       leaf n3-requests {
         description "Number of retries of GTP messages upon timeout";
         type union {
           type string {
             pattern "<.*>|$.*";
           }
           type uint16 {
             range "1 .. 5";
           }
         }
       }
       leaf t3-response {
         description "Response timeout value for GTP request message";
         units "seconds";
         type union {
           type string {
             pattern "<.*>|$.*";
           }
           type uint16 {
             range "1 .. 30";
           }
         }
       }
       leaf dscp-code-point {
         description "Static DSCP code point of egress host traffic";
         type union {
           type string {
             pattern "<.*>|$.*";
           }
           type uint8 {
             range "0 .. 63";
           }
         }
       }
       leaf no-response-cache {
         description "Disable GTP response cache";
         type empty;
       }
       leaf response-cache-timeout {
         description "GTP response cache timeout interval";
         default "15";
         units "seconds";
         type union {
           type string {
             pattern "<.*>|$.*";
           }
           type uint8 {
             range "5 .. 20";
           }
         }
       }
       leaf no-piggyback-support {
         description "Disable GTPv2 piggyback support";
         type empty;
       }
     }
     container data {
       description "Configure 3GPP GTP data plane options";
       uses apply-advanced;
       container interface {
         description "Interface name used for all 3GPP data interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf error-indication-interval {
         description "Error indication transmit interval per bearer ";
         default "2";
         units "seconds";
         type union {
           type string {
             pattern "<.*>|$.*";
           }
           type uint16 {
             range "1 .. 20";
           }
         }
       }
     }
     container gn {
       description "Configure 3GPP Gn interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
       }
       container data {
         description "Configure 3GPP data plane options";
         uses apply-advanced;
         container interface {
           description "Interface name used for data interface";
           leaf echo-interval {
             description "Echo Request interval value for path management";
             units "seconds";
             type union {
               type string {
                 pattern "<.*>|$.*";
               }
               type uint16 {
                 range "60 .. 65535";
               }
             }
           }
           leaf path-management {
             description "Enable/disable path management";
             type enumeration {
               enum "enable" {
                 description "Enable parameter";
               }
               enum "disable" {
                 description "Disable parameter";
               }
             }
           }
           leaf echo-n3-requests {
             description "Number of retries of GTP echo messages upon timeout";
             type union {
               type string {
                 pattern "<.*>|$.*";
               }
               type uint16 {
                 range "1 .. 8";
               }
             }
           }
           leaf echo-t3-response {
             description "Response timeout value for GTP echo request message";
             units "seconds";
             type union {
               type string {
                 pattern "<.*>|$.*";
               }
               type uint16 {
                 range "1 .. 30";
               }
             }
           }
           leaf path-failure {
             description "Enable/disable path failure";
             type enumeration {
               enum "enable" {
                 description "Enable parameter";
               }
               enum "disable" {
                 description "Disable parameter";
               }
             }
           }
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
       }
     }
     container gp {
       description "Configure 3GPP Gp interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
       }
       container data {
         description "Configure 3GPP data plane options";
         uses apply-advanced;
         container interface {
           description "Interface name used for data interface";
           leaf echo-interval {
             description "Echo Request interval value for path management";
             units "seconds";
             type union {
               type string {
                 pattern "<.*>|$.*";
               }
               type uint16 {
                 range "60 .. 65535";
               }
             }
           }
           leaf path-management {
             description "Enable/disable path management";
             type enumeration {
               enum "enable" {
                 description "Enable parameter";
               }
               enum "disable" {
                 description "Disable parameter";
               }
             }
           }
           leaf echo-n3-requests {
             description "Number of retries of GTP echo messages upon timeout";
             type union {
               type string {
                 pattern "<.*>|$.*";
               }
               type uint16 {
                 range "1 .. 8";
               }
             }
           }
           leaf echo-t3-response {
             description "Response timeout value for GTP echo request message";
             units "seconds";
             type union {
               type string {
                 pattern "<.*>|$.*";
               }
               type uint16 {
                 range "1 .. 30";
               }
             }
           }
           leaf path-failure {
             description "Enable/disable path failure";
             type enumeration {
               enum "enable" {
                 description "Enable parameter";
               }
               enum "disable" {
                 description "Disable parameter";
               }
             }
           }
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
       }
     }
     container s5 {
       description "Configure 3GPP S5 interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
         leaf support-16-bit-sequence {
           description "Enable 16 bit sequence number support";
           type empty;
         }
       }
       container data {
         description "Configure 3GPP data plane options";
         uses apply-advanced;
         container interface {
           description "Interface name used for data interface";
           leaf echo-interval {
             description "Echo Request interval value for path management";
             units "seconds";
             type union {
               type string {
                 pattern "<.*>|$.*";
               }
               type uint16 {
                 range "60 .. 65535";
               }
             }
           }
           leaf path-management {
             description "Enable/disable path management";
             type enumeration {
               enum "enable" {
                 description "Enable parameter";
               }
               enum "disable" {
                 description "Disable parameter";
               }
             }
           }
           leaf echo-n3-requests {
             description "Number of retries of GTP echo messages upon timeout";
             type union {
               type string {
                 pattern "<.*>|$.*";
               }
               type uint16 {
                 range "1 .. 8";
               }
             }
           }
           leaf echo-t3-response {
             description "Response timeout value for GTP echo request message";
             units "seconds";
             type union {
               type string {
                 pattern "<.*>|$.*";
               }
               type uint16 {
                 range "1 .. 30";
               }
             }
           }
           leaf path-failure {
             description "Enable/disable path failure";
             type enumeration {
               enum "enable" {
                 description "Enable parameter";
               }
               enum "disable" {
                 description "Disable parameter";
               }
             }
           }
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
       }
     }
     container s8 {
       description "Configure 3GPP S8 interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
         leaf support-16-bit-sequence {
           description "Enable 16 bit sequence number support";
           type empty;
         }
       }
       container data {
         description "Configure 3GPP data plane options";
         uses apply-advanced;
         container interface {
           description "Interface name used for data interface";
           leaf echo-interval {
             description "Echo Request interval value for path management";
             units "seconds";
             type union {
               type string {
                 pattern "<.*>|$.*";
               }
               type uint16 {
                 range "60 .. 65535";
               }
             }
           }
           leaf path-management {
             description "Enable/disable path management";
             type enumeration {
               enum "enable" {
                 description "Enable parameter";
               }
               enum "disable" {
                 description "Disable parameter";
               }
             }
           }
           leaf echo-n3-requests {
             description "Number of retries of GTP echo messages upon timeout";
             type union {
               type string {
                 pattern "<.*>|$.*";
               }
               type uint16 {
                 range "1 .. 8";
               }
             }
           }
           leaf echo-t3-response {
             description "Response timeout value for GTP echo request message";
             units "seconds";
             type union {
               type string {
                 pattern "<.*>|$.*";
               }
               type uint16 {
                 range "1 .. 30";
               }
             }
           }
           leaf path-failure {
             description "Enable/disable path failure";
             type enumeration {
               enum "enable" {
                 description "Enable parameter";
               }
               enum "disable" {
                 description "Disable parameter";
               }
             }
           }
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
       }
     }
     list peer-group {
       key name;
       ordered-by user;
       description "3GPP GTP peer group configuration";
       leaf name {
         description "GTP peer group name";
         type string {
           length "1 .. 64";
         }
       }
       uses apply-advanced;
       leaf routing-instance {
         description "Routing instance of peer group";
         type string;
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "3GPP GTP peer group control plane options";
         uses apply-advanced;
         leaf support-16-bit-sequence {
           description "Enable 16 bit sequence number support";
           type empty;
         }
         leaf no-piggyback-support {
           description "Disable GTPv2 piggyback support";
           type empty;
         }
       }
       container gn {
         description "3GPP GTP peer group Gn interface options";
         uses apply-advanced;
       }
       container gp {
         description "3GPP GTP peer group Gp interface options";
         uses apply-advanced;
       }
       list peer {
         key name;
         ordered-by user;
         description "Peer IP address configuration";
         leaf name {
           description "Enter IP addr with prefix";
           type jt:ipprefix-mandatory;
         }
       }
     }
     container traceoptions {
       description "Configure trace options";
       uses gtp-traceoptions;
     }
   }
   grouping gtp-traceoptions {
     description "Configure trace options";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "error" {
             description "Trace internal and external errors";
           }
           enum "warning" {
             description "Trace warnings";
           }
           enum "debug" {
             description "Trace debug information";
           }
           enum "encode" {
             description "Trace encoding of transmitted packets";
           }
           enum "decode" {
             description "Trace decoding of received packets";
           }
           enum "config" {
             description "Trace configuration related";
           }
           enum "events" {
             description "Trace all internal and external events";
           }
           enum "packet-io" {
             description "Trace transmitted and received packets";
           }
           enum "tracker" {
             description "Trace gtp tracker related events";
           }
           enum "peer" {
             description "Trace gtp peer related events";
           }
           enum "pathfailure" {
             description "Trace gtp peer path failure related events";
           }
           enum "all" {
             description "Trace everything";
           }
         }
       }
     }
   }
   grouping mobile-gateways-ipv6-router-advertisement {
     uses apply-advanced;
     leaf disable {
       description "Disable IPv6 router advertisements - default is enable";
       type empty;
     }
     leaf maximum-advertisement-interval {
       description "Maximum interval between router advertisements";
       default "21600";
       units "seconds";
       type union {
         type string {
           pattern "<.*>|$.*";
         }
         type uint32 {
           range "5400 .. 21600";
         }
       }
     }
     leaf minimum-advertisement-interval {
       description "Minimum interval between router advertisements";
       default "16200";
       units "seconds";
       type union {
         type string {
           pattern "<.*>|$.*";
         }
         type uint32 {
           range "3600 .. 16200";
         }
       }
     }
     leaf maximum-initial-advertisement-interval {
       description "Maximum interval between initial router advertisements";
       default "10";
       units "seconds";
       type union {
         type string {
           pattern "<.*>|$.*";
         }
         type uint32 {
           range "10 .. 16";
         }
       }
     }
     leaf maximum-initial-advertisements {
       description "Maximum number of initial router advertisements";
       default "3";
       type union {
         type string {
           pattern "<.*>|$.*";
         }
         type uint32 {
           range "2 .. 5";
         }
       }
     }
     leaf reachable-time {
       description "Value to be placed in reachable time field";
       default "0";
       units "milliseconds";
       type union {
         type string {
           pattern "<.*>|$.*";
         }
         type uint32 {
           range "0 .. 3600000";
         }
       }
     }
     leaf retransmission-timer {
       description "Value to be placed in retransmit timer field";
       default "0";
       units "milliseconds";
       type union {
         type uint32;
         type string {
           pattern "<.*>|$.*";
         }
       }
     }
     leaf router-lifetime {
       description "Value to be placed in router lifetime field";
       default "21840";
       units "seconds";
       type union {
         type string {
           pattern "<.*>|$.*";
         }
         type uint32 {
           range "5400 .. 21840";
         }
       }
     }
     leaf current-hop-limit {
       description "Value to be placed in current hop limit field";
       default "0";
       type union {
         type string {
           pattern "<.*>|$.*";
         }
         type uint32 {
           range "0 .. 3";
         }
       }
     }
   }
   grouping mobile-smd-traceoptions {
     description "Trace options related to mobile-smd";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "critical" {
           description "Match critical conditions";
         }
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "ctxt" {
             description "Trace UE/PDN/Bearer ctxt events";
           }
           enum "svcpic" {
             description "Trace service-PIC interface";
           }
           enum "fsm" {
             description "Trace FSM events";
           }
           enum "ha" {
             description "Trace High Availability events";
           }
           enum "waitq" {
             description "Trace waitq events";
           }
           enum "pfem" {
             description "Trace PFE Manager events";
           }
           enum "stats" {
             description "Trace stats events";
           }
           enum "bulkjob" {
             description "Trace resources";
           }
           enum "cos-cac" {
             description "Trace cos and cac events";
           }
           enum "all" {
             description "Trace everything";
           }
         }
       }
     }
   }
   grouping rmps-clnt-traceoptions-type {
     description "Trace options for Resource Management and Packet Steering Client";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Client to trace";
       leaf name {
         type enumeration {
           enum "infra" {
             description "Trace FSM and Infra code";
           }
           enum "memory" {
             description "Trace Memory Management Code";
           }
           enum "communication" {
             description "Trace IPC code";
           }
           enum "resource-tables" {
             description "Trace Resource Table Code";
           }
           enum "info-tables" {
             description "Trace Information Table Code";
           }
           enum "redundancy" {
             description "Trace GRES Code";
           }
           enum "all" {
             description "Trace All Resource Client Code";
           }
         }
       }
     }
   }
   grouping rmpsd-traceoptions-type {
     description "Trace options for Resource Management and Packet Steering Daemon";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Area to trace";
       leaf name {
         type enumeration {
           enum "config" {
             description "Trace configuration code";
           }
           enum "gres" {
             description "Trace GRES code";
           }
           enum "init" {
             description "Trace initialization code";
           }
           enum "memory" {
             description "Trace memory management code";
           }
           enum "communication" {
             description "Trace Infra code";
           }
           enum "license-management" {
             description "Trace license management code";
           }
           enum "signal" {
             description "Trace signal handling code";
           }
           enum "state" {
             description "Trace state handling code";
           }
           enum "timer" {
             description "Trace timer code";
           }
           enum "ui" {
             description "Trace user interface code";
           }
           enum "resource-manager" {
             description "Trace Resource Management Code";
           }
           enum "info-manager" {
             description "Trace Information Management Code";
           }
           enum "packet-steering" {
             description "Trace packet-steering code";
           }
           enum "all" {
             description "Trace all areas of code";
           }
         }
       }
     }
   }
   grouping sgw-config-gtp {
     description "GTP configuration";
     uses apply-advanced;
     leaf peer-history {
       description "Maximum number of peer stats stored in history";
       type union {
         type string {
           pattern "<.*>|$.*";
         }
         type uint16 {
           range "1 .. 1000";
         }
       }
     }
     container interface {
       description "Interface name used for all 3GPP interface";
       leaf intf-name {
         description "Interface name";
         junos:must "(\"interfaces $$-IFL family inet address\")";
         junos:must-message "Family inet address should be configured on this interface";
         type union {
           type jt:interface-name;
           type string {
             pattern "<.*>|$.*";
           }
         }
       }
       leaf v4-address {
         description "IPv4 address if multiple addresses configured on interface";
         type jt:ipv4addr;
       }
     }
     leaf echo-interval {
       description "Echo Request interval value for path management";
       units "seconds";
       type union {
         type string {
           pattern "<.*>|$.*";
         }
         type uint16 {
           range "60 .. 65535";
         }
       }
     }
     leaf path-management {
       description "Enable/disable path management";
       type enumeration {
         enum "enable" {
           description "Enable parameter";
         }
         enum "disable" {
           description "Disable parameter";
         }
       }
     }
     leaf echo-n3-requests {
       description "Number of retries of GTP echo messages upon timeout";
       type union {
         type string {
           pattern "<.*>|$.*";
         }
         type uint16 {
           range "1 .. 8";
         }
       }
     }
     leaf echo-t3-response {
       description "Response timeout value for GTP echo request message";
       units "seconds";
       type union {
         type string {
           pattern "<.*>|$.*";
         }
         type uint16 {
           range "1 .. 30";
         }
       }
     }
     leaf path-failure {
       description "Enable/disable path failure";
       type enumeration {
         enum "enable" {
           description "Enable parameter";
         }
         enum "disable" {
           description "Disable parameter";
         }
       }
     }
     leaf number-of-msgs-for-response-time {
       description "Number of msgs used for calculating peer response times";
       default "10000";
       type union {
         type string {
           pattern "<.*>|$.*";
         }
         type uint16 {
           range "1 .. 65535";
         }
       }
     }
     container control {
       description "Configure 3GPP GTP control plane options";
       uses apply-advanced;
       container interface {
         description "Interface name used for all 3GPP control interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       leaf forwarding-class {
         description "Classification of host traffic to forwarding engine";
         type string {
           junos:posix-pattern "^.{1,64}$";
           junos:pattern-message "Must be string of 64 characters or less";
         }
       }
       leaf n3-requests {
         description "Number of retries of GTP messages upon timeout";
         type union {
           type string {
             pattern "<.*>|$.*";
           }
           type uint16 {
             range "1 .. 5";
           }
         }
       }
       leaf t3-response {
         description "Response timeout value for GTP request message";
         units "seconds";
         type union {
           type string {
             pattern "<.*>|$.*";
           }
           type uint16 {
             range "1 .. 30";
           }
         }
       }
       leaf dscp-code-point {
         description "Static DSCP code point of egress host traffic";
         type union {
           type string {
             pattern "<.*>|$.*";
           }
           type uint8 {
             range "0 .. 63";
           }
         }
       }
       leaf ttl-value {
         description "Time To Live value for GTP messages";
         type union {
           type string {
             pattern "<.*>|$.*";
           }
           type uint8 {
             range "1 .. 255";
           }
         }
       }
       leaf ddn-delay-sync {
         description "Enable/disable downlink data notification delay sync";
         type enumeration {
           enum "enable" {
             description "Enable parameter";
           }
           enum "disable" {
             description "Disable parameter";
           }
         }
       }
       leaf no-response-cache {
         description "Disable GTP response cache";
         type empty;
       }
       leaf response-cache-timeout {
         description "GTP response cache timeout interval";
         default "15";
         units "seconds";
         type union {
           type string {
             pattern "<.*>|$.*";
           }
           type uint8 {
             range "5 .. 20";
           }
         }
       }
       leaf no-piggyback-support {
         description "Disable GTPv2 piggyback support";
         type empty;
       }
     }
     container data {
       description "Configure 3GPP GTP data plane options";
       uses apply-advanced;
       container interface {
         description "Interface name used for all 3GPP data interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf num-gtpu-end-markers {
         description "Number of GTPU end marker pkts to be sent. range:1..10";
         default "1";
         type union {
           type string {
             pattern "<.*>|$.*";
           }
           type uint8 {
             range "1 .. 10";
           }
         }
       }
       leaf indirect-tunnel {
         description "Enable/disable indirect tunnel";
         type enumeration {
           enum "enable" {
             description "Enable parameter";
           }
           enum "disable" {
             description "Disable parameter";
           }
         }
       }
       leaf error-indication-interval {
         description "Error indication transmit interval per bearer ";
         default "2";
         units "seconds";
         type union {
           type string {
             pattern "<.*>|$.*";
           }
           type uint16 {
             range "1 .. 20";
           }
         }
       }
     }
     container s1u {
       presence "enable s1u";
       description "Configure 3GPP S1U interface";
       uses apply-advanced;
       container interface {
         description "Interface name used for S1U data interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
     }
     container s11 {
       presence "enable s11";
       description "Configure 3GPP S11 interface";
       uses apply-advanced;
       container interface {
         description "Interface name used for S11 control interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       leaf forwarding-class {
         description "Classification of host traffic to forwarding engine";
         type string {
           junos:posix-pattern "^.{1,64}$";
           junos:pattern-message "Must be string of 64 characters or less";
         }
       }
       leaf n3-requests {
         description "Number of retries of GTP messages upon timeout";
         type union {
           type string {
             pattern "<.*>|$.*";
           }
           type uint16 {
             range "1 .. 5";
           }
         }
       }
       leaf t3-response {
         description "Response timeout value for GTP request message";
         units "seconds";
         type union {
           type string {
             pattern "<.*>|$.*";
           }
           type uint16 {
             range "1 .. 30";
           }
         }
       }
       leaf dscp-code-point {
         description "Static DSCP code point of egress host traffic";
         type union {
           type string {
             pattern "<.*>|$.*";
           }
           type uint8 {
             range "0 .. 63";
           }
         }
       }
       leaf ttl-value {
         description "Time To Live value for GTP messages";
         type union {
           type string {
             pattern "<.*>|$.*";
           }
           type uint8 {
             range "1 .. 255";
           }
         }
       }
     }
     container s12 {
       presence "enable s12";
       description "Configure 3GPP S12 interface";
       uses apply-advanced;
       container interface {
         description "Interface name used for S12 data interface";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
     }
     container s4 {
       description "Configure 3GPP S4 interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
         leaf ttl-value {
           description "Time To Live value for GTP messages";
           type union {
             type string {
               pattern "<.*>|$.*";
             }
             type uint8 {
               range "1 .. 255";
             }
           }
         }
       }
       container data {
         description "Configure 3GPP data plane options";
         uses apply-advanced;
         container interface {
           description "Interface name used for data interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
       }
     }
     container s5 {
       description "Configure 3GPP S5 interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
         leaf ttl-value {
           description "Time To Live value for GTP messages";
           type union {
             type string {
               pattern "<.*>|$.*";
             }
             type uint8 {
               range "1 .. 255";
             }
           }
         }
       }
       container data {
         description "Configure 3GPP data plane options";
         uses apply-advanced;
         container interface {
           description "Interface name used for data interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
       }
     }
     container s8 {
       description "Configure 3GPP S8 interface";
       uses apply-advanced;
       container interface {
         description "Interface name used";
         leaf intf-name {
           description "Interface name";
           junos:must "(\"interfaces $$-IFL family inet address\")";
           junos:must-message "Family inet address should be configured on this interface";
           type union {
             type jt:interface-name;
             type string {
               pattern "<.*>|$.*";
             }
           }
         }
         leaf v4-address {
           description "IPv4 address if multiple addresses configured on interface";
           type jt:ipv4addr;
         }
       }
       leaf echo-interval {
         description "Echo Request interval value for path management";
         units "seconds";
         type union {
           type string {
             pattern "<.*>|$.*";
           }
           type uint16 {
             range "60 .. 65535";
           }
         }
       }
       leaf path-management {
         description "Enable/disable path management";
         type enumeration {
           enum "enable" {
             description "Enable parameter";
           }
           enum "disable" {
             description "Disable parameter";
           }
         }
       }
       leaf echo-n3-requests {
         description "Number of retries of GTP echo messages upon timeout";
         type union {
           type string {
             pattern "<.*>|$.*";
           }
           type uint16 {
             range "1 .. 8";
           }
         }
       }
       leaf echo-t3-response {
         description "Response timeout value for GTP echo request message";
         units "seconds";
         type union {
           type string {
             pattern "<.*>|$.*";
           }
           type uint16 {
             range "1 .. 30";
           }
         }
       }
       leaf path-failure {
         description "Enable/disable path failure";
         type enumeration {
           enum "enable" {
             description "Enable parameter";
           }
           enum "disable" {
             description "Disable parameter";
           }
         }
       }
       leaf number-of-msgs-for-response-time {
         description "Number of msgs used for calculating peer response times";
         default "10000";
         type union {
           type string {
             pattern "<.*>|$.*";
           }
           type uint16 {
             range "1 .. 65535";
           }
         }
       }
       container control {
         description "Configure 3GPP control plane options";
         uses apply-advanced;
         container interface {
           description "Interface name used for control interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
         leaf number-of-msgs-for-response-time {
           description "Number of msgs used for calculating peer response times";
           default "10000";
           type union {
             type string {
               pattern "<.*>|$.*";
             }
             type uint16 {
               range "1 .. 65535";
             }
           }
         }
         leaf forwarding-class {
           description "Classification of host traffic to forwarding engine";
           type string {
             junos:posix-pattern "^.{1,64}$";
             junos:pattern-message "Must be string of 64 characters or less";
           }
         }
         leaf n3-requests {
           description "Number of retries of GTP messages upon timeout";
           type union {
             type string {
               pattern "<.*>|$.*";
             }
             type uint16 {
               range "1 .. 5";
             }
           }
         }
         leaf t3-response {
           description "Response timeout value for GTP request message";
           units "seconds";
           type union {
             type string {
               pattern "<.*>|$.*";
             }
             type uint16 {
               range "1 .. 30";
             }
           }
         }
         leaf dscp-code-point {
           description "Static DSCP code point of egress host traffic";
           type union {
             type string {
               pattern "<.*>|$.*";
             }
             type uint8 {
               range "0 .. 63";
             }
           }
         }
         leaf ttl-value {
           description "Time To Live value for GTP messages";
           type union {
             type string {
               pattern "<.*>|$.*";
             }
             type uint8 {
               range "1 .. 255";
             }
           }
         }
       }
       container data {
         description "Configure 3GPP data plane options";
         uses apply-advanced;
         container interface {
           description "Interface name used for data interface";
           leaf intf-name {
             description "Interface name";
             junos:must "(\"interfaces $$-IFL family inet address\")";
             junos:must-message "Family inet address should be configured on this interface";
             type union {
               type jt:interface-name;
               type string {
                 pattern "<.*>|$.*";
               }
             }
           }
           leaf v4-address {
             description "IPv4 address if multiple addresses configured on interface";
             type jt:ipv4addr;
           }
         }
         leaf echo-interval {
           description "Echo Request interval value for path management";
           units "seconds";
           type union {
             type string {
               pattern "<.*>|$.*";
             }
             type uint16 {
               range "60 .. 65535";
             }
           }
         }
         leaf path-management {
           description "Enable/disable path management";
           type enumeration {
             enum "enable" {
               description "Enable parameter";
             }
             enum "disable" {
               description "Disable parameter";
             }
           }
         }
         leaf echo-n3-requests {
           description "Number of retries of GTP echo messages upon timeout";
           type union {
             type string {
               pattern "<.*>|$.*";
             }
             type uint16 {
               range "1 .. 8";
             }
           }
         }
         leaf echo-t3-response {
           description "Response timeout value for GTP echo request message";
           units "seconds";
           type union {
             type string {
               pattern "<.*>|$.*";
             }
             type uint16 {
               range "1 .. 30";
             }
           }
         }
         leaf path-failure {
           description "Enable/disable path failure";
           type enumeration {
             enum "enable" {
               description "Enable parameter";
             }
             enum "disable" {
               description "Disable parameter";
             }
           }
         }
       }
     }
     container traceoptions {
       description "Configure trace options";
       uses gtp-traceoptions;
     }
   }
   grouping sgw-idle-mode-buffering {
     description "Idle mode buffering options";
     uses apply-advanced;
     leaf disable {
       description "Disable idle mode buffering";
       type empty;
     }
     leaf expire-timer {
       description "Expire timer";
       default "200";
       units "seconds";
       type union {
         type string {
           pattern "<.*>|$.*";
         }
         type uint32 {
           range "30 .. 300";
         }
       }
     }
   }
   grouping software-datapath-traceoptions {
     description "Trace options for software-datapath";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "ager" {
             description "Trace flow ager ";
           }
           enum "commands" {
             description "Trace operational commands";
           }
           enum "configuration" {
             description "Trace configuration events";
           }
           enum "flow" {
             description "Trace flow";
           }
           enum "init" {
             description "Trace events related to datapath daemon init";
           }
           enum "ipv6-router-advertisement" {
             description "Trace ipv6 router-advertisement ";
           }
           enum "memory" {
             description "Trace memory";
           }
           enum "redundancy" {
             description "Trace redundancy";
           }
           enum "reassembly" {
             description "Trace reassembly";
           }
           enum "buffering" {
             description "Trace buffering";
           }
           enum "all" {
             description "Trace everything";
           }
         }
       }
     }
   }
   grouping unified-edge-gateway-diameter {
     uses apply-advanced;
     list network-element {
       key name;
       ordered-by user;
       description "Diameter network element configuration per mobile gateway";
       leaf name {
         description "Diameter network-element name";
         junos:must "(\"access diameter network-element $$\")";
         junos:must-message "Referenced DNE must be defined";
         type string {
           length "1 .. 31";
         }
       }
       uses apply-advanced;
       container session-pics {
         description "Session MS-PICs to serve this Diameter network element";
         uses unified-edge-gateway-diameter-ne-session-pics;
       }
     }
   }
   grouping unified-edge-gateway-diameter-ne-session-pics {
     uses apply-advanced;
     list group {
       key name;
       ordered-by user;
       description "Diameter network element Multiservice PIC group";
       leaf name {
         description "Group name";
         type string;
       }
       uses apply-advanced;
       list session-pic {
         key name;
         ordered-by user;
         description "Multiservice PICs serving the Diameter network element in this group";
         leaf name {
           description "Interface name representing multiservice PIC";
           junos:must "(\".. .. .. .. .. .. system session-pics interface $$\")";
           junos:must-message "Session-pics should be defined under gateway";
           type union {
             type jt:interface-unit;
             type string {
               pattern "<.*>|$.*";
             }
           }
         }
         uses apply-advanced;
       }
     }
   }
   grouping unified-edge-ggsn-pgw-system {
     uses apply-advanced;
     container pfes {
       description "Packet forwarding engines used for anchoring";
       uses apply-advanced;
       list interface {
         key name;
         ordered-by user;
         description "Interface representing packet forwarding engine";
         leaf name {
           description "Interface name representing packet forwarding engine";
           type union {
             type jt:interface-unit;
             type string {
               pattern "<.*>|$.*";
             }
           }
         }
         uses apply-advanced;
         leaf service-mode {
           description "Service mode";
           type enumeration {
             enum "maintenance" {
               description "Maintenance mode";
             }
           }
         }
       }
     }
     container session-pics {
       description "Multiservice PICs used for anchoring control sessions";
       uses apply-advanced;
       list interface {
         key name;
         ordered-by user;
         description "Interface representing multiservice PIC";
         leaf name {
           description "Interface name representing multiservice PIC";
           type union {
             type jt:interface-unit;
             type string {
               pattern "<.*>|$.*";
             }
           }
         }
         uses apply-advanced;
         leaf service-mode {
           description "Service mode";
           type enumeration {
             enum "maintenance" {
               description "Maintenance mode";
             }
           }
         }
       }
     }
     container service-pics {
       presence "enable service-pics";
       description "Multiservice PICs used for anchoring service related data sessions";
       uses apply-advanced;
       list interface {
         key name;
         ordered-by user;
         description "Interface representing multiservice PIC";
         leaf name {
           description "Interface name representing multiservice PIC";
           type union {
             type jt:interface-unit;
             type string {
               pattern "<.*>|$.*";
             }
           }
         }
         uses apply-advanced;
         leaf service-mode {
           description "Service mode";
           type enumeration {
             enum "maintenance" {
               description "Maintenance mode";
             }
           }
         }
       }
     }
   }
   grouping unified-edge-mobile-options {
     description "Unified edge mobile options";
     uses apply-advanced;
     container traceoptions {
       description "Mobility config and operational command daemon trace options";
       uses mobiled-traceoptions;
     }
   }
   grouping mobiled-traceoptions {
     description "Trace options for mobiled";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Tracing parameters";
       leaf name {
         type enumeration {
           enum "configuration" {
             description "Trace configuration events";
           }
           enum "protocol" {
             description "Trace protocol processing events";
           }
           enum "init" {
             description "Trace events related to protocol daemon start-up";
           }
           enum "error" {
             description "Trace events related to catestrophic errors in daemon";
           }
           enum "all" {
             description "Trace everything";
           }
         }
       }
       leaf send {
         description "Trace transmitted packets";
         type empty;
       }
       leaf receive {
         description "Trace received packets";
         type empty;
       }
       leaf detail {
         description "Trace detailed information";
         type empty;
       }
       leaf disable {
         description "Disable this trace flag";
         type empty;
       }
     }
   }
   grouping unified-edge-pcef {
     description "PCEF configuration";
     uses apply-advanced;
     container traceoptions {
       description "Trace options related to PCEF";
       uses pcef-traceoptions;
     }
     container event-trigger-profiles {
       description "Event trigger profiles";
       uses apply-advanced;
       list profile {
         key name;
         uses evt-trigger-profile;
       }
     }
     container flow-descriptions {
       description "PCC flow descriptions";
       uses apply-advanced;
       list definition {
         key name;
         uses pcc-flow;
       }
     }
     container pcc-action-profiles {
       description "PCC action profiles";
       uses apply-advanced;
       list definition {
         key name;
         uses pcc-action-profile;
       }
     }
     container pcc-rules {
       description "PCC rules";
       uses apply-advanced;
       list definition {
         key name;
         uses pcc-rule;
       }
     }
     container pcc-rulebases {
       description "PCC rulebases";
       uses apply-advanced;
       list definition {
         key name;
         ordered-by user;
         uses pcc-rulebase;
       }
     }
     container profiles {
       junos:must "(!(\"system services subscriber-management enable\"))";
       junos:must-message "unified-edge pcef profiles is not allowed when enhanced-ip is configured";
       description "PCEF profiles";
       uses apply-advanced;
       list definition {
         key name;
         ordered-by user;
         uses pcef-profiles;
       }
     }
     container pcc-time-of-day-profiles {
       description "PCEF Time Of Day profiles";
       uses apply-advanced;
       list definition {
         key name;
         ordered-by user;
         uses pcef-time-of-day-profile;
       }
     }
   }
   grouping evt-trigger-profile {
     description "Event trigger profile";
     leaf name {
       description "Event trigger profile name";
       type string {
         length "1 .. 63";
       }
     }
     uses apply-advanced;
     leaf rat-change {
       description "RAT change trigger";
       type empty;
     }
     leaf sgsn-change {
       description "SGSN change trigger";
       type empty;
     }
     leaf plmn-change {
       description "PLMN change trigger";
       type empty;
     }
     leaf ip-can-change {
       description "IP-CAN change trigger";
       type empty;
     }
     leaf tft-change {
       description "TFT change trigger";
       type empty;
     }
     leaf rai-change {
       description "RAI change trigger";
       type empty;
     }
     leaf user-location-change {
       description "User location change";
       type empty;
     }
     leaf ue-timezone-change {
       description "UE timezone change";
       type empty;
     }
   }
   grouping pcc-action-profile {
     description "PCC action profiles";
     leaf name {
       description "PCC action profile identifier";
       type string {
         length "1 .. 63";
       }
     }
     uses apply-advanced;
     leaf logging-rule {
       description "Policy based logging rule name";
       junos:must "(any \"services lrf profile <*> rule $$\")";
       junos:must-message "Specified rule should be configured under services lrf profile rule";
       type string {
         length "1 .. 63";
       }
     }
     container maximum-bit-rate {
       presence "enable maximum-bit-rate";
       description "Maximum bit rate";
       leaf uplink {
         description "Maximum bit rate uplink";
         default "0";
         units "kilobits";
         type union {
           type string {
             pattern "<.*>|$.*";
           }
           type uint32 {
             range "0 .. 6144000";
           }
         }
       }
       leaf downlink {
         description "Maximum bit rate downlink";
         default "0";
         units "kilobits";
         type union {
           type string {
             pattern "<.*>|$.*";
           }
           type uint32 {
             range "0 .. 6144000";
           }
         }
       }
     }
     container burst-size {
       presence "enable burst-size";
       description "Burst Size";
       uses apply-advanced;
       leaf uplink {
         description "Burst size uplink";
         units "bytes";
         type union {
           type string {
             pattern "<.*>|$.*";
           }
           type uint32 {
             range "1500 .. 1500000000";
           }
         }
       }
       leaf downlink {
         description "Burst size downlink";
         units "bytes";
         type union {
           type string {
             pattern "<.*>|$.*";
           }
           type uint32 {
             range "1500 .. 1500000000";
           }
         }
       }
     }
     leaf gate-status {
       description "Control gate status";
       type enumeration {
         enum "uplink" {
           description "Enable uplink traffic";
         }
         enum "downlink" {
           description "Enable downlink traffic";
         }
         enum "uplink-downlink" {
           description "Enable uplink and downlink traffic";
         }
         enum "disable-both" {
           description "Disable any traffic";
         }
       }
     }
     container charging {
       description "Charing related configuration";
       uses apply-advanced;
       leaf rating-group {
         description "Rating group";
         type union {
           type string {
             pattern "<.*>|$.*";
           }
           type uint32 {
             range "0 .. 4294967294";
           }
         }
       }
       leaf service-identifier {
         description "Service identifier";
         default "0";
         type union {
           type string {
             pattern "<.*>|$.*";
           }
           type uint32 {
             range "0 .. 4294967294";
           }
         }
       }
       leaf charging-method {
         description "Charging method";
         type enumeration {
           enum "online" {
             description "Use online charging method";
           }
           enum "offline" {
             description "Use offline charging method";
           }
           enum "both" {
             description "Use online and offline charging method";
           }
           enum "none" {
             description "Use no charging";
           }
         }
       }
       leaf measurement-method {
         description "Charging measure method";
         default "volume-time";
         type enumeration {
           enum "none" {
             description "No default measuring method for charging";
           }
           enum "volume" {
             description "Volume based charging";
           }
           enum "time" {
             description "Time based charging";
           }
           enum "volume-time" {
             description "Volume and time based charging";
           }
           enum "event" {
             description "Event based charging";
           }
         }
       }
       container application-function-record-info {
         presence "enable application-function-record-info";
         description "Application function record information";
         uses apply-advanced;
         leaf af-charging-identifier {
           description "Application function charging identifier";
           type string {
             length "1 .. 63";
           }
         }
       }
       leaf service-id-level-reporting {
         description "Toggle service-id level reporting";
         type empty;
       }
     }
     container redirect {
       description "Redirect to different destination";
       uses apply-advanced;
       leaf url {
         description "Redirect url name";
         junos:must "(!(\".. routing-instance\"))";
         junos:must-message "Either url or routing instance can be defined";
         type string {
           length "1 .. 512";
         }
       }
     }
     container forwarding-class {
       description "Classify packet to forwarding class";
       uses apply-advanced;
       leaf class-name {
         description "Forwarding class name";
         type string {
           junos:posix-pattern "^.{1,64}$";
           junos:pattern-message "Must be string of 64 characters or less";
         }
       }
     }
     container steering {
       description "Steering information";
       uses apply-advanced;
       container routing-instance {
         description "Routing instance information";
         leaf uplink {
           description "Instance name uplink";
           junos:must "(\"routing-instances $$\")";
           junos:must-message "routing instance must be defined";
           type string;
         }
         leaf downlink {
           description "Instance name downlink";
           junos:must "(\"routing-instances $$\")";
           junos:must-message "routing instance must be defined";
           type string;
         }
       }
       container path {
         description "HTTP steering information";
         choice ip-address-type {
           case case_1 {
             leaf ipv4-address {
               description "IPv4 address of the steering destination";
               type jt:ipv4prefix;
             }
           }
           case case_2 {
             leaf ipv6-address {
               description "IPv6 address of the steering destination";
               type jt:ipv6prefix;
             }
           }
         }
       }
       leaf keep-existing-steering {
         description "Keep existing steering";
         type empty;
       }
     }
     container hcm-profile {
       description "HCM Profile";
       uses apply-advanced;
       leaf profile-name {
         description "HCM Profile Name";
         junos:must "(\"services hcm profile $$\")";
         junos:must-message "HCM Profile must be configured";
         type string;
       }
     }
     leaf monitoring-key {
       description "Usage Monitoring key";
       type string {
         length "1 .. 63";
       }
     }
   }
   grouping pcc-flow {
     description "Configure PCC flow";
     leaf name {
       description "PCC flow identifier";
       type string {
         length "1 .. 63";
       }
     }
     uses apply-advanced;
     leaf direction {
       description "PCC flow direction";
       type enumeration {
         enum "downlink" {
           description "Downlink direction";
         }
         enum "uplink" {
           description "Uplink direction";
         }
         enum "both" {
           description "Both uplink and downlink directons";
         }
       }
     }
     leaf protocol {
       description "PCC flow IPv4 protocol";
       type union {
         type string {
           pattern "<.*>|$.*";
         }
         type uint8 {
           range "0 .. 255";
         }
       }
     }
     leaf-list local-ports {
       description "Local port or port list";
       junos:must "(!(\".. local-port-range\"))";
       junos:must-message "Either port list or port range can be defined";
       type union {
         type string {
           pattern "<.*>|$.*";
         }
         type uint16 {
           range "1 .. 65535";
         }
       }
       max-elements 3;
     }
     list local-port-range {
       key "low high";
       ordered-by user;
       description "Local port range";
       junos:must "(!(\".. local-ports\"))";
       junos:must-message "Either port list or port range can be defined";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     leaf-list remote-ports {
       description "Remote port or port list";
       junos:must "(!(\".. remote-port-range\"))";
       junos:must-message "Either port list or port range can be defined";
       type union {
         type string {
           pattern "<.*>|$.*";
         }
         type uint16 {
           range "1 .. 65535";
         }
       }
       max-elements 3;
     }
     list remote-port-range {
       key "low high";
       ordered-by user;
       description "Remote port range";
       junos:must "(!(\".. remote-ports\"))";
       junos:must-message "Either port list or port range can be defined";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     container remote-address {
       description "Remote address";
       choice ip-address-type {
         case case_1 {
           leaf ipv4-address {
             description "IPv4 address for the flow";
             type jt:ipv4prefix;
           }
         }
         case case_2 {
           leaf ipv6-address {
             description "IPv6 address for the flow";
             type jt:ipv6prefix;
           }
         }
       }
     }
   }
   grouping pcc-rule {
     description "PCC rules configuration";
     leaf name {
       description "PCC Rule identifier";
       type string {
         junos:posix-pattern "^[.0-9A-Za-z_-]{1,63}$";
         junos:pattern-message "Must be a string of 63 or fewer characters and may contain letters, numbers, decimals and dashes.";
       }
     }
     uses apply-advanced;
     container from {
       description "Aggregate of flows using same pcc-action-profile";
       uses apply-advanced;
       list flows {
         key name;
         ordered-by user;
         description "Associate PCC Flows";
         max-elements 64;
         leaf name {
           description "PCC Flow identifier";
           junos:must "(\".. .. .. .. .. flow-descriptions $$\")";
           junos:must-message "Referenced flow must be defined";
           type string {
             length "1 .. 63";
           }
         }
         uses apply-advanced;
       }
       list applications {
         key name;
         ordered-by user;
         description "Associated application signature names";
         max-elements 10;
         leaf name {
           description "Signature names";
           type string {
             length "1 .. 63";
           }
         }
         uses apply-advanced;
       }
       list nested-applications {
         key name;
         ordered-by user;
         description "Associated nested application signature names";
         status deprecated;
         max-elements 10;
         leaf name {
           description "Nested application signature names";
           type string {
             length "1 .. 63";
           }
         }
         uses apply-advanced;
       }
       list application-groups {
         key name;
         ordered-by user;
         description "Application Group signature names";
         max-elements 10;
         leaf name {
           description "Application group names";
           type string {
             length "1 .. 63";
           }
         }
         uses apply-advanced;
       }
     }
     container then {
       description "Specified pcc-action-profile";
       uses apply-advanced;
       leaf pcc-action-profile {
         description "PCC Action profile name";
         junos:must "(\".. .. .. .. pcc-action-profiles $$\")";
         junos:must-message "Referenced action profile must be defined";
         type string {
           length "1 .. 63";
         }
       }
     }
   }
   grouping pcc-rulebase {
     description "PCC rulebases";
     leaf name {
       description "PCC Rulebase identifier";
       type string {
         junos:posix-pattern "^[.0-9A-Za-z_-]{1,63}$";
         junos:pattern-message "Must be a string of 63 or fewer charactars and may contain letters, numbers, decimals and dashes";
       }
     }
     uses apply-advanced;
     list pcc-rule {
       key name;
       ordered-by user;
       max-elements 32;
       leaf name {
         description "PCC rule name";
         junos:must "(\".. .. .. .. pcc-rules $$\")";
         junos:must-message "Referenced rule must be defined";
         type string {
           length "1 .. 63";
           junos:posix-pattern "^[.0-9A-Za-z_-]{1,63}$";
           junos:pattern-message "Must be a string of 63 or fewer charactars and may contain letters, numbers, decimals and dashes";
         }
       }
       leaf precedence {
         description "PCC rule precedence";
         junos:must "(unique \".. .. pcc-rule <*> precedence $$\")";
         junos:must-message "Precedence has to unique among rules";
         type union {
           type string {
             pattern "<.*>|$.*";
           }
           type uint16 {
             range "1 .. 4000";
           }
         }
       }
     }
   }
   grouping pcef-profiles {
     description "PCEF profiles";
     leaf name {
       description "PCEF profile name";
       type string {
         length "1 .. 63";
       }
     }
     uses apply-advanced;
     leaf control-byte-rating-group {
       description "Rating group id";
       type union {
         type string {
           pattern "<.*>|$.*";
         }
         type uint32 {
           range "0 .. 4294967294";
         }
       }
     }
     leaf unresolved-flow-action {
       description "Flow action";
       type enumeration {
         enum "forward" {
           description "Forward";
         }
         enum "drop" {
           description "Drop";
         }
       }
     }
     container maximum-per-pdn-service-flows {
       description "Max service flows per PDN";
       leaf num {
         description "Value";
         type union {
           type uint32;
           type string {
             pattern "<.*>|$.*";
           }
         }
       }
     }
     container dynamic-policy-control {
       junos:must "((\"diameter-profile\" || \".. .. .. .. .. system services subscriber-management enable\"))";
       junos:must-message "diameter-profile must be configured when 'system services subscriber-management' is not enabled";
       junos:must "((!(\".. static-policy-control\") && !(\".. aaa-policy-control\")))";
       junos:must-message "Either static or dynamic or AAA policy control can be specified";
       description "Dynamic policy control";
       uses apply-advanced;
       container pcc-rules {
         description "PCC rules association";
         uses apply-advanced;
         list rule-assoc {
           key name;
           ordered-by user;
           max-elements 64;
           uses profile-rule-assoc;
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
       }
       leaf diameter-profile {
         description "Diameter profile name";
         junos:must "(\".. .. .. .. .. diameter-profiles gx-profile $$\")";
         junos:must-message "Referenced diameter profile must be defined";
         type string {
           length "1 .. 63";
         }
       }
       leaf event-trigger-profile {
         description "Event trigger profile name";
         junos:must "(\".. .. .. .. event-trigger-profiles $$\")";
         junos:must-message "Referenced event trigger profile must be defined";
         type string {
           length "1 .. 63";
         }
       }
       leaf session-failover-not-supported {
         description "Session failover not supported";
         type empty;
       }
       leaf release {
         description "To override Gx release to R8|R9";
         type enumeration {
           enum "r8" {
             description "Gx release 8";
           }
           enum "r9" {
             description "Gx release 9";
           }
         }
       }
     }
     container static-policy-control {
       junos:must "((!(\".. dynamic-policy-control\") && !(\".. aaa-policy-control\")))";
       junos:must-message "Either static or dynamic or AAA policy control can be specified";
       description "Static policy control";
       uses apply-advanced;
       container pcc-rules {
         description "PCC rules association";
         uses apply-advanced;
         list rule-assoc {
           key name;
           ordered-by user;
           max-elements 64;
           uses profile-static-rule-association;
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
         leaf time-of-day-profile {
           description "Time of day profile name";
           junos:must "(\".. .. .. .. .. pcc-time-of-day-profiles $$\")";
           junos:must-message "Referenced time-of-day profile must be defined";
           type string {
             length "1 .. 63";
           }
         }
       }
       leaf-list activate-dedicated-bearers {
         description "Enable dedicated bearer activation on initial attach with qci";
         type union {
           type string {
             pattern "<.*>|$.*";
           }
           type uint8 {
             range "1 .. 9";
           }
         }
         max-elements 9;
       }
     }
     container aaa-policy-control {
       junos:must "((!(\".. static-policy-control\") && !(\".. dynamic-policy-control\")))";
       junos:must-message "Either static or dynamic or AAA policy control can be specified";
       description "AAA policy control";
       uses apply-advanced;
       leaf profile {
         description "AAA profile name";
         junos:must "(\".. .. .. .. .. aaa profiles $$\")";
         junos:must-message "Referenced AAA profile must be defined";
         type string {
           length "1 .. 32";
         }
       }
       leaf user-password {
         description "User password";
         type string {
           length "1 .. 32";
         }
       }
       list pcc-rulebases {
         key name;
         ordered-by user;
         description "PCC rulebase association";
         leaf name {
           description "PCC rulebase name";
           junos:must "(\".. .. .. .. .. pcc-rulebases $$\")";
           junos:must-message "Referenced rulebase must be defined";
           type string {
             length "1 .. 63";
           }
         }
         uses apply-advanced;
       }
     }
   }
   grouping pcef-time-of-day-profile {
     description "PCEF Time Of Day profiles";
     leaf name {
       description "PCEF Time Of Day profile name";
       type string {
         length "1 .. 63";
       }
     }
     uses apply-advanced;
     container rule-activation-time {
       description "Rule Activation Time of this profile";
       uses pcef-tod-time-type;
     }
     container rule-deactivation-time {
       description "Rule Dectivation Time of this profile";
       uses pcef-tod-time-type;
     }
   }
   grouping pcef-tod-time-type {
     description "Day of month or week, month of year and Time of the day for this profile";
     uses apply-advanced;
     choice day-of-week-or-month {
       case case_1 {
         leaf SUNDAY {
           description "Sunday";
           type empty;
         }
       }
       case case_2 {
         leaf MONDAY {
           description "Monday";
           type empty;
         }
       }
       case case_3 {
         leaf TUESDAY {
           description "Tuesday";
           type empty;
         }
       }
       case case_4 {
         leaf WEDNESDAY {
           description "Wednesday";
           type empty;
         }
       }
       case case_5 {
         leaf THURSDAY {
           description "Thursday";
           type empty;
         }
       }
       case case_6 {
         leaf FRIDAY {
           description "Friday";
           type empty;
         }
       }
       case case_7 {
         leaf SATURDAY {
           description "Saturday";
           type empty;
         }
       }
       case case_8 {
         leaf DAY1 {
           description "1st of the month";
           type empty;
         }
       }
       case case_9 {
         leaf DAY2 {
           description "2nd of the month";
           type empty;
         }
       }
       case case_10 {
         leaf DAY3 {
           description "3rd of the month";
           type empty;
         }
       }
       case case_11 {
         leaf DAY4 {
           description "4th of the month";
           type empty;
         }
       }
       case case_12 {
         leaf DAY5 {
           description "5th of the month";
           type empty;
         }
       }
       case case_13 {
         leaf DAY6 {
           description "6th of the month";
           type empty;
         }
       }
       case case_14 {
         leaf DAY7 {
           description "7th of the month";
           type empty;
         }
       }
       case case_15 {
         leaf DAY8 {
           description "8th of the month";
           type empty;
         }
       }
       case case_16 {
         leaf DAY9 {
           description "9th of the month";
           type empty;
         }
       }
       case case_17 {
         leaf DAY10 {
           description "10th of the month";
           type empty;
         }
       }
       case case_18 {
         leaf DAY11 {
           description "11th of the month";
           type empty;
         }
       }
       case case_19 {
         leaf DAY12 {
           description "12th of the month";
           type empty;
         }
       }
       case case_20 {
         leaf DAY13 {
           description "13th of the month";
           type empty;
         }
       }
       case case_21 {
         leaf DAY14 {
           description "14th of the month";
           type empty;
         }
       }
       case case_22 {
         leaf DAY15 {
           description "15th of the month";
           type empty;
         }
       }
       case case_23 {
         leaf DAY16 {
           description "16th of the month";
           type empty;
         }
       }
       case case_24 {
         leaf DAY17 {
           description "17th of the month";
           type empty;
         }
       }
       case case_25 {
         leaf DAY18 {
           description "18th of the month";
           type empty;
         }
       }
       case case_26 {
         leaf DAY19 {
           description "19th of the month";
           type empty;
         }
       }
       case case_27 {
         leaf DAY20 {
           description "20th of the month";
           type empty;
         }
       }
       case case_28 {
         leaf DAY21 {
           description "21st of the month";
           type empty;
         }
       }
       case case_29 {
         leaf DAY22 {
           description "22nd of the month";
           type empty;
         }
       }
       case case_30 {
         leaf DAY23 {
           description "23rd of the month";
           type empty;
         }
       }
       case case_31 {
         leaf DAY24 {
           description "24th of the month";
           type empty;
         }
       }
       case case_32 {
         leaf DAY25 {
           description "25th of the month";
           type empty;
         }
       }
       case case_33 {
         leaf DAY26 {
           description "26th of the month";
           type empty;
         }
       }
       case case_34 {
         leaf DAY27 {
           description "27th of the month";
           type empty;
         }
       }
       case case_35 {
         leaf Last-day-of-month {
           description "Last day of the month";
           type empty;
         }
       }
     }
     choice month {
       case case_1 {
         leaf JANUARY {
           description "January";
           type empty;
         }
       }
       case case_2 {
         leaf FEBRUARY {
           description "February";
           type empty;
         }
       }
       case case_3 {
         leaf MARCH {
           description "March";
           type empty;
         }
       }
       case case_4 {
         leaf APRIL {
           description "April";
           type empty;
         }
       }
       case case_5 {
         leaf MAY {
           description "May";
           type empty;
         }
       }
       case case_6 {
         leaf JUNE {
           description "June";
           type empty;
         }
       }
       case case_7 {
         leaf JULY {
           description "July";
           type empty;
         }
       }
       case case_8 {
         leaf AUGUST {
           description "August";
           type empty;
         }
       }
       case case_9 {
         leaf SEPTEMBER {
           description "September";
           type empty;
         }
       }
       case case_10 {
         leaf OCTOBER {
           description "October";
           type empty;
         }
       }
       case case_11 {
         leaf NOVEMBER {
           description "November";
           type empty;
         }
       }
       case case_12 {
         leaf DECEMBER {
           description "December";
           type empty;
         }
       }
     }
     leaf time {
       description "Time of the day in hh:mm format";
       type jt:time-of-day;
     }
   }
   grouping pcef-traceoptions {
     description "Trace options related to PCEF";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "high-availability" {
             description "Trace high availability events";
           }
           enum "debug" {
             description "Trace debug internal events";
           }
           enum "fsm" {
             description "Trace fsm events";
           }
           enum "tftmgr" {
             description "Trace tftmgr events";
           }
           enum "all" {
             description "Trace everything";
           }
         }
       }
     }
   }
   grouping profile-rule-assoc {
     leaf name {
       description "PCC rule name";
       junos:must "(\".. .. .. .. .. .. pcc-rules $$\")";
       junos:must-message "Referenced rule must be defined";
       type string {
         length "1 .. 63";
       }
     }
     leaf precedence {
       description "PCC rule precedence";
       junos:must "(unique \".. .. <*> precedence $$\")";
       junos:must-message "Precedence has to unique among rules";
       type union {
         type string {
           pattern "<.*>|$.*";
         }
         type uint16 {
           range "1 .. 4000";
         }
       }
     }
   }
   grouping profile-static-rule-association {
     leaf name {
       description "PCC rule name";
       junos:must "(\".. .. .. .. .. .. pcc-rules $$\")";
       junos:must-message "Referenced rule must be defined";
       type string {
         length "1 .. 63";
       }
     }
     leaf precedence {
       description "PCC rule precedence";
       junos:must "(unique \".. .. <*> precedence $$\")";
       junos:must-message "Precedence has to unique among rules";
       type union {
         type string {
           pattern "<.*>|$.*";
         }
         type uint16 {
           range "1 .. 4000";
         }
       }
     }
     leaf time-of-day-profile {
       description "Time of day profile name";
       junos:must "(\".. .. .. .. .. .. pcc-time-of-day-profiles $$\")";
       junos:must-message "Referenced time-of-day profile must be defined";
       type string {
         length "1 .. 63";
       }
     }
     container pcc-action-profile {
       description "PCC action profile association";
       status deprecated;
       leaf rules-action-profile {
         description "PCC action profile name";
         junos:must "(\".. .. .. .. .. .. .. pcc-action-profiles $$\")";
         junos:must-message "Referenced action profile must be defined";
         type string {
           length "1 .. 63";
         }
       }
     }
   }
   grouping unified-edge-sgw-system {
     uses apply-advanced;
     container pfes {
       description "Packet forwarding engines used for anchoring";
       uses apply-advanced;
       list interface {
         key name;
         ordered-by user;
         description "Interface representing packet forwarding engine";
         leaf name {
           description "Interface name representing packet forwarding engine";
           type union {
             type jt:interface-unit;
             type string {
               pattern "<.*>|$.*";
             }
           }
         }
         uses apply-advanced;
         leaf service-mode {
           description "Service mode";
           type enumeration {
             enum "maintenance" {
               description "Maintenance mode";
             }
           }
         }
       }
     }
     container session-pics {
       description "Multiservice PICs used for anchoring control sessions";
       uses apply-advanced;
       list interface {
         key name;
         ordered-by user;
         description "Interface representing multiservice PIC";
         leaf name {
           description "Interface name representing multiservice PIC";
           type union {
             type jt:interface-unit;
             type string {
               pattern "<.*>|$.*";
             }
           }
         }
         uses apply-advanced;
         leaf service-mode {
           description "Service mode";
           type enumeration {
             enum "maintenance" {
               description "Maintenance mode";
             }
           }
         }
       }
     }
   }
   grouping unified-edge-tdf {
     description "Traffic Detection Function configuration";
     leaf name {
       description "TDF name";
       type string {
         length "1 .. 63";
       }
     }
     uses apply-advanced;
     leaf service-mode {
       description "Service mode";
       type enumeration {
         enum "maintenance" {
           description "Maintenance mode";
         }
       }
     }
     container system {
       description "System parameters";
       uses unified-edge-tdf-system;
     }
     container call-rate-statistics {
       presence "enable call-rate-statistics";
       description "Call-rate-statistics options";
       uses apply-advanced;
       leaf interval {
         description "Time interval in minutes";
         default "60";
         units "minutes";
         type union {
           type string {
             pattern "<.*>|$.*";
           }
           type uint32 {
             range "5 .. 120";
           }
         }
       }
       leaf history {
         description "Number of intervals";
         default "1";
         type union {
           type string {
             pattern "<.*>|$.*";
           }
           type uint32 {
             range "1 .. 10";
           }
         }
       }
     }
     container traceoptions {
       description "Trace options related to subscriber management";
       uses mobile-smd-traceoptions;
     }
     container cac {
       presence "enable cac";
       description "TDF cac configuration";
       uses apply-advanced;
       leaf maximum-subscribers {
         description "Maximum number of TDF subscribers";
         default "5000";
         units "thousands";
         type union {
           type string {
             pattern "<.*>|$.*";
           }
           type uint32 {
             range "10 .. 5000";
           }
         }
       }
       leaf maximum-subscribers-trap-percentage {
         description "Percentage of Maximum subscribers";
         default "70";
         units "percentage";
         type union {
           type string {
             pattern "<.*>|$.*";
           }
           type uint32 {
             range "1 .. 90";
           }
         }
       }
       container memory {
         description "Memory threshold configuration";
         uses apply-advanced;
         leaf percentage {
           description "Memory threshold";
           units "Percentage";
           type union {
             type string {
               pattern "<.*>|$.*";
             }
             type uint32 {
               range "1 .. 90";
             }
           }
         }
       }
       container cpu {
         description "CPU threshold configuration";
         uses apply-advanced;
         leaf percentage {
           description "CPU threshold";
           units "Percentage";
           type union {
             type string {
               pattern "<.*>|$.*";
             }
             type uint32 {
               range "1 .. 90";
             }
           }
         }
       }
     }
     container charging {
       presence "enable charging";
       description "TDF charging profile definitions";
       uses apply-advanced;
       container traceoptions {
         description "Charging trace options";
         uses charging-traceoptions;
       }
       container charging-profiles {
         description "Charging profile";
         uses apply-advanced;
         list charging-profile {
           key name;
           max-elements 255;
           uses juniper-charging-profiles;
         }
       }
       container transport-profiles {
         description "Transport profile definition";
         uses apply-advanced;
         list transport-profile {
           key name;
           max-elements 8;
           uses juniper-transport-profiles;
         }
       }
     }
     container domains {
       description "TDF domains configuration";
       uses apply-advanced;
       list domain {
         key name;
         max-elements 128;
         uses tdf-domain;
       }
     }
     container domain-selection {
       description "TDF domain selection";
       uses apply-advanced;
       list term {
         key name;
         ordered-by user;
         description "Define a domain selection term";
         max-elements 200;
         leaf name {
           description "Term name";
           type string {
             length "1 .. 50";
           }
         }
         uses apply-advanced;
         container from {
           description "Define match criteria";
           uses domain-sel-match-object;
         }
         container then {
           description "Action to take if the 'from' condition is matched";
           uses apply-advanced;
           leaf domain {
             description "TDF domain name";
             junos:must "(!(\"unified-edge gateways tdf ${tdf} domains $$ subscriber-type ifl\"))";
             junos:must-message "Referenced domain must be defined as ip-subscriber";
             junos:must "(\"unified-edge gateways tdf ${tdf} domains $$\")";
             junos:must-message "Referenced domain must be defined";
             type string {
               length "1 .. 50";
             }
           }
           leaf pcef-profile {
             description "PCEF profile name";
             junos:must "(\"unified-edge pcef profiles $$\")";
             junos:must-message "Referenced pcef profile must be defined";
             type string {
               length "1 .. 63";
             }
           }
         }
       }
     }
     container aaa {
       description "AAA related configuration";
       uses apply-advanced;
       container clients {
         description "AAA radius clients";
         uses apply-advanced;
         list client {
           key name;
           ordered-by user;
           description "AAA radius client";
           leaf name {
             description "Name of the radius client";
             junos:must "(\"access radius clients $$\")";
             junos:must-message "Referenced Radius client must be defined";
             type string {
               length "1 .. 31";
             }
           }
           uses apply-advanced;
         }
       }
       container snoop-segments {
         description "AAA radius snoop segments";
         uses apply-advanced;
         list snoop-segment {
           key name;
           ordered-by user;
           description "AAA radius snoop segment";
           leaf name {
             description "Name of Radius snoop segment";
             junos:must "(\"access radius snoop-segments $$\")";
             junos:must-message "Referenced Radius snoop-segment must be defined";
             type string {
               length "1 .. 32";
             }
           }
           uses apply-advanced;
         }
       }
     }
   }
   grouping domain-sel-match-object {
     description "TDF domain selection match";
     uses apply-advanced;
     list client {
       key name;
       ordered-by user;
       description "AAA Radius client";
       max-elements 5;
       leaf name {
         description "Name of the Radius client";
         junos:must "(\"access radius clients $$\")";
         junos:must-message "Referenced Radius client must be defined";
         type string {
           length "1 .. 31";
         }
       }
       uses apply-advanced;
     }
     list snoop-segment {
       key name;
       ordered-by user;
       description "AAA Radius snoop-segment";
       max-elements 5;
       leaf name {
         description "Name of Radius snoop-segment";
         junos:must "(\"access radius snoop-segments $$\")";
         junos:must-message "Referenced Radius snoop-segment must be defined";
         type string {
           length "1 .. 32";
         }
       }
       uses apply-advanced;
     }
     container user-name {
       description "Radius avp user-name";
       choice match_choice {
         case case_1 {
           container equals {
             description "Attribute match options";
             uses apply-advanced;
             leaf value {
               description "String value";
               type string {
                 length "1 .. 254";
               }
             }
           }
         }
         case case_2 {
           container has-prefix {
             description "Attribute match options";
             uses apply-advanced;
             leaf value {
               description "String value";
               type string {
                 length "1 .. 254";
               }
             }
           }
         }
         case case_3 {
           container has-suffix {
             description "Attribute match options";
             uses apply-advanced;
             leaf value {
               description "String value";
               type string {
                 length "1 .. 254";
               }
             }
           }
         }
         case case_4 {
           container matches {
             description "Attribute match options";
             uses apply-advanced;
             leaf value {
               description "String value";
               type string {
                 length "1 .. 254";
               }
             }
           }
         }
       }
     }
     container nas-ip-address {
       description "Radius avp nas-ip-address";
       container equals {
         description "Attribute match options";
         uses apply-advanced;
         leaf value {
           description "IPv4 address/prefix value";
           type jt:ipv4prefix;
         }
       }
     }
     container calling-station-id {
       description "Radius avp calling-station-id";
       choice match_choice {
         case case_1 {
           container equals {
             description "Attribute match options";
             uses apply-advanced;
             leaf value {
               description "String value";
               type string {
                 length "1 .. 254";
               }
             }
           }
         }
         case case_2 {
           container has-prefix {
             description "Attribute match options";
             uses apply-advanced;
             leaf value {
               description "String value";
               type string {
                 length "1 .. 254";
               }
             }
           }
         }
         case case_3 {
           container has-suffix {
             description "Attribute match options";
             uses apply-advanced;
             leaf value {
               description "String value";
               type string {
                 length "1 .. 254";
               }
             }
           }
         }
         case case_4 {
           container matches {
             description "Attribute match options";
             uses apply-advanced;
             leaf value {
               description "String value";
               type string {
                 length "1 .. 254";
               }
             }
           }
         }
       }
     }
     container called-station-id {
       description "Radius avp called-station-id";
       choice match_choice {
         case case_1 {
           container equals {
             description "Attribute match options";
             uses apply-advanced;
             leaf value {
               description "String value";
               type string {
                 length "1 .. 254";
               }
             }
           }
         }
         case case_2 {
           container has-prefix {
             description "Attribute match options";
             uses apply-advanced;
             leaf value {
               description "String value";
               type string {
                 length "1 .. 254";
               }
             }
           }
         }
         case case_3 {
           container has-suffix {
             description "Attribute match options";
             uses apply-advanced;
             leaf value {
               description "String value";
               type string {
                 length "1 .. 254";
               }
             }
           }
         }
         case case_4 {
           container matches {
             description "Attribute match options";
             uses apply-advanced;
             leaf value {
               description "String value";
               type string {
                 length "1 .. 254";
               }
             }
           }
         }
       }
     }
     container class {
       description "Radius avp class";
       choice match_choice {
         case case_1 {
           container equals {
             description "Attribute match options";
             uses apply-advanced;
             leaf value {
               description "String value";
               type string {
                 length "1 .. 254";
               }
             }
           }
         }
         case case_2 {
           container has-prefix {
             description "Attribute match options";
             uses apply-advanced;
             leaf value {
               description "String value";
               type string {
                 length "1 .. 254";
               }
             }
           }
         }
         case case_3 {
           container has-suffix {
             description "Attribute match options";
             uses apply-advanced;
             leaf value {
               description "String value";
               type string {
                 length "1 .. 254";
               }
             }
           }
         }
         case case_4 {
           container matches {
             description "Attribute match options";
             uses apply-advanced;
             leaf value {
               description "String value";
               type string {
                 length "1 .. 254";
               }
             }
           }
         }
       }
     }
     container threegpp-imsi {
       description "Radius avp 3gpp-imsi";
       choice match_choice {
         case case_1 {
           container equals {
             description "Attribute match options";
             uses apply-advanced;
             leaf value {
               description "String value";
               type string {
                 length "1 .. 254";
               }
             }
           }
         }
         case case_2 {
           container has-prefix {
             description "Attribute match options";
             uses apply-advanced;
             leaf value {
               description "String value";
               type string {
                 length "1 .. 254";
               }
             }
           }
         }
         case case_3 {
           container has-suffix {
             description "Attribute match options";
             uses apply-advanced;
             leaf value {
               description "String value";
               type string {
                 length "1 .. 254";
               }
             }
           }
         }
         case case_4 {
           container matches {
             description "Attribute match options";
             uses apply-advanced;
             leaf value {
               description "String value";
               type string {
                 length "1 .. 254";
               }
             }
           }
         }
       }
     }
     container framed-ip-address {
       description "Radius avp framed-ip-address";
       container equals {
         description "Attribute match options";
         uses apply-advanced;
         leaf value {
           description "IPv4 address/prefix value";
           type jt:ipv4prefix;
         }
       }
     }
     container framed-ipv6-prefix {
       description "Radius avp framed-ipv6-prefix";
       container equals {
         description "Attribute match options";
         uses apply-advanced;
         leaf value {
           description "IPv6 address/prefix value";
           type jt:ipv6prefix;
         }
       }
     }
     list attribute {
       key name;
       ordered-by user;
       description "Custom radius attributes";
       max-elements 5;
       leaf name {
         description "Custom attribute name";
         type string {
           length "1 .. 50";
         }
       }
       uses apply-advanced;
       leaf code {
         description "Attribute code";
         type union {
           type string {
             pattern "<.*>|$.*";
           }
           type uint8 {
             range "0 .. 255";
           }
         }
       }
       leaf vendor-id {
         description "Attribute vendor-id";
         default "0";
         type union {
           type string {
             pattern "<.*>|$.*";
           }
           type uint32 {
             range "0 .. 65534";
           }
         }
       }
       container format {
         description "Attribute format";
         choice format_choice {
           case case_1 {
             container string {
               description "Format string";
               uses apply-advanced;
               choice match_choice {
                 case case_1 {
                   container equals {
                     description "Attribute match options";
                     uses apply-advanced;
                     leaf value {
                       description "String value";
                       type string {
                         length "1 .. 254";
                       }
                     }
                   }
                 }
                 case case_2 {
                   container has-prefix {
                     description "Attribute match options";
                     uses apply-advanced;
                     leaf value {
                       description "String value";
                       type string {
                         length "1 .. 254";
                       }
                     }
                   }
                 }
                 case case_3 {
                   container has-suffix {
                     description "Attribute match options";
                     uses apply-advanced;
                     leaf value {
                       description "String value";
                       type string {
                         length "1 .. 254";
                       }
                     }
                   }
                 }
                 case case_4 {
                   container matches {
                     description "Attribute match options";
                     uses apply-advanced;
                     leaf value {
                       description "String value";
                       type string {
                         length "1 .. 254";
                       }
                     }
                   }
                 }
               }
             }
           }
           case case_2 {
             container time {
               description "Format time";
               uses apply-advanced;
               choice match_choice {
                 case case_1 {
                   container equals {
                     description "Attribute match options";
                     uses apply-advanced;
                     leaf value {
                       description "Time value";
                       type jt:time;
                     }
                   }
                 }
                 case case_2 {
                   container greater-than {
                     description "Attribute match options";
                     uses apply-advanced;
                     leaf value {
                       description "Time value";
                       type jt:time;
                     }
                   }
                 }
                 case case_3 {
                   container less-than {
                     description "Attribute match options";
                     uses apply-advanced;
                     leaf value {
                       description "Time value";
                       type jt:time;
                     }
                   }
                 }
               }
             }
           }
           case case_3 {
             container integer {
               description "Format integer";
               uses apply-advanced;
               choice match_choice {
                 case case_1 {
                   container equals {
                     description "Attribute match options";
                     uses apply-advanced;
                     leaf value {
                       description "Integer value";
                       type union {
                         type int32;
                         type string {
                           pattern "<.*>|$.*";
                         }
                       }
                     }
                   }
                 }
                 case case_2 {
                   container greater-than {
                     description "Attribute match options";
                     uses apply-advanced;
                     leaf value {
                       description "Integer value";
                       type union {
                         type int32;
                         type string {
                           pattern "<.*>|$.*";
                         }
                       }
                     }
                   }
                 }
                 case case_3 {
                   container less-than {
                     description "Attribute match options";
                     uses apply-advanced;
                     leaf value {
                       description "Integer value";
                       type union {
                         type int32;
                         type string {
                           pattern "<.*>|$.*";
                         }
                       }
                     }
                   }
                 }
               }
             }
           }
           case case_4 {
             container v4address {
               description "Format v4address";
               uses apply-advanced;
               container equals {
                 description "Attribute match options";
                 uses apply-advanced;
                 leaf value {
                   description "IPv4 address/prefix value";
                   type jt:ipv4prefix;
                 }
               }
             }
           }
           case case_5 {
             container v6prefix {
               description "Format v6prefix";
               uses apply-advanced;
               container equals {
                 description "Attribute match options";
                 uses apply-advanced;
                 leaf value {
                   description "IPv6 address/prefix value";
                   type jt:ipv6prefix;
                 }
               }
             }
           }
           case case_6 {
             container v6address {
               description "Format v6address";
               uses apply-advanced;
               container equals {
                 description "Attribute match options";
                 uses apply-advanced;
                 leaf value {
                   description "IPv6 address/prefix value";
                   type jt:ipv6prefix;
                 }
               }
             }
           }
         }
       }
     }
   }
   grouping tdf-domain {
     description "Configure domain for tdf gateway";
     leaf name {
       description "TDF domain name";
       type string {
         length "1 .. 50";
       }
     }
     uses apply-advanced;
     leaf subscriber-type {
       description "Specify subscriber type";
       default "ip";
       type enumeration {
         enum "ip" {
           description "Subscriber type IP";
         }
         enum "ifl" {
           description "Subscriber type IFL";
         }
       }
     }
     container subscriber-exclude-prefix {
       description "Exclude subscriber address prefix";
       uses apply-advanced;
       container family {
         description "Address family";
         uses apply-advanced;
         container inet {
           description "IPv4 address configuration";
           uses apply-advanced;
           list network {
             key name;
             ordered-by user;
             description "Specify IPv4 network prefix";
             max-elements 8;
             leaf name {
               description "IPv4 network prefix";
               type jt:ipv4prefix-only;
             }
             uses apply-advanced;
           }
         }
         container inet6 {
           description "IPv6 address pool configuration";
           uses apply-advanced;
           list network {
             key name;
             ordered-by user;
             description "Specify IPv6 network prefix";
             max-elements 8;
             leaf name {
               description "IPv6 network prefix";
               type jt:ipv6prefix-only;
             }
             uses apply-advanced;
           }
         }
       }
     }
     leaf pcef-profile {
       description "PCEF profile for the TDF domain";
       junos:must "(\"unified-edge pcef profiles $$\")";
       junos:must-message "Referenced PCEF profile must be defined";
       type string {
         length "1 .. 63";
       }
     }
     leaf tdf-interface {
       description "TDF interface";
       junos:must "((\"interfaces $$-IFL family inet service\" || \"interfaces $$-IFL family inet6 service\"))";
       junos:must-message "service set must be defined for the tdf-interface";
       junos:must "(\"interfaces $$\")";
       junos:must-message "referenced mif interface must be defined";
       type union {
         type jt:interface-unit;
         type string {
           pattern "<.*>|$.*";
         }
       }
     }
     container maximum-bit-rate {
       presence "enable maximum-bit-rate";
       description "Default subscriber policy for TDF traffic";
       uses apply-advanced;
       leaf uplink {
         description "Maximum bit rate uplink";
         default "0";
         units "kilobits";
         type union {
           type string {
             pattern "<.*>|$.*";
           }
           type uint32 {
             range "0 .. 6144000";
           }
         }
       }
       leaf downlink {
         description "Maximum bit rate downlink";
         default "0";
         units "kilobits";
         type union {
           type string {
             pattern "<.*>|$.*";
           }
           type uint32 {
             range "0 .. 6144000";
           }
         }
       }
     }
     container burst-size {
       presence "enable burst-size";
       description "Default Subscriber Burst Size for TDF traffic";
       uses apply-advanced;
       leaf uplink {
         description "Subscriber burst size uplink";
         default "1500";
         units "bytes";
         type union {
           type string {
             pattern "<.*>|$.*";
           }
           type uint32 {
             range "1500 .. 1500000000";
           }
         }
       }
       leaf downlink {
         description "Subscriber burst size downlink";
         default "1500";
         units "bytes";
         type union {
           type string {
             pattern "<.*>|$.*";
           }
           type uint32 {
             range "1500 .. 1500000000";
           }
         }
       }
     }
     leaf charging-profile {
       description "Charging profile for the domain";
       junos:must "(\"unified-edge gateways tdf ${tdf} charging charging-profiles $$\")";
       junos:must-message "Charging profile must be defined";
       type string;
     }
     leaf service-mode {
       description "Service mode";
       type enumeration {
         enum "maintenance" {
           description "Maintenance mode";
         }
       }
     }
     container call-rate-statistics {
       presence "enable call-rate-statistics";
       description "Call-rate-statistics options";
       uses apply-advanced;
       leaf interval {
         description "Time interval in minutes";
         default "60";
         units "minutes";
         type union {
           type string {
             pattern "<.*>|$.*";
           }
           type uint32 {
             range "5 .. 120";
           }
         }
       }
       leaf history {
         description "Number of intervals";
         default "1";
         type union {
           type string {
             pattern "<.*>|$.*";
           }
           type uint32 {
             range "1 .. 10";
           }
         }
       }
     }
     container ip-subscriber {
       description "Configure ip subscriber";
       uses apply-advanced;
       list access-interfaces {
         key name;
         ordered-by user;
         description "Access facing interfaces";
         max-elements 16;
         leaf name {
           description "Interface name";
           junos:must "(\"interfaces $$\")";
           junos:must-message "interface must be defined";
           type union {
             type jt:interface-name;
             type string {
               pattern "<.*>|$.*";
             }
           }
         }
         uses apply-advanced;
       }
       leaf subscriber-attach-method {
         description "Specify subscriber attach method";
         type enumeration {
           enum "radius-accounting" {
             description "Attached by RADIUS accounting messages";
           }
           enum "packet-triggered" {
             description "Attached by data packet";
           }
           enum "pcrf-initiated" {
             description "Attached by PCRF initiation";
           }
         }
       }
       container subscription-id {
         description "Specify subscription id options";
         uses apply-advanced;
         list subscription-id-options {
           key name;
           ordered-by user;
           description "Subscription id options sets";
           max-elements 6;
           uses subscription-id-set;
         }
         container constant {
           description "Constant string for subscription-id";
           leaf constant-value {
             description "Constant string";
             type string {
               length "1 .. 128";
             }
           }
         }
         leaf use-class-regular-expression {
           description "Regular expression for Class attribute parsing";
           status deprecated;
           junos:must "(!(\".. use-class\"))";
           junos:must-message "use-class-regular-expression is deprecated; use use-class regex";
           junos:must "(any \".. subscription-id-options <*> id-components use-class\")";
           junos:must-message "use subscription-id-options";
           type string {
             length "1 .. 64";
           }
         }
         container use-class {
           uses apply-advanced;
           leaf regex {
             description "Regular expression for Class attribute parsing";
             junos:must "(any \".. .. subscription-id-options <*> id-components use-class\")";
             junos:must-message "id-components must contain use-class";
             type string {
               length "1 .. 64";
             }
           }
           leaf pattern {
             description "Substitution template to use with regular expression";
             junos:must "(\".. regex\")";
             junos:must-message "Substitution works with regular expression";
             type string {
               length "1 .. 64";
             }
           }
           leaf subscription-id-type {
             description "Subscription id type";
             type enumeration {
               enum "imsi" {
                 description "Use as IMSI subscriber type";
               }
               enum "msisdn" {
                 description "Use as MSISDN (E164) subscriber type";
               }
               enum "nai" {
                 description "Use as NAI subscriber type";
               }
               enum "sip-uri" {
                 description "Use as SIP URI name subscriber type";
               }
               enum "private" {
                 description "Use as private subscriber type";
               }
             }
           }
         }
       }
       leaf immediate-accounting-response {
         description "Enable/disable immediate RADIUS response message";
         type enumeration {
           enum "enable" {
             description "Enable immediate RADIUS accounting response";
           }
           enum "disable" {
             description "Disable immediate RADIUS accounting response";
           }
         }
       }
       container subscriber-address {
         description "Specify the subscriber address information";
         uses apply-advanced;
         container inet {
           description "Specify address pool name for IPv4";
           uses apply-advanced;
           leaf pool {
             type string {
               length "1 .. 64";
             }
           }
         }
         container inet6 {
           description "Specify address pool name for IPv6";
           uses apply-advanced;
           leaf pool {
             type string {
               length "1 .. 64";
             }
           }
         }
       }
       leaf maximum-subscribers {
         description "Maximum TDF subscribers";
         units "in thousands";
         type union {
           type string {
             pattern "<.*>|$.*";
           }
           type uint32 {
             range "10 .. 5000";
           }
         }
       }
       leaf idle-timeout {
         description "Session idle timeout value";
         units "minutes";
         type union {
           type string {
             pattern "<.*>|$.*";
           }
           type uint32 {
             range "0 .. 300";
           }
         }
       }
       container default-local-policy {
         presence "enable default-local-policy";
         description "Default local policy for TDF traffic";
         uses apply-advanced;
         leaf flow-action {
           description "Flow action";
           type enumeration {
             enum "forward" {
               description "Forward";
             }
             enum "drop" {
               description "Drop";
             }
           }
         }
         container maximum-bit-rate {
           presence "enable maximum-bit-rate";
           description "Maximum bit rate";
           leaf uplink {
             description "Maximum bit rate uplink";
             default "0";
             units "kilobits";
             type union {
               type string {
                 pattern "<.*>|$.*";
               }
               type uint32 {
                 range "0 .. 6144000";
               }
             }
           }
           leaf downlink {
             description "Maximum bit rate downlink";
             default "0";
             units "kilobits";
             type union {
               type string {
                 pattern "<.*>|$.*";
               }
               type uint32 {
                 range "0 .. 6144000";
               }
             }
           }
         }
         container burst-size {
           presence "enable burst-size";
           description "Burst Size for TDF traffic";
           uses apply-advanced;
           leaf uplink {
             description "Burst size uplink";
             default "1500";
             units "bytes";
             type union {
               type string {
                 pattern "<.*>|$.*";
               }
               type uint32 {
                 range "1500 .. 1500000000";
               }
             }
           }
           leaf downlink {
             description "Burst size downlink";
             default "1500";
             units "bytes";
             type union {
               type string {
                 pattern "<.*>|$.*";
               }
               type uint32 {
                 range "1500 .. 1500000000";
               }
             }
           }
         }
       }
     }
     container ifl-subscriber {
       description "IFL subscriber configuration";
       uses apply-advanced;
       list ifl-subscribers {
         key name;
         max-elements 32;
         uses tdf-ifl-subscriber;
       }
     }
   }
   grouping subscription-id-set {
     description "Specify subscription id set";
     leaf name {
       description "Subscription id set name";
       type string {
         length "1 .. 128";
       }
     }
     uses apply-advanced;
     leaf-list id-components {
       ordered-by user;
       description "Subscription id components";
       type enumeration {
         enum "use-imsi" {
           description "Use imsi for subscriber ID";
         }
         enum "use-msisdn" {
           description "Use msisdn for subscriber ID";
         }
         enum "use-nai" {
           description "Use nai for subscriber ID";
         }
         enum "use-username" {
           description "Use user name for subscriber ID";
         }
         enum "use-realm" {
           description "Use realm for subscriber ID";
         }
         enum "use-nas-port" {
           description "Use NAS port for subscriber ID";
         }
         enum "use-nas-port-id" {
           description "Use NAS port ID for subscriber ID";
         }
         enum "use-class" {
           description "Parse Class attribute to get subscriber ID";
         }
       }
     }
   }
   grouping tdf-ifl-subscriber {
     description "Configure ifl subscriber";
     leaf name {
       description "IFL subscriber name";
       type string {
         length "1 .. 64";
       }
     }
     uses apply-advanced;
     list access-interfaces {
       key name;
       ordered-by user;
       description "Access facing interfaces";
       max-elements 16;
       leaf name {
         description "Interface name";
         junos:must "(\"interfaces $$\")";
         junos:must-message "interface must be defined";
         type union {
           type jt:interface-name;
           type string {
             pattern "<.*>|$.*";
           }
         }
       }
       uses apply-advanced;
     }
   }
   grouping unified-edge-tdf-system {
     uses apply-advanced;
     container session-pics {
       description "Multiservice PICs used for anchoring control sessions";
       uses apply-advanced;
       list interface {
         key name;
         ordered-by user;
         description "Interface representing multiservice PIC";
         leaf name {
           description "Interface name representing multiservice PIC";
           type union {
             type jt:interface-unit;
             type string {
               pattern "<.*>|$.*";
             }
           }
         }
         uses apply-advanced;
         leaf service-mode {
           description "Service mode";
           type enumeration {
             enum "maintenance" {
               description "Maintenance mode";
             }
           }
         }
       }
     }
     container service-pics {
       presence "enable service-pics";
       description "Multiservice PICs used for anchoring service related data sessions";
       uses apply-advanced;
       list interface {
         key name;
         ordered-by user;
         description "Interface representing multiservice PIC";
         leaf name {
           description "Interface name representing multiservice PIC";
           type union {
             type jt:interface-unit;
             type string {
               pattern "<.*>|$.*";
             }
           }
         }
         uses apply-advanced;
         leaf service-mode {
           description "Service mode";
           type enumeration {
             enum "maintenance" {
               description "Maintenance mode";
             }
           }
         }
       }
     }
   }
 }
