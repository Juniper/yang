/*
 * Copyright (c) 2021 Juniper Networks, Inc.
 * All rights reserved.
 */
 module junos-nfx-conf-dialer {
   namespace "http://yang.juniper.net/junos-nfx/conf/dialer";

   prefix jc-dialer;

   import junos-common-ddl-extensions {
     prefix junos;
     revision-date 2019-01-01;
   }

   import junos-common-types {
     prefix jt;
     revision-date 2019-01-01;
   }

   import junos-nfx-conf-root {
     prefix jc;
     revision-date 2019-01-01;
   }

   organization "Juniper Networks, Inc.";

   contact "yang-support@juniper.net";

   description "Junos dialer configuration module";

   revision 2019-01-01 {
     description "Junos: 21.2R1.10";
   }

   augment /jc:configuration {
     uses dialer-group;
   }
   augment /jc:configuration/jc:groups {
     uses dialer-group;
   }
   grouping dialer-group {
     container dialer {
       description "Dialer services configuration";
       status deprecated;
       uses apply-advanced;
       container traceoptions {
         junos:must "(!((\"system processes dialer-services traceoptions\" && \"dialer traceoptions\")))";
         junos:must-message "Dialer traceoptions should be configured only under [system processes dialer-services]";
         description "Trace options for dialer services";
         uses apply-advanced;
         leaf no-remote-trace {
           description "Disable remote tracing";
           junos:must "(\"system tracing\")";
           junos:must-message "'no-remote-trace' is valid only when [system tracing] is configured";
           type empty;
         }
         container file {
           description "Trace file information";
           leaf filename {
             description "Name of file in which to write trace information";
             type string {
               length "1 .. 1024";
               junos:posix-pattern "![/ %]";
               junos:pattern-message "Must not contain '/', % or a space";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "One or more message or event types to include in trace";
           leaf name {
             type enumeration {
               enum "config" {
                 description "Dialer configuration messages";
               }
               enum "kernel" {
                 description "Messages from the kernel";
               }
               enum "route" {
                 description "Route and next-hop messages for dialer watch";
               }
               enum "interface" {
                 description "Interface-related events";
               }
               enum "error" {
                 description "Error messages";
               }
               enum "memory" {
                 description "Memory allocation or deallocation messages";
               }
               enum "all" {
                 description "All messages and events";
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
