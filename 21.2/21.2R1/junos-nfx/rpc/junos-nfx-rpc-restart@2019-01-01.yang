/*
 * Copyright (c) 2021 Juniper Networks, Inc.
 * All rights reserved.
 */
 module junos-nfx-rpc-restart {
   namespace "http://yang.juniper.net/junos-nfx/rpc/restart";

   prefix restart;

   import junos-common-types {
     prefix jt;
     revision-date 2019-01-01;
   }

   organization "Juniper Networks, Inc.";

   contact "yang-support@juniper.net";

   description "Junos RPC YANG module for restart command(s)";

   revision 2019-01-01 {
     description "Junos: 21.2R1.10";
   }

   rpc restart-daemon {
     description "Restart software process";
     input {
       uses command-forwarding;
       leaf daemon-name {
         type string;
         mandatory true;
       }
       leaf how-to-reset {
         default "gracefully";
         type enumeration {
           enum "gracefully" {
             description "Gracefully restart the process";
           }
           enum "soft" {
             description "Soft reset (SIGHUP) the process";
           }
           enum "immediately" {
             description "Immediately restart (SIGKILL) the process";
           }
         }
       }
     }
     output {
       choice output_c {
         case output-tag {
           leaf output {
             type string;
           }
         }
         case multichassis-tag {
           anyxml multi-routing-engine-results;
         }
       }
     }
   }
   rpc routing-restart {
     description "Routing protocol process";
     input {
       uses command-forwarding;
       leaf how-to-reset {
         default "gracefully";
         type enumeration {
           enum "gracefully" {
             description "Gracefully restart the process";
           }
           enum "soft" {
             description "Soft reset (SIGHUP) the process";
           }
           enum "immediately" {
             description "Immediately restart (SIGKILL) the process";
           }
         }
       }
     }
     output {
       choice output_c {
         case output-tag {
           leaf output {
             type string;
           }
         }
         case multichassis-tag {
           anyxml multi-routing-engine-results;
         }
       }
     }
   }
   rpc restart-kernel-replication {
     description "Kernel replication process";
     input {
       uses command-forwarding;
       leaf how-to-reset {
         default "gracefully";
         type enumeration {
           enum "gracefully" {
             description "Gracefully restart the process";
           }
           enum "soft" {
             description "Soft reset (SIGHUP) the process";
           }
           enum "immediately" {
             description "Immediately restart (SIGKILL) the process";
           }
         }
       }
     }
     output {
       choice output_c {
         case output-tag {
           leaf output {
             type string;
           }
         }
         case actual-tag {
           anyxml restart-kernel-replication;
         }
         case multichassis-tag {
           anyxml multi-routing-engine-results;
         }
       }
     }
   }
   rpc restart-web-management {
     description "Web management process";
     output {
       choice output_c {
         case output-tag {
           leaf output {
             type string;
           }
         }
         case multichassis-tag {
           anyxml multi-routing-engine-results;
         }
       }
     }
   }
   rpc restart-named-service {
     description "DNS server process";
     output {
       choice output_c {
         case output-tag {
           leaf output {
             type string;
           }
         }
         case multichassis-tag {
           anyxml multi-routing-engine-results;
         }
       }
     }
   }
   rpc restart-jdmd {
     description "Juniper Device Manager service process";
     input {
       leaf how-to-reset {
         default "gracefully";
         type enumeration {
           enum "gracefully" {
             description "Gracefully restart the process";
           }
           enum "soft" {
             description "Soft reset (SIGHUP) the process";
           }
           enum "immediately" {
             description "Immediately restart (SIGKILL) the process";
           }
         }
       }
     }
     output {
       choice output_c {
         case output-tag {
           leaf output {
             type string;
           }
         }
         case multichassis-tag {
           anyxml multi-routing-engine-results;
         }
       }
     }
   }
   rpc restart-jinventoryd {
     description "Juniper Inventory Management Daemon";
     input {
       leaf how-to-reset {
         default "gracefully";
         type enumeration {
           enum "gracefully" {
             description "Gracefully restart the process";
           }
           enum "soft" {
             description "Soft reset (SIGHUP) the process";
           }
           enum "immediately" {
             description "Immediately restart (SIGKILL) the process";
           }
         }
       }
     }
     output {
       choice output_c {
         case output-tag {
           leaf output {
             type string;
           }
         }
         case multichassis-tag {
           anyxml multi-routing-engine-results;
         }
       }
     }
   }
   rpc jlinkmon-restart {
     description "Juniper link monitor daemon (runs on host)";
     output {
       choice output_c {
         case output-tag {
           leaf output {
             type string;
           }
         }
         case multichassis-tag {
           anyxml multi-routing-engine-results;
         }
       }
     }
   }
   rpc restart-ddns {
     description "Restart the dynamic DNS client";
     output {
       choice output_c {
         case output-tag {
           leaf output {
             type string;
           }
         }
         case multichassis-tag {
           anyxml multi-routing-engine-results;
         }
       }
     }
   }
   rpc restart-pgcp-service {
     description "Packet gateway service process";
     input {
       leaf gateway {
         description "Gateway name";
         type string;
         mandatory true;
       }
     }
     output {
       choice output_c {
         case output-tag {
           leaf output {
             type string;
           }
         }
         case actual-tag {
           anyxml restart-pgcp-service-information;
         }
         case multichassis-tag {
           anyxml multi-routing-engine-results;
         }
       }
     }
   }
   rpc restart-border-signaling-gateway-service {
     description "Border signaling gateway service process";
     input {
       leaf gateway {
         description "Name of border signaling gateway";
         type string;
         mandatory true;
       }
     }
     output {
       choice output_c {
         case output-tag {
           leaf output {
             type string;
           }
         }
         case actual-tag {
           anyxml restart-bsg-service-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
