/*
 * Copyright (c) 2021 Juniper Networks, Inc.
 * All rights reserved.
 */
 module junos-ex-conf-services {
   namespace "http://yang.juniper.net/junos-ex/conf/services";

   prefix jc-services;

   import junos-common-types {
     prefix jt;
     revision-date 2019-01-01;
   }

   import junos-ex-conf-root {
     prefix jc;
     revision-date 2019-01-01;
   }

   organization "Juniper Networks, Inc.";

   contact "yang-support@juniper.net";

   description "Junos services configuration module";

   revision 2019-01-01 {
     description "Junos: 21.2R1.10";
   }

   augment /jc:configuration {
     uses services-group;
   }
   augment /jc:configuration/jc:groups {
     uses services-group;
   }
   grouping services-group {
     container services {
       description "System services";
       uses apply-advanced;
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           type union {
             type jt:interface-name;
             type string {
               pattern "<.*>|$.*";
             }
           }
         }
         leaf tunnel-interface {
           description "Tunnel interface through which flow-tap would communicate with MD";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               type string;
             }
           }
           case case_2 {
             list logical-system {
               key name;
               ordered-by user;
               description "Logical system to be used for radius flow tap";
               max-elements 1;
               leaf name {
                 description "Logical system name";
                 type string;
               }
               uses apply-advanced;
               leaf routing-instance {
                 description "Routing instance to be used for radius flow tap";
                 type string;
               }
             }
           }
         }
         list policy {
           key name;
           ordered-by user;
           description "Policy";
           leaf name {
             description "Policy Name";
             type string {
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container mobile-flow-tap {
         description "Configure mobile triggered flow-tap parameters";
         uses apply-advanced;
         container source-interface {
           presence "enable source-interface";
           description "Source interface from which IRI packets will be sent";
           leaf interface-name {
             description "Interface name";
             type union {
               type jt:interface-name;
               type string {
                 pattern "<.*>|$.*";
               }
             }
           }
           leaf ipv4-address {
             description "Source IPv4 address to be used";
             type jt:ipv4addr;
           }
         }
       }
       container jdaf {
         description "Juniper distributed application framework (JDAF)";
         uses apply-advanced;
         leaf-list routing-instances {
           ordered-by user;
           description "List of routing-instance name for JDAF clients";
           type string {
             length "1 .. 128";
           }
         }
       }
       container rpm {
         presence "enable rpm";
         description "Real-time performance monitoring";
         uses apply-advanced;
         container traceoptions {
           description "RMOPD trace options";
           uses rmopd-traceoptions;
         }
         container bgp {
           description "BGP options for real-time performance monitoring";
           uses apply-advanced;
           leaf probe-type {
             description "RPM-BGP probe request type";
             default "icmp-ping";
             type enumeration {
               enum "icmp-ping" {
                 description "Send ICMP echo request to target address";
               }
               enum "icmp-ping-timestamp" {
                 description "Send ICMP timestamp request to target address";
               }
               enum "icmp6-ping" {
                 description "Send ICMP6 echo request to target address";
               }
               enum "tcp-ping" {
                 description "Send TCP packets to target";
               }
               enum "udp-ping" {
                 description "Send UDP packets to target";
               }
               enum "udp-ping-timestamp" {
                 description "Send UDP packets with timestamp to target";
               }
             }
           }
           leaf probe-count {
             description "Total number of probes per test";
             default "1";
             type union {
               type string {
                 pattern "<.*>|$.*";
               }
               type uint32 {
                 range "1 .. 15";
               }
             }
           }
           leaf probe-interval {
             description "Delay between probes";
             default "3";
             units "seconds";
             type union {
               type string {
                 pattern "<.*>|$.*";
               }
               type uint32 {
                 range "1 .. 255";
               }
             }
           }
           leaf test-interval {
             description "Delay between tests";
             default "1";
             units "seconds";
             type union {
               type string {
                 pattern "<.*>|$.*";
               }
               type uint32 {
                 range "0 .. 86400";
               }
             }
           }
           leaf destination-port {
             description "TCP/UDP port number";
             type union {
               type string {
                 pattern "<.*>|$.*";
               }
               type uint16 {
                 range "7 .. 65535";
               }
             }
           }
           leaf history-size {
             description "Number of stored history entries";
             default "50";
             type union {
               type string {
                 pattern "<.*>|$.*";
               }
               type uint32 {
                 range "0 .. 512";
               }
             }
           }
           leaf moving-average-size {
             description "Number of samples used for moving average";
             default "0";
             type union {
               type string {
                 pattern "<.*>|$.*";
               }
               type uint32 {
                 range "0 .. 1024";
               }
             }
           }
           leaf data-size {
             description "Size of the data portion of the probes";
             default "0";
             type union {
               type string {
                 pattern "<.*>|$.*";
               }
               type uint32 {
                 range "0 .. 65400";
               }
             }
           }
           leaf data-fill {
             description "Define contents of the data portion of the probes";
             type string {
               length "1 .. 2048";
             }
           }
           leaf ttl {
             description "Time to Live (hop-limit) value for an RPM IPv4(IPv6) packet";
             default "64";
             type union {
               type string {
                 pattern "<.*>|$.*";
               }
               type uint32 {
                 range "1 .. 254";
               }
             }
           }
           list logical-system {
             key name;
             description "Logical systems";
             uses bgp-logical-system;
           }
           list routing-instances {
             key name;
             description "Routing instances";
             uses bgp-routing-instances;
           }
         }
         list probe {
           key name;
           ordered-by user;
           description "TCP/UDP/ICMP ping";
           leaf name {
             description "Name of owner";
             type string {
               length "1 .. 32";
             }
           }
           uses apply-advanced;
           leaf delegate-probes {
             description "Offload real-time performance monitoring probes to MS-MIC/MS-MPC card";
             type empty;
           }
           list test {
             key name;
             ordered-by user;
             description "TCP/UDP/ICMP/ICMP6 ping test";
             leaf name {
               description "Name of test";
               type string {
                 length "1 .. 32";
               }
             }
             uses apply-advanced;
             container rpm-scale {
               presence "enable rpm-scale";
               description "Configuring real-time performance monitoring scale tests";
               uses apply-advanced;
               leaf tests-count {
                 description "Number of probe-tests generated using scale config";
                 type union {
                   type string {
                     pattern "<.*>|$.*";
                   }
                   type uint32 {
                     range "1 .. 500000";
                   }
                 }
               }
               choice target-type {
                 case case_1 {
                   container target {
                     presence "enable target";
                     description "Target address generation for scale test config";
                     uses apply-advanced;
                     leaf address-base {
                       description "Base address of target host in a.b.c.d format";
                       type jt:ipv4addr;
                     }
                     leaf step {
                       description "Steps to increment target address in a.b.c.d format";
                       type jt:ipv4addr;
                     }
                     leaf count {
                       description "Target address count";
                       type union {
                         type string {
                           pattern "<.*>|$.*";
                         }
                         type uint32 {
                           range "1 .. 500000";
                         }
                       }
                     }
                   }
                 }
                 case case_2 {
                   container target-inet6 {
                     presence "enable target-inet6";
                     description "IPv6 target address generation for scale test config";
                     uses apply-advanced;
                     leaf address-base {
                       description "Base address of target host in a:b:c:d:e:f:g:h format";
                       type jt:ipv6addr;
                     }
                     leaf step {
                       description "Steps to increment target address in a:b:c:d:e:f:g:h format";
                       type jt:ipv6addr;
                     }
                     leaf count {
                       description "Target address count";
                       type union {
                         type string {
                           pattern "<.*>|$.*";
                         }
                         type uint32 {
                           range "1 .. 500000";
                         }
                       }
                     }
                   }
                 }
               }
               choice source-type {
                 case case_1 {
                   container source {
                     presence "enable source";
                     description "Source address generation in scale tests";
                     uses apply-advanced;
                     leaf address-base {
                       description "Base address of host in a.b.c.d format";
                       type jt:ipv4addr;
                     }
                     leaf step {
                       description "Steps to increment src address in a.b.c.d format";
                       type jt:ipv4addr;
                     }
                     leaf count {
                       description "Source-address count";
                       type union {
                         type string {
                           pattern "<.*>|$.*";
                         }
                         type uint32 {
                           range "1 .. 500000";
                         }
                       }
                     }
                   }
                 }
                 case case_2 {
                   container source-inet6 {
                     presence "enable source-inet6";
                     description "IPv6 source address generation in scale tests";
                     uses apply-advanced;
                     leaf address-base {
                       description "Base address of host in a:b:c:d:e:f:g:h format";
                       type jt:ipv6addr;
                     }
                     leaf step {
                       description "Steps to increment src address in a:b:c:d:e:f:g:h format";
                       type jt:ipv6addr;
                     }
                     leaf count {
                       description "Source-address count";
                       type union {
                         type string {
                           pattern "<.*>|$.*";
                         }
                         type uint32 {
                           range "1 .. 500000";
                         }
                       }
                     }
                   }
                 }
               }
               container destination {
                 presence "enable destination";
                 description "Name of output interface for probes";
                 uses apply-advanced;
                 leaf interface {
                   description "Base destination interface for scale test";
                   type union {
                     type jt:interface-name;
                     type string {
                       pattern "<.*>|$.*";
                     }
                   }
                 }
                 leaf subunit-cnt {
                   description "Subunit count for destination interface for scale test";
                   type union {
                     type string {
                       pattern "<.*>|$.*";
                     }
                     type uint32 {
                       range "1 .. 500000";
                     }
                   }
                 }
               }
             }
             leaf probe-type {
               description "Probe request type";
               default "icmp-ping";
               type enumeration {
                 enum "http-get" {
                   description "Perform HTTP Get request at target URL";
                 }
                 enum "http-metadata-get" {
                   description "Perform HTTP Get request of metadata at target URL";
                 }
                 enum "icmp-ping" {
                   description "Send ICMP echo request to target address";
                 }
                 enum "icmp-ping-timestamp" {
                   description "Send ICMP timestamp request to target address";
                 }
                 enum "icmp6-ping" {
                   description "Send ICMP6 echo request to target address";
                 }
                 enum "tcp-ping" {
                   description "Send TCP packets to target";
                 }
                 enum "udp-ping" {
                   description "Send UDP packets to target";
                 }
                 enum "udp-ping-timestamp" {
                   description "Send UDP packets with timestamp to target";
                 }
               }
             }
             container target {
               presence "enable target";
               description "Target destination for probe";
               choice target-type {
                 case case_1 {
                   leaf address {
                     description "Address of target host";
                     type jt:ipv4addr;
                   }
                 }
                 case case_2 {
                   leaf inet6-address {
                     description "Inet6 Address of target host";
                     type jt:ipv6addr;
                   }
                 }
                 case case_3 {
                   leaf url {
                     description "Fully formed target URL";
                     type string;
                   }
                 }
                 case case_4 {
                   leaf inet6-url {
                     description "Fully formed target IPV6 URL";
                     type string;
                   }
                 }
               }
             }
             container inet6-options {
               presence "enable inet6-options";
               description "IPV6 related options";
               uses apply-advanced;
               leaf source-address {
                 description "Inet6 Source Address of the probe";
                 type jt:ipv6addr;
               }
             }
             leaf probe-count {
               description "Total number of probes per test";
               default "1";
               type union {
                 type string {
                   pattern "<.*>|$.*";
                 }
                 type uint32 {
                   range "1 .. 15";
                 }
               }
             }
             leaf probe-interval {
               description "Delay between probes";
               default "3";
               units "seconds";
               type union {
                 type string {
                   pattern "<.*>|$.*";
                 }
                 type uint32 {
                   range "1 .. 255";
                 }
               }
             }
             leaf test-interval {
               description "Delay between tests";
               default "1";
               units "seconds";
               type union {
                 type string {
                   pattern "<.*>|$.*";
                 }
                 type uint32 {
                   range "0 .. 86400";
                 }
               }
             }
             leaf destination-port {
               description "TCP/UDP port number";
               type union {
                 type string {
                   pattern "<.*>|$.*";
                 }
                 type uint16 {
                   range "7 .. 65535";
                 }
               }
             }
             leaf source-address {
               description "Source address for probe";
               type jt:ipv4addr;
             }
             leaf routing-instance {
               description "Routing instance used by probes";
               type string {
               }
             }
             leaf history-size {
               description "Number of stored history entries";
               default "50";
               type union {
                 type string {
                   pattern "<.*>|$.*";
                 }
                 type uint32 {
                   range "0 .. 512";
                 }
               }
             }
             leaf moving-average-size {
               description "Number of samples used for moving average";
               default "0";
               type union {
                 type string {
                   pattern "<.*>|$.*";
                 }
                 type uint32 {
                   range "0 .. 1024";
                 }
               }
             }
             leaf dscp-code-points {
               description "Differentiated Services code point bits or alias";
               default "000000";
               type string {
               }
             }
             leaf data-size {
               description "Size of the data portion of the probes";
               default "0";
               type union {
                 type string {
                   pattern "<.*>|$.*";
                 }
                 type uint32 {
                   range "0 .. 65400";
                 }
               }
             }
             leaf data-fill {
               description "Define contents of the data portion of the probes";
               type string {
                 length "1 .. 2048";
               }
             }
             leaf ttl {
               description "Time to Live (hop-limit) value for an RPM IPv4(IPv6) packet";
               default "64";
               type union {
                 type string {
                   pattern "<.*>|$.*";
                 }
                 type uint32 {
                   range "1 .. 254";
                 }
               }
             }
             container thresholds {
               presence "enable thresholds";
               description "Probe and test threshold values. Set 0 to disable respective threshold";
               uses apply-advanced;
               leaf successive-loss {
                 description "Successive probe loss count indicating probe failure";
                 default "1";
                 type union {
                   type string {
                     pattern "<.*>|$.*";
                   }
                   type uint32 {
                     range "0 .. 15";
                   }
                 }
               }
               leaf total-loss {
                 description "Total probe loss count indicating test failure";
                 default "1";
                 type union {
                   type string {
                     pattern "<.*>|$.*";
                   }
                   type uint32 {
                     range "0 .. 15";
                   }
                 }
               }
               leaf rtt {
                 description "Maximum round trip time per probe";
                 default "0";
                 units "microseconds";
                 type union {
                   type string {
                     pattern "<.*>|$.*";
                   }
                   type uint32 {
                     range "0 .. 60000000";
                   }
                 }
               }
               leaf jitter-rtt {
                 description "Maximum jitter per test";
                 default "0";
                 units "microseconds";
                 type union {
                   type string {
                     pattern "<.*>|$.*";
                   }
                   type uint32 {
                     range "0 .. 60000000";
                   }
                 }
               }
               leaf std-dev-rtt {
                 description "Maximum standard deviation per test";
                 default "0";
                 units "microseconds";
                 type union {
                   type string {
                     pattern "<.*>|$.*";
                   }
                   type uint32 {
                     range "0 .. 60000000";
                   }
                 }
               }
               leaf egress-time {
                 description "Maximum source to destination time per probe";
                 default "0";
                 units "microseconds";
                 type union {
                   type string {
                     pattern "<.*>|$.*";
                   }
                   type uint32 {
                     range "0 .. 60000000";
                   }
                 }
               }
               leaf ingress-time {
                 description "Maximum destination to source time per probe";
                 default "0";
                 units "microseconds";
                 type union {
                   type string {
                     pattern "<.*>|$.*";
                   }
                   type uint32 {
                     range "0 .. 60000000";
                   }
                 }
               }
               leaf jitter-ingress {
                 description "Maximum destination to source jitter per test";
                 default "0";
                 units "microseconds";
                 type union {
                   type string {
                     pattern "<.*>|$.*";
                   }
                   type uint32 {
                     range "0 .. 60000000";
                   }
                 }
               }
               leaf jitter-egress {
                 description "Maximum source to destination jitter per test";
                 default "0";
                 units "microseconds";
                 type union {
                   type string {
                     pattern "<.*>|$.*";
                   }
                   type uint32 {
                     range "0 .. 60000000";
                   }
                 }
               }
               leaf std-dev-ingress {
                 description "Maximum destination to source standard deviation per test";
                 default "0";
                 units "microseconds";
                 type union {
                   type string {
                     pattern "<.*>|$.*";
                   }
                   type uint32 {
                     range "0 .. 60000000";
                   }
                 }
               }
               leaf std-dev-egress {
                 description "Maximum source to destination standard deviation per test";
                 default "0";
                 units "microseconds";
                 type union {
                   type string {
                     pattern "<.*>|$.*";
                   }
                   type uint32 {
                     range "0 .. 60000000";
                   }
                 }
               }
             }
             leaf-list traps {
               ordered-by user;
               description "Trap to send if threshold is met or exceeded";
               type enumeration {
                 enum "probe-failure" {
                   description "Successive probe loss threshold reached";
                 }
                 enum "test-failure" {
                   description "Total probe loss threshold reached";
                 }
                 enum "test-completion" {
                   description "Test completed";
                 }
                 enum "rtt-exceeded" {
                   description "Exceeded maximum round trip time threshold";
                 }
                 enum "std-dev-exceeded" {
                   description "Exceeded round trip time standard deviation threshold";
                 }
                 enum "jitter-exceeded" {
                   description "Exceeded jitter in round trip time threshold";
                 }
                 enum "ingress-time-exceeded" {
                   description "Exceeded maximum ingress time threshold";
                 }
                 enum "ingress-std-dev-exceeded" {
                   description "Exceeded ingress time standard deviation threshold";
                 }
                 enum "ingress-jitter-exceeded" {
                   description "Exceeded jitter in ingress time threshold";
                 }
                 enum "egress-time-exceeded" {
                   description "Exceeded maximum egress time threshold";
                 }
                 enum "egress-std-dev-exceeded" {
                   description "Exceeded egress time standard deviation threshold";
                 }
                 enum "egress-jitter-exceeded" {
                   description "Exceeded jitter in egress time threshold";
                 }
               }
             }
             leaf destination-interface {
               description "Name of output interface for probes";
               type union {
                 type jt:interface-name;
                 type string {
                   pattern "<.*>|$.*";
                 }
               }
             }
             leaf one-way-hardware-timestamp {
               description "Enable hardware timestamps for one-way measurements";
               type empty;
             }
           }
         }
         container probe-server {
           description "ICMP/TCP/UDP probe server";
           uses apply-advanced;
           container tcp {
             description "TCP probe server";
             uses apply-advanced;
             leaf port {
               description "Port number 7 through 65535";
               type union {
                 type uint16;
                 type string {
                   pattern "<.*>|$.*";
                 }
               }
             }
           }
           container udp {
             description "UDP probe server";
             uses apply-advanced;
             leaf port {
               description "Port number 7 through 65535";
               type union {
                 type uint16;
                 type string {
                   pattern "<.*>|$.*";
                 }
               }
             }
           }
         }
         leaf probe-limit {
           description "Maximum number of concurrent probes allowed";
           default "100";
           type union {
             type string {
               pattern "<.*>|$.*";
             }
             type uint32 {
               range "1 .. 500";
             }
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             description "Management address connected to compute cluster";
             uses apply-advanced;
             list routing-instance {
               key routing-instance-name;
               ordered-by user;
               description "Packets are restriction to specified routing instance";
               max-elements 1;
               leaf routing-instance-name {
                 description "Name of routing instance";
                 type string {
                 }
               }
               uses apply-advanced;
               container family {
                 description "Protocol family";
                 container inet {
                   description "IPv4 parameters";
                   uses apply-advanced;
                   leaf address {
                     description "Interface address";
                     type jt:ipv4addr;
                   }
                 }
               }
             }
             container family {
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   type jt:mac-addr;
                 }
               }
               case case_2 {
               }
               case case_3 {
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   type string {
                     length "1 .. 15";
                   }
                 }
                 uses apply-advanced;
                 leaf management {
                   description "Use this as management interface";
                   type empty;
                 }
                 container family {
                   description "Protocol family";
                   uses family;
                 }
                 leaf enable-passthrough {
                   description "Enable passthrough on this interface";
                   type empty;
                 }
                 leaf mtu {
                   description "Maximum transmit packet size";
                   type union {
                     type string {
                       pattern "<.*>|$.*";
                     }
                     type uint16 {
                       range "256 .. 9192";
                     }
                   }
                 }
                 container ether-options {
                   uses apply-advanced;
                   choice agg-intf {
                     case case_1 {
                       leaf ieee-802-3ad {
                         description "Aggregated interface name";
                         type string {
                           length "1 .. 15";
                         }
                       }
                     }
                   }
                 }
               }
               list bridge {
                 key name;
                 ordered-by user;
                 description "Bridge configuration";
                 leaf name {
                   description "Bridge name";
                   type string {
                     length "1 .. 15";
                   }
                 }
                 uses apply-advanced;
                 leaf management {
                   description "Use this as management bridge";
                   type empty;
                 }
                 container family {
                   description "Protocol family";
                   uses family;
                 }
                 leaf-list interface {
                   ordered-by user;
                   description "Bridge interface list";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   type string {
                     length "1 .. 15";
                   }
                 }
                 uses apply-advanced;
                 leaf management {
                   description "Use this as management aggregate";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 max-elements 1;
                 leaf routing-instance-name {
                   description "Name of routing instance";
                   type string {
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 type string {
                   length "1 .. 15";
                 }
               }
               uses apply-advanced;
               leaf compute-node {
                 description "Compute node on which the virtual-machine runs";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container unified-access-control {
         description "Configure Unified Access Control";
         uses apply-advanced;
         list infranet-controller {
           key name;
           ordered-by user;
           description "Configure infranet controller";
           leaf name {
             description "Infranet controller name";
             type string {
               length "1 .. 31";
             }
           }
           uses apply-advanced;
           leaf address {
             description "Infranet controller IP address";
             type jt:ipv4addr;
           }
           leaf port {
             description "Infranet controller port";
             default "11123";
             type union {
               type string {
                 pattern "<.*>|$.*";
               }
               type uint32 {
                 range "1 .. 65535";
               }
             }
           }
           leaf interface {
             description "Outgoing interface";
             type union {
               type jt:interface-name;
               type string {
                 pattern "<.*>|$.*";
               }
             }
           }
           leaf password {
             description "Infranet controller server password";
             type string {
               length "1 .. 255";
             }
           }
           leaf-list ca-profile {
             ordered-by user;
             description "Define a list of certificate authority";
             type string;
           }
           leaf server-certificate-subject {
             description "Subject name of infranet controller certificate to match";
             type string {
               length "1 .. 255";
             }
           }
         }
         leaf certificate-verification {
           description "Specify certificate verification requirement";
           default "warning";
           type enumeration {
             enum "warning" {
               description "Warn if certificate is not being verified";
             }
             enum "required" {
               description "Require certificate verification. Most secure";
             }
             enum "optional" {
               description "Make verification optional, no warnings. Least secure";
             }
           }
         }
         leaf timeout {
           description "Timeout for idle infranet controller link in seconds";
           default "300";
           type union {
             type string {
               pattern "<.*>|$.*";
             }
             type uint32 {
               range "2 .. 10000";
             }
           }
         }
         leaf interval {
           description "Heartbeat interval from infranet controller in seconds";
           default "30";
           type union {
             type string {
               pattern "<.*>|$.*";
             }
             type uint32 {
               range "1 .. 9999";
             }
           }
         }
         leaf timeout-action {
           description "Specify action when infranet controller timeout occurs";
           default "close";
           type enumeration {
             enum "close" {
               description "Remove existing sessions and block further traffic";
             }
             enum "no-change" {
               description "Preserve existing connections; block new sessions";
             }
             enum "open" {
               description "Allow traffic for new and existing sessions to go through";
             }
           }
         }
         container traceoptions {
           description "UAC trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "all" {
                   description "Trace with all flags enabled";
                 }
                 enum "ipc" {
                   description "IPC tracing";
                 }
                 enum "config" {
                   description "Configuration tracing";
                 }
                 enum "connect" {
                   description "Communication with infranet controller tracing";
                 }
               }
             }
           }
         }
       }
       container captive-portal {
         description "Captive Portal options";
         uses juniper-services-captive-portal;
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
       }
       container pcp {
         description "Configure Port Control Protocol";
         uses pcp-object;
       }
       container rtlog {
         presence "enable rtlog";
         description "Secure log daemon options";
         uses apply-advanced;
         container traceoptions {
           description "Security log daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             type string {
               length "1 .. 63";
             }
           }
           uses apply-advanced;
           leaf collector {
             description "Specify a collector name";
             type string {
               length "1 .. 63";
             }
           }
           leaf-list collector-group {
             ordered-by user;
             description "Specify a collector-group name";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
         }
       }
       container service-device-pools {
         description "Configure service device pools";
         uses apply-advanced;
         list pool {
           key name;
           ordered-by user;
           description "Define service device pool";
           uses service_device_pool_object;
         }
       }
       container analytics {
         presence "enable analytics";
         description "Traffic analytics configuration options";
         uses apply-advanced;
         container zero-suppression {
           presence "enable zero-suppression";
           description "Configure suppression of zeros for GRPC sensors";
           uses apply-advanced;
           leaf no-zero-suppression {
             description "Disable zero suppression";
             type empty;
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:ipaddr;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipv4addr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-sdm" {
                 description "Use gpb self-describing-message format";
               }
               enum "gpb-gnmi" {
                 description "Use gnmi format for gpb messages";
               }
               enum "json-gnmi" {
                 description "Use gnmi format for json messages";
               }
             }
           }
           leaf transport {
             description "Telemetry export transport protocol";
             type enumeration {
               enum "udp" {
                 description "Use UDP transport protocol";
               }
               enum "grpc" {
                 description "Use grpc transport";
               }
             }
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 255";
             }
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
           }
           leaf target-defined {
             description "Allow target to decide periodic, on-change or mix";
             type empty;
           }
           leaf life-time {
             description "Denotes sensor life-time";
             type enumeration {
               enum "long-lived" {
                 description "A long-lived susbcription";
               }
               enum "one-off" {
                 description "An one-off subscription";
               }
             }
           }
         }
         container agent {
           description "Configure analytics agent";
           uses apply-advanced;
           list service-agents {
             key name;
             ordered-by user;
             description "Analytics service agent configuration";
             leaf name {
               description "Analytics service agent name";
               type string;
             }
             uses apply-advanced;
             container inputs {
               description "List of input plugins";
               uses apply-advanced;
               container input-jti-ipfix {
                 presence "enable input-jti-ipfix";
                 description "Junos grpc IPFIX group plugin";
                 uses apply-advanced;
                 container parameters {
                   presence "enable parameters";
                   uses apply-advanced;
                   list record-group {
                     key name;
                     ordered-by user;
                     description "Group sensors";
                     max-elements 10;
                     leaf name {
                       description "Group sensors";
                       type string;
                     }
                     uses apply-advanced;
                     leaf reporting-interval {
                       description "Reporting-interval";
                       default "900";
                       type union {
                         type string {
                           pattern "<.*>|$.*";
                         }
                         type uint32 {
                           range "60 .. 86400";
                         }
                       }
                     }
                     leaf-list record {
                       ordered-by user;
                       description "Ipfix record name";
                       type enumeration {
                         enum "port-statistics" {
                           description "Port statistics";
                         }
                         enum "address-pool-utilization" {
                           description "Address pool utilization";
                         }
                         enum "dhcpv4-server-stats" {
                           description "Dhcpv4 server statistics";
                         }
                         enum "thermal" {
                           description "Thermal statistics";
                         }
                         enum "chassis-inventory" {
                           description "Chassis inventory details";
                         }
                         enum "chassis-power" {
                           description "Chassis power details";
                         }
                         enum "resource-utilization" {
                           description "Resource utilization details";
                         }
                         enum "uptime" {
                           description "Uptime value";
                         }
                         enum "subscriber-statistics" {
                           description "Subscriber statistics";
                         }
                         enum "interface-metadata" {
                           description "Interface metadata details";
                         }
                         enum "interface-queue-statistics" {
                           description "Interface Queue statistics";
                         }
                       }
                     }
                   }
                 }
               }
               container input-ipfix {
                 presence "enable input-ipfix";
                 description "Junos IPFIX Mediator input plugin";
                 uses apply-advanced;
                 container parameters {
                   presence "enable parameters";
                   description "List of IPFIX parameters";
                   uses apply-advanced;
                   leaf tcp-port {
                     description "Listening TCP Port for IPFIX Mediator";
                     type union {
                       type uint16;
                       type string {
                         pattern "<.*>|$.*";
                       }
                     }
                   }
                   leaf maximum-connections {
                     description "Maximum TCP Connections 1..500";
                     type union {
                       type string {
                         pattern "<.*>|$.*";
                       }
                       type uint32 {
                         range "1 .. 500";
                       }
                     }
                   }
                   leaf vrf-name {
                     description "VRF name on which IPFIX packets are accepted";
                     type string;
                   }
                 }
               }
               container analytics {
                 presence "enable analytics";
                 description "Junos Telemetry plugin";
                 uses apply-advanced;
                 container parameters {
                   presence "enable parameters";
                   description "List of key:value parameters";
                   uses apply-advanced;
                   leaf sample-frequency {
                     description "Interval for sensor data in seconds, max 24 hours";
                     default "5";
                     units "seconds";
                     type union {
                       type string {
                         pattern "<.*>|$.*";
                       }
                       type uint32 {
                         range "0 .. 86400";
                       }
                     }
                   }
                   leaf sensors {
                     description "Space separated list of sensor paths";
                     type string {
                       length "1 .. 2048";
                     }
                   }
                   leaf generate-tags {
                     description "Enable generation of tags";
                     type empty;
                   }
                 }
               }
             }
             list outputs {
               key name;
               ordered-by user;
               description "List of output plugins";
               max-elements 1;
               uses output-plugin;
             }
           }
           container traceoptions {
             presence "enable traceoptions";
             uses apply-advanced;
             leaf flag {
               description "Set log level for tracing";
               type enumeration {
                 enum "trace" {
                   description "Log level TRACE, will trace everything";
                 }
                 enum "debug" {
                   description "Log level DEBUG, will trace debug messages";
                 }
                 enum "info" {
                   description "Log level INFO";
                 }
                 enum "error" {
                   description "Log level ERROR, will trace all error messages";
                 }
               }
             }
             leaf filename {
               description "Configure filename for trace messages";
               default "ntf-agent.log";
               type string;
             }
           }
         }
         container traceoptions {
           description "Traffic analytics trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace configuration events";
                 }
                 enum "configuration" {
                   description "Log configuration events";
                 }
                 enum "rtsock" {
                   description "Trace rtsock message events";
                 }
                 enum "client-server" {
                   description "Trace client-server events";
                 }
                 enum "interface" {
                   description "Trace interface update events";
                 }
                 enum "xmlproxy" {
                   description "Trace xmlproxy events";
                 }
               }
             }
             leaf disable {
               description "Disable this trace flag";
               type empty;
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
             }
             leaf low {
               description "Low queue depth threshold";
               units "bytes";
               type union {
                 type string {
                   pattern "<.*>|$.*";
                 }
                 type uint32 {
                   range "1 .. 1250000000";
                 }
               }
             }
           }
           container latency-threshold {
             description "Latency threshold configuration";
             leaf high {
               description "High latency threshold";
               units "nanoseconds";
               type union {
                 type string {
                   pattern "<.*>|$.*";
                 }
                 type uint32 {
                   range "1 .. 100000000";
                 }
               }
             }
             leaf low {
               description "Low latency threshold";
               units "nanoseconds";
               type union {
                 type string {
                   pattern "<.*>|$.*";
                 }
                 type uint32 {
                   range "1 .. 100000000";
                 }
               }
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
         container traffic-statistics {
           description "Traffic statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Traffic statistics polling interval";
             units "seconds";
             type union {
               type string {
                 pattern "<.*>|$.*";
               }
               type uint32 {
                 range "1 .. 300";
               }
             }
           }
         }
         container queue-statistics {
           description "Microburst statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Queue statistics polling interval";
             units "milliseconds";
             type union {
               type string {
                 pattern "<.*>|$.*";
               }
               type uint32 {
                 range "1 .. 1000";
               }
             }
           }
         }
         container interfaces {
           description "Interface configuration options";
           status deprecated;
           uses apply-advanced;
           list interface {
             key name;
             uses interface_type;
           }
         }
         container streaming-servers {
           description "Remote streaming servers configuration options";
           status deprecated;
           uses apply-advanced;
           list address {
             key name;
             ordered-by user;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               leaf stream-format {
                 description "Streaming data format";
                 type enumeration {
                   enum "json" {
                     description "Javascript object notation";
                   }
                   enum "csv" {
                     description "Comma separated value";
                   }
                   enum "tsv" {
                     description "Tab separated value";
                   }
                 }
               }
               list stream-type {
                 key name;
                 description "Type of statistics to stream";
                 leaf name {
                   type enumeration {
                     enum "traffic-statistics" {
                       description "Enable streaming of traffic statistics";
                     }
                     enum "queue-statistics" {
                       description "Enable streaming of queue statistics";
                     }
                   }
                 }
                 uses apply-advanced;
               }
             }
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping bgp-logical-system {
     description "Logical systems configuration for rpm";
     leaf name {
       description "Logical system name";
       type string {
       }
     }
     uses apply-advanced;
     list routing-instances {
       key name;
       description "Routing instances";
       uses bgp-routing-instances;
     }
   }
   grouping bgp-routing-instances {
     description "Routing-instance configuration for rpm";
     leaf name {
       description "Routing instance name";
       type string;
     }
     uses apply-advanced;
   }
   grouping drop-policy-term {
     description "One or more drop terms";
     leaf name {
       description "Term name";
       type string {
       }
     }
     uses apply-advanced;
     container from {
       description "Define match criteria";
       uses apply-advanced;
       container source-address {
         description "Source IP Address";
         presence "enable source-address";
         uses li_policy_addr_simple_object;
       }
       container destination-address {
         description "Destination IP Address";
         presence "enable destination-address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
       }
     }
     uses apply-advanced;
     container from {
       description "Define match criteria";
       uses apply-advanced;
       container source-address {
         description "Source IPv6 Address or Prefix";
         presence "enable source-address";
         uses li_policy_addr6_simple_object;
       }
       container destination-address {
         description "Destination IPv6 Address or Prefix";
         presence "enable destination-address";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping juniper-services-captive-portal {
     uses apply-advanced;
     leaf authentication-profile-name {
       description "Access profile name to use for authentication";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
             }
             enum "parse" {
               description "Trace configuration parsing";
             }
             enum "esw-if" {
               description "Trace ESW Interactions";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
         }
         enum "https" {
           description "Encrypted HTTPS will be used for Captive Portal authentication";
         }
       }
     }
     container custom-options {
       presence "enable custom-options";
       description "Captive Portal html user interface customization options";
       uses apply-advanced;
       leaf header-logo {
         description "Path to logo image file";
         type string {
           length "1 .. 255";
         }
       }
       leaf header-bgcolor {
         description "Background color of the html header in hex html format";
         type string {
           length 7;
         }
       }
       leaf header-text-color {
         description "Text color of the html header in hex html format";
         type string {
           length 7;
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
         }
       }
       leaf form-header-text-color {
         description "Text color of the login form header in hex html format";
         type string {
           length 7;
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
         }
       }
       leaf footer-text-color {
         description "Text color of the footer in hex html format";
         type string {
           length 7;
         }
       }
       leaf post-authentication-url {
         description "Post authentication redirection URL";
         type string {
           length "1 .. 255";
         }
       }
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping macro-data-type {
     leaf name {
       description "Keyword part of the keyword-value pair";
       type string;
     }
     leaf value {
       description "Value part of the keyword-value pair";
       type string;
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping output-plugin {
     leaf name {
       description "Plugin name";
       type string;
     }
     uses apply-advanced;
     list parameters {
       key name;
       ordered-by user;
       description "List of key:value parameters for plugin";
       uses parameter-pair;
     }
   }
   grouping parameter-pair {
     leaf name {
       description "Parameter key";
       type string;
     }
     uses apply-advanced;
     leaf value {
       description "Parameter value";
       type string;
     }
   }
   grouping pcp-object {
     description "Configure Port Control Protocol";
     uses apply-advanced;
     container traceoptions {
       description "Trace options for PCP-LOG";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list rule-set {
       key name;
       ordered-by user;
       description "Defines a set of PCP rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping rmopd-traceoptions {
     description "Trace options for remote-monitoring";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "ipc" {
             description "Trace ipc messages";
           }
           enum "ppm" {
             description "Trace ppm";
           }
           enum "rpd" {
             description "Trace rpd events";
           }
           enum "info" {
             description "Trace info events";
           }
           enum "statistics" {
             description "Trace statistics";
           }
           enum "error" {
             description "Trace events related to catastrophic errors in daemon";
           }
           enum "all" {
             description "Trace everything";
           }
         }
       }
     }
   }
   grouping service_device_pool_object {
     leaf name {
       description "Service device pool name";
       type string {
         length "1 .. 63";
       }
     }
     uses apply-advanced;
     list interface {
       key name;
       ordered-by user;
       description "Service device name";
       leaf name {
         type string;
       }
       uses apply-advanced;
     }
   }
   grouping service_interface_pool_object {
     leaf name {
       description "Service interface pool name";
       type string {
         length "1 .. 63";
       }
     }
     uses apply-advanced;
     list interface {
       key name;
       ordered-by user;
       description "Service interface name";
       leaf name {
         type union {
           type jt:interface-unit;
           type string {
             pattern "<.*>|$.*";
           }
         }
       }
       uses apply-advanced;
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf client-certificate {
         description "Local certificate identifier";
         type string {
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf server-certificate {
         description "Local certificate identifier";
         type string {
         }
       }
     }
   }
   grouping ssl-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
     container packet-filter {
       description "SSL Packet filter";
       uses apply-advanced;
       leaf source-ip {
         description "Source IP address";
         type jt:ipaddr;
       }
       leaf destination-ip {
         description "Destination IP address";
         type jt:ipaddr;
       }
       leaf source-port {
         description "Source port";
         type union {
           type string {
             pattern "<.*>|$.*";
           }
           type uint16 {
             range "1 .. 65535";
           }
         }
       }
       leaf destination-port {
         description "Destination port";
         type union {
           type string {
             pattern "<.*>|$.*";
           }
           type uint16 {
             range "1 .. 65535";
           }
         }
       }
     }
   }
   grouping tunnel_interface_type {
     description "One or more tunnel interfaces on which to configure flow-tap service";
     leaf name {
       description "Tunnel Interface name";
       type union {
         type jt:interface-unit;
         type string {
           pattern "<.*>|$.*";
         }
       }
     }
     uses apply-advanced;
   }
 }
