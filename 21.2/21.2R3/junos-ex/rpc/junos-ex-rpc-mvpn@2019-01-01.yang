/*
 * Copyright (c) 2022 Juniper Networks, Inc.
 * All rights reserved.
 */
 module junos-ex-rpc-mvpn {
   namespace "http://yang.juniper.net/junos-ex/rpc/mvpn";

   prefix mvpn;

   import junos-common-types {
     prefix jt;
     revision-date 2019-01-01;
   }

   organization "Juniper Networks, Inc.";

   contact "yang-support@juniper.net";

   description "Junos RPC YANG module for mvpn command(s)";

   revision 2019-01-01 {
     description "Junos: 21.2R3.8";
   }

   rpc get-mvpn-instance-information {
     description "Show MVPN instance";
     input {
       choice daemon-select {
         case logical-system {
           leaf logical-system {
             description "Name of logical system, or 'all'";
             type string {
             }
           }
         }
       }
       leaf display-tunnel-name {
         description "Display ingress provider tunnel name instead of attribute";
         type empty;
       }
       leaf instance-name {
         description "Name of MVPN instance";
         default "all";
         type string;
       }
       leaf family {
         description "MVPN instance address family";
         type enumeration {
           enum "inet" {
             description "Display IPv4 instance";
           }
           enum "inet6" {
             description "Display IPv6 instance";
           }
         }
       }
       leaf level {
         default "detail";
         type enumeration {
           enum "summary" {
             description "Display summary output";
           }
           enum "detail" {
             description "Display detailed version of output";
           }
           enum "extensive" {
             description "Display extensive version of output";
           }
         }
       }
     }
     output {
       choice output_c {
         case output-tag {
           leaf output {
             type string;
           }
         }
         case actual-tag {
           anyxml mvpn-instance-information;
         }
         case multichassis-tag {
           anyxml multi-routing-engine-results;
         }
       }
     }
   }
   rpc get-mvpn-neighbor-information {
     description "Show MVPN neighbor";
     input {
       choice daemon-select {
         case logical-system {
           leaf logical-system {
             description "Name of logical system, or 'all'";
             type string {
             }
           }
         }
       }
       leaf neighbor-address {
         description "Address of MVPN neighbor";
         default "all";
         type string;
       }
       leaf instance-name {
         description "Name of MVPN instance";
         default "all";
         type string;
       }
       leaf family {
         description "MVPN neighbor address family";
         type enumeration {
           enum "inet" {
             description "Display IPv4 neighbor";
           }
           enum "inet6" {
             description "Display IPv6 neighbor";
           }
         }
       }
       leaf level {
         default "detail";
         type enumeration {
           enum "summary" {
             description "Display summary output";
           }
           enum "detail" {
             description "Display detailed version of output";
           }
           enum "extensive" {
             description "Display extensive version of output";
           }
         }
       }
     }
     output {
       choice output_c {
         case output-tag {
           leaf output {
             type string;
           }
         }
         case actual-tag {
           anyxml mvpn-instance-information;
         }
         case multichassis-tag {
           anyxml multi-routing-engine-results;
         }
       }
     }
   }
   rpc get-mvpn-c-multicasti-route {
     description "Show MVPN c-multicast route";
     input {
       choice daemon-select {
         case logical-system {
           leaf logical-system {
             description "Name of logical system, or 'all'";
             type string {
             }
           }
         }
       }
       leaf display-tunnel-name {
         description "Display ingress provider tunnel name instead of attribute";
         type empty;
       }
       leaf source-pe {
         description "Display source PE information";
         type empty;
       }
       leaf instance-name {
         description "Name of MVPN instance";
         default "all";
         type string;
       }
       leaf family {
         description "MVPN c-multicast route address family";
         type enumeration {
           enum "inet" {
             description "Display IPv4 c-multicast route";
           }
           enum "inet6" {
             description "Display IPv6 c-multicast route";
           }
         }
       }
       leaf level {
         default "detail";
         type enumeration {
           enum "summary" {
             description "Display summary output";
           }
           enum "detail" {
             description "Display detailed version of output";
           }
           enum "extensive" {
             description "Display extensive version of output";
           }
         }
       }
     }
     output {
       choice output_c {
         case output-tag {
           leaf output {
             type string;
           }
         }
         case actual-tag {
           anyxml mvpn-instance-information;
         }
         case multichassis-tag {
           anyxml multi-routing-engine-results;
         }
       }
     }
   }
   rpc get-mvpn-suppressed-information {
     description "Show suppressed MVPN forwarding prefixes";
     input {
       choice daemon-select {
         case logical-system {
           leaf logical-system {
             description "Name of logical system, or 'all'";
             type string {
             }
           }
         }
       }
       leaf general {
         description "Display suppressed general entries";
         type empty;
       }
       leaf mvpn-rpt {
         description "Display suppressed MVPN (*,G) entries";
         type empty;
       }
       leaf instance {
         description "Name of instance";
         type string;
         mandatory true;
       }
       leaf family {
         description "Address family";
         type enumeration {
           enum "inet" {
             description "Display IPv4 suppressed prefixes";
           }
           enum "inet6" {
             description "Display IPv6 suppressed prefixes";
           }
         }
       }
       leaf level {
         type enumeration {
           enum "summary" {
             description "Display summary output";
           }
         }
       }
     }
     output {
       choice output_c {
         case output-tag {
           leaf output {
             type string;
           }
         }
         case actual-tag {
           anyxml mvpn-suppressed-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
