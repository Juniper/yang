/*
 * Copyright (c) 2022 Juniper Networks, Inc.
 * All rights reserved.
 */
 module junos-nfx-conf-schedulers {
   namespace "http://yang.juniper.net/junos-nfx/conf/schedulers";

   prefix jc-schedulers;

   import junos-common-types {
     prefix jt;
     revision-date 2019-01-01;
   }

   import junos-nfx-conf-root {
     prefix jc;
     revision-date 2019-01-01;
   }

   organization "Juniper Networks, Inc.";

   contact "yang-support@juniper.net";

   description "Junos schedulers configuration module";

   revision 2019-01-01 {
     description "Junos: 21.2R3.8";
   }

   augment /jc:configuration {
     uses schedulers-group;
   }
   augment /jc:configuration/jc:groups {
     uses schedulers-group;
   }
   grouping schedulers-group {
     container schedulers {
       description "Security scheduler";
       uses apply-advanced;
       list scheduler {
         key name;
         ordered-by user;
         description "Scheduler configuration";
         uses scheduler_object_type;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
   grouping scheduler_object_type {
     leaf name {
       description "Name of security scheduler";
       type string {
         length "1 .. 63";
       }
     }
     uses apply-advanced;
     leaf description {
       description "Text description of scheduler";
       type string {
         length "1 .. 900";
       }
     }
     list start-date {
       key "start-date stop-date";
       ordered-by user;
       description "Start date and time ([YYYY-]MM-DD.hh:mm)";
       max-elements 2;
       leaf start-date {
         description "Start date and time ([YYYY-]MM-DD.hh:mm)";
         type string {
         }
       }
       leaf stop-date {
         description "Stop date and time ([YYYY-]MM-DD.hh:mm)";
         type string {
         }
       }
       uses apply-advanced;
     }
     container daily {
       description "Everyday; can be overwritten by specific weekday";
       uses daily-object;
     }
     container sunday {
       description "Every Sunday";
       uses daily-object;
     }
     container monday {
       description "Every Monday";
       uses daily-object;
     }
     container tuesday {
       description "Every Tuesday";
       uses daily-object;
     }
     container wednesday {
       description "Every Wednesday";
       uses daily-object;
     }
     container thursday {
       description "Every Thursday";
       uses daily-object;
     }
     container friday {
       description "Every Friday";
       uses daily-object;
     }
     container saturday {
       description "Every Saturday";
       uses daily-object;
     }
   }
   grouping daily-object {
     description "Daily schedule";
     uses apply-advanced;
     choice daily_type {
       case case_1 {
         list start-time {
           key "start-time-value stop-time";
           description "Time range for day";
           max-elements 2;
           leaf start-time-value {
             description "Start time for day (hh:mm)";
             type string {
             }
           }
           leaf stop-time {
             description "Stop time for day (hh:mm)";
             type string {
             }
           }
           uses apply-advanced;
         }
       }
       case case_2 {
         leaf exclude {
           description "Exclude day from week";
           type empty;
         }
       }
       case case_3 {
         leaf all-day {
           description "Include complete day";
           type empty;
         }
       }
     }
   }
 }
