/*
 * Copyright (c) 2022 Juniper Networks, Inc.
 * All rights reserved.
 */
 module junos-nfx-rpc-l2-learning {
   namespace "http://yang.juniper.net/junos-nfx/rpc/l2-learning";

   prefix l2-learning;

   import junos-common-types {
     prefix jt;
     revision-date 2019-01-01;
   }

   organization "Juniper Networks, Inc.";

   contact "yang-support@juniper.net";

   description "Junos RPC YANG module for l2-learning command(s)";

   revision 2019-01-01 {
     description "Junos: 21.2R3.8";
   }

   rpc get-l2-learning-interface-information {
     description "Show interface";
     output {
       choice output_c {
         case output-tag {
           leaf output {
             type string;
           }
         }
         case actual-tag {
           anyxml l2ald-iff-information;
         }
         case multichassis-tag {
           anyxml multi-routing-engine-results;
         }
       }
     }
   }
   rpc get-l2-learning-global-mac-count {
     description "Show layer-2 global mac address count";
     output {
       choice output_c {
         case output-tag {
           leaf output {
             type string;
           }
         }
         case actual-tag {
           anyxml l2ald-global-macdb-count;
         }
         case multichassis-tag {
           anyxml multi-routing-engine-results;
         }
       }
     }
   }
   rpc get-l2-learning-global-mac-ip-count {
     description "Show global MAC+IP bindings count";
     output {
       choice output_c {
         case output-tag {
           leaf output {
             type string;
           }
         }
         case actual-tag {
           anyxml l2ald-global-mac-ip-count;
         }
         case multichassis-tag {
           anyxml multi-routing-engine-results;
         }
       }
     }
   }
   rpc get-l2-learning-global-information {
     description "Show process-related information";
     output {
       choice output_c {
         case output-tag {
           leaf output {
             type string;
           }
         }
         case actual-tag {
           anyxml l2ald-global-configuration;
         }
         case multichassis-tag {
           anyxml multi-routing-engine-results;
         }
       }
     }
   }
   rpc get-l2-learning-routing-instances {
     description "Show routing instances";
     input {
       leaf instance-name {
         description "Display information for a specified instance";
         default "all";
         type string;
       }
       leaf bridge-domain {
         description "Particular bridge-domain or 'all'";
         default "all";
         type string;
       }
       leaf ifbd {
         description "Display information for ifbds under bd";
         type enumeration {
           enum "all" {
             description "Display all IFBDs";
           }
         }
       }
     }
     output {
       choice output_c {
         case output-tag {
           leaf output {
             type string;
           }
         }
         case actual-tag {
           anyxml l2ald-routing-table-information;
         }
         case multichassis-tag {
           anyxml multi-routing-engine-results;
         }
       }
     }
   }
   rpc get-l2-learning-provider-instance {
     description "Show provider instance (I-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
         }
       }
       leaf isid {
         description "Display Information for specified ISID or all ISID(s)";
         type string;
       }
     }
     output {
       choice output_c {
         case output-tag {
           leaf output {
             type string;
           }
         }
         case actual-tag {
           anyxml l2ald-pbn;
         }
         case multichassis-tag {
           anyxml multi-routing-engine-results;
         }
       }
     }
   }
   rpc get-l2-learning-backbone-instance {
     description "Show provider backbone instance (B-component)";
     input {
       leaf instance {
         description "Display information for a specified instance";
         default "all";
         type string;
       }
       leaf bridge-domain {
         description "Display information for a specified bridge domain";
         status deprecated;
         default "all";
         type string;
       }
       leaf bridge-domain-name {
         description "Display information for a specified bridge domain";
         type string;
       }
       leaf logical-system {
         description "Name of logical system, or 'all'";
         default "all";
         type string {
         }
       }
       leaf isid {
         description "Display Information for specified ISID or all ISID(s)";
         type string;
       }
     }
     output {
       choice output_c {
         case output-tag {
           leaf output {
             type string;
           }
         }
         case actual-tag {
           anyxml l2ald-pbbn;
         }
         case multichassis-tag {
           anyxml multi-routing-engine-results;
         }
       }
     }
   }
   rpc get-l2-learning-remote-backbone-edge-bridges {
     description "Show remote backbone edge bridges in a PBBN network";
     input {
       leaf remote-beb-mac-address {
         description "Remote backbone edge bridge MAC address";
         default "all";
         type jt:mac-addr;
       }
       leaf logical-system {
         description "Name of logical system, or 'all'";
         default "all";
         type string {
         }
       }
       leaf instance {
         description "Display information for a specified instance";
         default "all";
         type string;
       }
     }
     output {
       choice output_c {
         case output-tag {
           leaf output {
             type string;
           }
         }
         case actual-tag {
           anyxml l2ald-rbeb-information;
         }
         case multichassis-tag {
           anyxml multi-routing-engine-results;
         }
       }
     }
   }
   rpc get-l2-learning-redundancy-groups {
     description "Show redundancy-groups";
     input {
       choice daemon-select {
         case logical-system {
           leaf logical-system {
             description "Name of logical system";
             type string {
             }
           }
         }
       }
       leaf redundancy-group-id {
         description "Display information for a specified RG";
         default "0";
         type union {
           type string {
             pattern "<.*>|$.*";
           }
           type uint32 {
             range "0 .. 4294967294";
           }
         }
       }
       leaf options {
         description "Display information for specified RG or all RG(s)";
         type enumeration {
           enum "remote-macs" {
             description "Display MAC for all RG(s)";
           }
           enum "arp-statistics" {
             description "Show MCAE ARP Synchronization statistics";
           }
           enum "nd-statistics" {
             description "Show MCAE ND synchronization statistics";
           }
           enum "remote-irb-ifas" {
             description "Show MCLAG Remote IRB IFAs";
           }
           enum "local-irb-ifas" {
             description "Show MCLAG Locally Syned IRB IFAs";
           }
         }
       }
     }
     output {
       choice output_c {
         case output-tag {
           leaf output {
             type string;
           }
         }
         case actual-tag {
           anyxml l2ald-mc-ae-rg-entry;
         }
         case multichassis-tag {
           anyxml multi-routing-engine-results;
         }
       }
     }
   }
   rpc get-l2-learning-context-history {
     description "Print context history";
     output {
       choice output_c {
         case output-tag {
           leaf output {
             type string;
           }
         }
         case actual-tag {
           anyxml l2ald-ctxt-history;
         }
         case multichassis-tag {
           anyxml multi-routing-engine-results;
         }
       }
     }
   }
   rpc get-l2-learning-context-history-mac {
     description "Mac context history";
     input {
       leaf address {
         description "MAC address";
         default "all";
         type jt:mac-addr;
       }
     }
     output {
       choice output_c {
         case output-tag {
           leaf output {
             type string;
           }
         }
         case actual-tag {
           anyxml l2ald-ctxt-history;
         }
         case multichassis-tag {
           anyxml multi-routing-engine-results;
         }
       }
     }
   }
   rpc get-l2-learning-context-history-mac-ip {
     description "Mac-ip context history";
     input {
       leaf address {
         description "MAC address";
         default "all";
         type jt:mac-addr;
       }
     }
     output {
       choice output_c {
         case output-tag {
           leaf output {
             type string;
           }
         }
         case actual-tag {
           anyxml l2ald-ctxt-history;
         }
         case multichassis-tag {
           anyxml multi-routing-engine-results;
         }
       }
     }
   }
   rpc get-l2-learning-context-history-rpd {
     description "Rpd context history";
     input {
       leaf address {
         description "MAC address";
         default "all";
         type jt:mac-addr;
       }
     }
     output {
       choice output_c {
         case output-tag {
           leaf output {
             type string;
           }
         }
         case actual-tag {
           anyxml l2ald-ctxt-history;
         }
         case multichassis-tag {
           anyxml multi-routing-engine-results;
         }
       }
     }
   }
   rpc get-l2-learning-context-history-rts {
     description "Rtsock context history";
     output {
       choice output_c {
         case output-tag {
           leaf output {
             type string;
           }
         }
         case actual-tag {
           anyxml l2ald-ctxt-history;
         }
         case multichassis-tag {
           anyxml multi-routing-engine-results;
         }
       }
     }
   }
   rpc get-l2-learning-context-history-mac-addr {
     description "Context history for mac-addr";
     input {
       leaf address {
         description "Mac Address";
         type jt:mac-addr;
         mandatory true;
       }
       leaf bd-id {
         description "BD Id";
         default "0";
         type union {
           type string {
             pattern "<.*>|$.*";
           }
           type int32 {
             range "0 .. 65534";
           }
         }
       }
       leaf verbosity {
         default "detail";
         type enumeration {
           enum "detail" {
             description "Display detailed output";
           }
           enum "summary" {
             description "Display summary output";
           }
         }
       }
     }
     output {
       choice output_c {
         case output-tag {
           leaf output {
             type string;
           }
         }
         case actual-tag {
           anyxml l2ald-ctxt-history;
         }
         case multichassis-tag {
           anyxml multi-routing-engine-results;
         }
       }
     }
   }
   rpc get-l2-learning-mgrp-policy {
     description "Display global mesh group policy";
     output {
       choice output_c {
         case output-tag {
           leaf output {
             type string;
           }
         }
         case actual-tag {
           anyxml l2ald-mgrp-policy;
         }
         case multichassis-tag {
           anyxml multi-routing-engine-results;
         }
       }
     }
   }
   rpc get-l2-learning-mgrp-policy-information {
     description "Display Mesh Group policy for routing instance";
     input {
       leaf instance-name {
         description "Display information for a specified instance";
         default "all";
         type string;
       }
       leaf mgrp-id {
         description "Mesh group id";
         type union {
           type uint32;
           type string {
             pattern "<.*>|$.*";
           }
         }
       }
     }
     output {
       choice output_c {
         case output-tag {
           leaf output {
             type string;
           }
         }
         case actual-tag {
           anyxml l2ald-mgrp-policy-ri;
         }
         case multichassis-tag {
           anyxml multi-routing-engine-results;
         }
       }
     }
   }
   rpc get-l2-learning-flood-group {
     description "Display  Flood Group info";
     output {
       choice output_c {
         case output-tag {
           leaf output {
             type string;
           }
         }
         case actual-tag {
           anyxml l2ald-flood-group;
         }
         case multichassis-tag {
           anyxml multi-routing-engine-results;
         }
       }
     }
   }
   rpc get-l2-learning-flood-group-information {
     description "Display Flood Group info for routing instance";
     input {
       leaf instance-name {
         description "Display information for a specified instance";
         default "all";
         type string;
       }
       leaf bd-index {
         description "Bd id";
         type union {
           type uint32;
           type string {
             pattern "<.*>|$.*";
           }
         }
       }
     }
     output {
       choice output_c {
         case output-tag {
           leaf output {
             type string;
           }
         }
         case actual-tag {
           anyxml l2ald-flood-group-ri;
         }
         case multichassis-tag {
           anyxml multi-routing-engine-results;
         }
       }
     }
   }
   rpc get-l2-learning-eamnh-information {
     description "Display EAMNH and member info";
     input {
       leaf logical-system {
         description "Name of logical system, or 'all'";
         default "all";
         type string {
         }
       }
       leaf instance {
         description "Display information for a specified instance";
         default "all";
         type string;
       }
       leaf bridge-domain {
         description "Name of bridging domain, or 'all'";
         default "all";
         type string;
       }
     }
     output {
       choice output_c {
         case output-tag {
           leaf output {
             type string;
           }
         }
         case actual-tag {
           anyxml l2ald-enh-eamnh-info;
         }
         case multichassis-tag {
           anyxml multi-routing-engine-results;
         }
       }
     }
   }
   rpc get-l2-learning-nh-learn-entries {
     description "Display information on all RNH_LE entries";
     output {
       choice output_c {
         case output-tag {
           leaf output {
             type string;
           }
         }
         case actual-tag {
           anyxml l2ald-nh-learn-entity;
         }
         case multichassis-tag {
           anyxml multi-routing-engine-results;
         }
       }
     }
   }
   rpc get-l2-learning-vxlan-svtep-info {
     description "Display source VXLAN tunnel endpoint configuration";
     input {
       leaf logical-system {
         description "Name of logical system, or 'all'";
         default "all";
         type string {
         }
       }
       leaf instance {
         description "Display information for a specified instance";
         default "all";
         type string;
       }
     }
     output {
       choice output_c {
         case output-tag {
           leaf output {
             type string;
           }
         }
         case actual-tag {
           anyxml vxlan-source-vtep-information;
         }
         case multichassis-tag {
           anyxml multi-routing-engine-results;
         }
       }
     }
   }
   rpc get-l2-learning-vxlan-svtep-ip-information {
     description "Display VXLAN configuration for source ip address";
     input {
       leaf virtual-tunnel-end-point-source-ip {
         description "Display information for a source ip";
         type jt:ipaddr;
         mandatory true;
       }
       leaf logical-system {
         description "Name of logical system, or 'all'";
         default "all";
         type string {
         }
       }
       leaf instance {
         description "Display information for a specified instance";
         default "all";
         type string;
       }
     }
     output {
       choice output_c {
         case output-tag {
           leaf output {
             type string;
           }
         }
         case actual-tag {
           anyxml vxlan-source-vtep-information;
         }
         case multichassis-tag {
           anyxml multi-routing-engine-results;
         }
       }
     }
   }
   rpc get-l2-learning-vxlan-rvtep-info {
     description "Display remote VXLAN tunnel endpoint information";
     input {
       leaf logical-system {
         description "Name of logical system, or 'all'";
         default "all";
         type string {
         }
       }
       leaf instance {
         description "Display information for a specified instance";
         default "all";
         type string;
       }
       leaf verbosity {
         default "detail";
         type enumeration {
           enum "detail" {
             description "Display detailed output";
           }
           enum "summary" {
             description "Display summary output";
           }
         }
       }
     }
     output {
       choice output_c {
         case output-tag {
           leaf output {
             type string;
           }
         }
         case actual-tag {
           anyxml vxlan-source-vtep-information;
         }
         case multichassis-tag {
           anyxml multi-routing-engine-results;
         }
       }
     }
   }
   rpc get-l2-learning-vxlan-rvtep-mactable-information {
     description "Display remote VTEP MAC table";
     input {
       leaf logical-system {
         description "Name of logical system, or 'all'";
         default "all";
         type string {
         }
       }
       leaf instance {
         description "Display information for a specified instance";
         default "all";
         type string;
       }
     }
     output {
       choice output_c {
         case output-tag {
           leaf output {
             type string;
           }
         }
         case actual-tag {
           anyxml vxlan-remote-vtep-mactable;
         }
         case multichassis-tag {
           anyxml multi-routing-engine-results;
         }
       }
     }
   }
   rpc get-l2-learning-vxlan-remote-svtep-ip-information {
     description "Display remote VXLAN endpoints associated with source endpoint";
     input {
       leaf virtual-tunnel-end-point-source-ip {
         description "Display information for a source ip";
         type jt:ipaddr;
         mandatory true;
       }
     }
     output {
       choice output_c {
         case output-tag {
           leaf output {
             type string;
           }
         }
         case actual-tag {
           anyxml vxlan-source-vtep-information;
         }
         case multichassis-tag {
           anyxml multi-routing-engine-results;
         }
       }
     }
   }
   rpc get-l2-learning-vxlan-rvtep-ip-information {
     description "Display remote VTEP MAC table for ip address";
     input {
       leaf virtual-tunnel-end-point-remote-ip {
         description "Display information for a remote end point";
         type jt:ipaddr;
         mandatory true;
       }
       leaf logical-system {
         description "Name of logical system, or 'all'";
         default "all";
         type string {
         }
       }
       leaf instance {
         description "Display information for a specified instance";
         default "all";
         type string;
       }
     }
     output {
       choice output_c {
         case output-tag {
           leaf output {
             type string;
           }
         }
         case actual-tag {
           anyxml vxlan-remote-vtep-ip;
         }
         case multichassis-tag {
           anyxml multi-routing-engine-results;
         }
       }
     }
   }
   rpc get-l2-learning-vxlan-esi-info {
     description "Display VXLAN tunnel endpoint ESI information";
     input {
       leaf logical-system {
         description "Name of logical system, or 'all'";
         default "all";
         type string {
         }
       }
       leaf instance {
         description "Display information for a specified instance";
         default "all";
         type string;
       }
       leaf esi-identifier {
         description "Ethernet segment identifier";
         type string;
       }
     }
     output {
       choice output_c {
         case output-tag {
           leaf output {
             type string;
           }
         }
         case actual-tag {
           anyxml vxlan-esi-information;
         }
         case multichassis-tag {
           anyxml multi-routing-engine-results;
         }
       }
     }
   }
   rpc get-l2-learning-vxlan-arvlbnh-info {
     description "Display VXLAN tunnel endpoint AR-VLBNH information";
     output {
       choice output_c {
         case output-tag {
           leaf output {
             type string;
           }
         }
         case actual-tag {
           anyxml vxlan-arvlbnh-information;
         }
         case multichassis-tag {
           anyxml multi-routing-engine-results;
         }
       }
     }
   }
   rpc get-l2-learning-arvlbnh-info-index {
     description "Display VxLAN AR-VLBNH information for VLBNH index";
     input {
       leaf vxlan-ar-vlbnh-index {
         description "Display information for a specified index";
         type union {
           type uint32;
           type string {
             pattern "<.*>|$.*";
           }
         }
         mandatory true;
       }
     }
     output {
       choice output_c {
         case output-tag {
           leaf output {
             type string;
           }
         }
         case actual-tag {
           anyxml vxlan-arvlbnh-information;
         }
         case multichassis-tag {
           anyxml multi-routing-engine-results;
         }
       }
     }
   }
   rpc get-l2-learning-vxlan-info-rtt-index {
     description "Display VxLAN AR-VLBNH information for RTT index";
     input {
       leaf vxlan-ar-vlbnh-rtt-index {
         description "Display information for a specified RTT index";
         type union {
           type uint32;
           type string {
             pattern "<.*>|$.*";
           }
         }
         mandatory true;
       }
     }
     output {
       choice output_c {
         case output-tag {
           leaf output {
             type string;
           }
         }
         case actual-tag {
           anyxml vxlan-arvlbnh-information;
         }
         case multichassis-tag {
           anyxml multi-routing-engine-results;
         }
       }
     }
   }
   rpc get-l2-learning-vxlan-info-bd-index {
     description "Display VxLAN AR-VLBNH information for BD index";
     input {
       leaf vxlan-ar-vlbnh-bd-index {
         description "Display information for a specified BD index";
         type union {
           type uint32;
           type string {
             pattern "<.*>|$.*";
           }
         }
         mandatory true;
       }
     }
     output {
       choice output_c {
         case output-tag {
           leaf output {
             type string;
           }
         }
         case actual-tag {
           anyxml vxlan-arvlbnh-information;
         }
         case multichassis-tag {
           anyxml multi-routing-engine-results;
         }
       }
     }
   }
   rpc get-l2-learning-vxlan-mh-vtep-info {
     description "Display Multi Homing Peer VTEP information";
     input {
       leaf logical-system {
         description "Name of logical system, or 'all'";
         default "all";
         type string {
         }
       }
     }
     output {
       choice output_c {
         case output-tag {
           leaf output {
             type string;
           }
         }
         case actual-tag {
           anyxml vxlan-mh-vtep-information;
         }
         case multichassis-tag {
           anyxml multi-routing-engine-results;
         }
       }
     }
   }
   rpc get-l2-learning-vxlan-rtt-mh-vtep-information {
     description "Display MH Peer table for routing instance";
     input {
       leaf instance-name {
         description "Display information for a specified instance";
         default "all";
         type string;
       }
     }
     output {
       choice output_c {
         case output-tag {
           leaf output {
             type string;
           }
         }
         case actual-tag {
           anyxml vxlan-rtt-mh-vtep-information;
         }
         case multichassis-tag {
           anyxml multi-routing-engine-results;
         }
       }
     }
   }
   rpc get-l2-learning-vxlan-ip-mh-vtep-information {
     description "Display MH Peer table for ip address";
     input {
       leaf virtual-tunnel-end-point-remote-ip {
         description "Display information for a remote end point";
         type jt:ipaddr;
         mandatory true;
       }
     }
     output {
       choice output_c {
         case output-tag {
           leaf output {
             type string;
           }
         }
         case actual-tag {
           anyxml vxlan-ip-mh-vtep-information;
         }
         case multichassis-tag {
           anyxml multi-routing-engine-results;
         }
       }
     }
   }
   rpc get-evpn-arp-statistics {
     description "EVPN arp statistics for irb interfaces";
     input {
       leaf instance {
         description "Display information for a specified instance";
         default "all";
         type string;
       }
       leaf bridge-domain {
         description "Name of bridging domain, or 'all'";
         default "all";
         type string;
       }
     }
     output {
       choice output_c {
         case output-tag {
           leaf output {
             type string;
           }
         }
         case actual-tag {
           anyxml l2rtb-evpn-arp-statistics;
         }
         case multichassis-tag {
           anyxml multi-routing-engine-results;
         }
       }
     }
   }
   rpc get-evpn-arp-statistics-interface {
     description "Display information for irb interfaces";
     input {
       choice interface-choice {
         case interface-name {
           leaf interface-name {
             description "Name of the irb interface";
             type string;
           }
         }
         case all {
           leaf all {
             description "All irb interfaces";
             type empty;
           }
         }
       }
     }
     output {
       choice output_c {
         case output-tag {
           leaf output {
             type string;
           }
         }
         case actual-tag {
           anyxml l2rtb-evpn-arp-statistics-interface;
         }
         case multichassis-tag {
           anyxml multi-routing-engine-results;
         }
       }
     }
   }
   rpc get-evpn-nd-statistics {
     description "EVPN ND statistics for irb interfaces";
     input {
       leaf instance {
         description "Display information for a specified instance";
         default "all";
         type string;
       }
       leaf bridge-domain {
         description "Name of bridging domain, or 'all'";
         default "all";
         type string;
       }
     }
     output {
       choice output_c {
         case output-tag {
           leaf output {
             type string;
           }
         }
         case actual-tag {
           anyxml l2rtb-evpn-nd-statistics;
         }
         case multichassis-tag {
           anyxml multi-routing-engine-results;
         }
       }
     }
   }
   rpc get-evpn-nd-statistics-interface {
     description "Display information for irb interfaces";
     input {
       choice interface-choice {
         case interface-name {
           leaf interface-name {
             description "Name of the irb interface";
             type string;
           }
         }
         case all {
           leaf all {
             description "All irb interfaces";
             type empty;
           }
         }
       }
     }
     output {
       choice output_c {
         case output-tag {
           leaf output {
             type string;
           }
         }
         case actual-tag {
           anyxml l2rtb-evpn-nd-statistics-interface;
         }
         case multichassis-tag {
           anyxml multi-routing-engine-results;
         }
       }
     }
   }
   rpc get-vlan-evpn-mcnh-information {
     description "EVPN MCNH Info";
     input {
       leaf instance {
         description "Display information for a specified instance";
         default "all";
         type string;
       }
       leaf bridge-domain {
         description "Name of bridging domain, or 'all'";
         default "all";
         type string;
       }
     }
     output {
       choice output_c {
         case output-tag {
           leaf output {
             type string;
           }
         }
         case actual-tag {
           anyxml l2ald-mcnh-info;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
