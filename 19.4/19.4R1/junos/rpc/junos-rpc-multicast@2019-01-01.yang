/*
 * Copyright (c) 2019 Juniper Networks, Inc.
 * All rights reserved.
 */
 module junos-rpc-multicast {
   namespace "http://yang.juniper.net/junos/rpc/multicast";

   prefix multicast;

   import junos-common-types {
     prefix jt;
     revision-date 2019-01-01;
   }

   organization "Juniper Networks, Inc.";

   contact "yang-support@juniper.net";

   description "Junos RPC YANG module for multicast command(s)";

   revision 2019-01-01 {
     description "Junos: 19.4R1.9";
   }

   rpc get-mc-fwd-cache-information {
     description "Show multicast forwarding cache statistics";
     input {
       choice daemon-select {
         case logical-system {
           leaf logical-system {
             description "Name of logical system, or 'all'";
             type string {
             }
           }
         }
       }
       leaf instance {
         description "Name of instance";
         type string;
       }
       leaf family {
         description "Address Family";
         type enumeration {
           enum "inet" {
             description "Display IPv4 information";
           }
           enum "inet6" {
             description "Display IPv6 information";
           }
         }
       }
     }
     output {
       choice output_c {
         case output-tag {
           leaf output {
             type string;
           }
         }
         case actual-tag {
           anyxml mc-fwd-cache-information;
         }
         case multichassis-tag {
           anyxml multi-routing-engine-results;
         }
       }
     }
   }
   rpc get-multicast-router-information {
     description "Request multicast router information";
     input {
       leaf host {
         description "Hostname or address of remote host";
         type string;
         mandatory true;
       }
     }
     output {
       choice output_c {
         case output-tag {
           leaf output {
             type string;
           }
         }
         case multichassis-tag {
           anyxml multi-routing-engine-results;
         }
       }
     }
   }
   rpc get-multicast-route-information {
     description "Show the multicast routing table";
     input {
       choice daemon-select {
         case logical-system {
           leaf logical-system {
             description "Name of logical system, or 'all'";
             type string {
             }
           }
         }
       }
       leaf instance {
         description "Name of instance";
         type string;
       }
       leaf mode {
         default "all";
         type enumeration {
           enum "all" {
             description "Display all route entries";
           }
           enum "active" {
             description "Display active route entries";
           }
           enum "inactive" {
             description "Display inactive route entries";
           }
         }
       }
       leaf verbosity_level {
         default "brief";
         type enumeration {
           enum "summary" {
             description "Display summary output";
           }
           enum "brief" {
             description "Display brief output (default)";
           }
           enum "detail" {
             description "Display detailed output";
           }
           enum "extensive" {
             description "Display extensive output";
           }
         }
       }
       leaf family {
         description "Address family";
         default "inet";
         type enumeration {
           enum "inet" {
             description "Display IPv4 information";
           }
           enum "inet6" {
             description "Display IPv6 information";
           }
         }
       }
       leaf table {
         description "Entries in a particular routing table";
         status deprecated;
         type string;
       }
       leaf group {
         description "IP address and optional prefix length of group";
         type jt:ipprefix;
       }
       leaf source-prefix {
         description "IP address and optional prefix length of source for routes";
         type jt:ipprefix;
       }
       leaf regexp {
         description "Regular expression for session to match";
         type string;
       }
       leaf display-tunnel-name {
         description "Display provider tunnel name instead of branch information";
         type empty;
       }
       leaf display-origin-protocol {
         description "Display originating protocol instead of upstream protocol";
         type empty;
       }
       leaf oif-count {
         description "Display outgoing interface count instead of list";
         type empty;
       }
     }
     output {
       choice output_c {
         case output-tag {
           leaf output {
             type string;
           }
         }
         case actual-tag {
           anyxml multicast-route-information;
         }
         case multichassis-tag {
           anyxml multi-routing-engine-results;
         }
       }
     }
   }
   rpc get-multicast-next-hops-information {
     description "Show the multicast next-hop table";
     input {
       choice daemon-select {
         case logical-system {
           leaf logical-system {
             description "Name of logical system, or 'all'";
             type string {
             }
           }
         }
       }
       leaf verbosity_level {
         default "brief";
         type enumeration {
           enum "terse" {
             description "Display terse output";
           }
           enum "brief" {
             description "Display brief output (default)";
           }
           enum "detail" {
             description "Display detailed output";
           }
         }
       }
       leaf identifier {
         description "ID of next hop";
         type union {
           type uint32;
           type string {
             pattern "<.*>|$.*";
           }
         }
       }
       leaf family {
         description "Address family";
         default "inet";
         type enumeration {
           enum "inet" {
             description "Display IPv4 information";
           }
           enum "inet6" {
             description "Display IPv6 information";
           }
         }
       }
     }
     output {
       choice output_c {
         case output-tag {
           leaf output {
             type string;
           }
         }
         case actual-tag {
           anyxml multicast-next-hops-information;
         }
         case multichassis-tag {
           anyxml multi-routing-engine-results;
         }
       }
     }
   }
   rpc get-satellite-control-next-hop {
     description "Show satellite multicast unicast next-hops";
     input {
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml satellite-control-next-hop;
         }
         case multichassis-tag {
           anyxml multi-routing-engine-results;
         }
       }
     }
   }
   rpc get-multicast-rpf-information {
     description "Show reverse-path forwarding (RPF) source network information";
     input {
       choice daemon-select {
         case logical-system {
           leaf logical-system {
             description "Name of logical system, or 'all'";
             type string {
             }
           }
         }
       }
       leaf instance {
         description "Name of instance";
         type string;
       }
       leaf verbosity_level {
         type enumeration {
           enum "summary" {
             description "Display summary output";
           }
         }
       }
       leaf prefix {
         description "IP address and optional prefix length of host";
         type jt:ipprefix;
       }
       leaf family {
         description "Address family";
         default "inet";
         type enumeration {
           enum "inet" {
             description "Display RPF information for IPv4 ";
           }
           enum "inet6" {
             description "Display RPF information for IPv6 ";
           }
         }
       }
     }
     output {
       choice output_c {
         case output-tag {
           leaf output {
             type string;
           }
         }
         case actual-tag {
           anyxml multicast-rpf-information;
         }
         case multichassis-tag {
           anyxml multi-routing-engine-results;
         }
       }
     }
   }
   rpc get-multicast-scope-information {
     description "Show administratively scoped multicast information";
     input {
       choice daemon-select {
         case logical-system {
           leaf logical-system {
             description "Name of logical system, or 'all'";
             type string {
             }
           }
         }
       }
       leaf instance {
         description "Name of instance";
         type string;
       }
       leaf family {
         description "Address family";
         default "inet";
         type enumeration {
           enum "inet" {
             description "Display IPv4 information";
           }
           enum "inet6" {
             description "Display IPv6 information";
           }
         }
       }
     }
     output {
       choice output_c {
         case output-tag {
           leaf output {
             type string;
           }
         }
         case actual-tag {
           anyxml multicast-scope-information;
         }
         case multichassis-tag {
           anyxml multi-routing-engine-results;
         }
       }
     }
   }
   rpc get-multicast-sessions-information {
     description "Show announced multicast sessions";
     input {
       choice daemon-select {
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
           enum "extensive" {
             description "Display extensive output";
           }
         }
       }
       leaf regexp {
         description "Regular expression for sessions to match";
         type string;
       }
     }
     output {
       choice output_c {
         case output-tag {
           leaf output {
             type string;
           }
         }
         case actual-tag {
           anyxml multicast-sessions-information;
         }
         case multichassis-tag {
           anyxml multi-routing-engine-results;
         }
       }
     }
   }
   rpc get-multicast-statistics-information {
     description "Show multicast statistics";
     input {
       choice daemon-select {
         case logical-system {
           leaf logical-system {
             description "Name of logical system, or 'all'";
             type string {
             }
           }
         }
       }
       leaf instance {
         description "Name of instance";
         type string;
       }
       leaf interface {
         description "Name of interface";
         type string;
       }
       leaf family {
         description "Address family";
         default "inet";
         type enumeration {
           enum "inet" {
             description "Display statistics for IPv4 ";
           }
           enum "inet6" {
             description "Display statistics for IPv6 ";
           }
         }
       }
     }
     output {
       choice output_c {
         case output-tag {
           leaf output {
             type string;
           }
         }
         case actual-tag {
           anyxml multicast-statistics-information;
         }
         case multichassis-tag {
           anyxml multi-routing-engine-results;
         }
       }
     }
   }
   rpc get-satellite-control-statistics {
     description "Show satellite multicast statistics";
     input {
       leaf verbosity_level {
         default "detail";
         type enumeration {
           enum "brief" {
             description "Display brief output (default)";
           }
           enum "detail" {
             description "Display detailed output";
           }
         }
       }
     }
     output {
       choice output_c {
         case output-tag {
           leaf output {
             type string;
           }
         }
         case actual-tag {
           anyxml satellite-control-statistics;
         }
         case multichassis-tag {
           anyxml multi-routing-engine-results;
         }
       }
     }
   }
   rpc get-multicast-tunnels-information {
     description "Show multicast tunnel information";
     status deprecated;
     input {
       choice daemon-select {
         case logical-system {
           leaf logical-system {
             description "Name of logical system, or 'all'";
             type string {
             }
           }
         }
       }
     }
     output {
       choice output_c {
         case output-tag {
           leaf output {
             type string;
           }
         }
         case actual-tag {
           anyxml multicast-tunnels-information;
         }
         case multichassis-tag {
           anyxml multi-routing-engine-results;
         }
       }
     }
   }
   rpc get-multicast-usage-information {
     description "Show multicast usage information";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
       leaf family {
         description "Address family";
         default "inet";
         type enumeration {
           enum "inet" {
             description "Display IPv4 information";
           }
           enum "inet6" {
             description "Display IPv6 information";
           }
         }
       }
     }
     output {
       choice output_c {
         case output-tag {
           leaf output {
             type string;
           }
         }
         case actual-tag {
           anyxml multicast-usage-information;
         }
         case multichassis-tag {
           anyxml multi-routing-engine-results;
         }
       }
     }
   }
   rpc get-multicast-flow-maps-information {
     description "Show configured flow maps";
     input {
       choice daemon-select {
         case logical-system {
           leaf logical-system {
             description "Name of logical system, or 'all'";
             type string {
             }
           }
         }
       }
       leaf instance {
         description "Name of instance";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml multicast-flow-maps-information;
         }
         case multichassis-tag {
           anyxml multi-routing-engine-results;
         }
       }
     }
   }
   rpc get-multicast-interface-information {
     description "Show configured interfaces";
     input {
       choice daemon-select {
         case logical-system {
           leaf logical-system {
             description "Name of logical system, or 'all'";
             type string {
             }
           }
         }
       }
     }
     output {
       choice output_c {
         case output-tag {
           leaf output {
             type string;
           }
         }
         case actual-tag {
           anyxml multicast-interface-information;
         }
         case multichassis-tag {
           anyxml multi-routing-engine-results;
         }
       }
     }
   }
   rpc get-multicast-pim-to-igmp-proxy-information {
     description "Show pim-to-igmp-proxy information";
     input {
       choice daemon-select {
         case logical-system {
           leaf logical-system {
             description "Name of logical system, or 'all'";
             type string {
             }
           }
         }
       }
       leaf instance {
         description "Name of instance";
         type string;
       }
     }
     output {
       choice output_c {
         case output-tag {
           leaf output {
             type string;
           }
         }
         case actual-tag {
           anyxml multicast-pim-to-igmp-proxy-information;
         }
         case multichassis-tag {
           anyxml multi-routing-engine-results;
         }
       }
     }
   }
   rpc get-multicast-pim-to-mld-proxy-information {
     description "Show pim-to-mld-proxy information";
     input {
       choice daemon-select {
         case logical-system {
           leaf logical-system {
             description "Name of logical system, or 'all'";
             type string {
             }
           }
         }
       }
       leaf instance {
         description "Name of instance";
         type string;
       }
     }
     output {
       choice output_c {
         case output-tag {
           leaf output {
             type string;
           }
         }
         case actual-tag {
           anyxml multicast-pim-to-mld-proxy-information;
         }
         case multichassis-tag {
           anyxml multi-routing-engine-results;
         }
       }
     }
   }
   rpc get-multicast-backup-pe-groups-information {
     description "Show backup PE groups";
     input {
       choice daemon-select {
         case logical-system {
           leaf logical-system {
             description "Name of logical system, or 'all'";
             type string {
             }
           }
         }
       }
       leaf instance {
         description "Name of instance";
         type string;
       }
     }
     output {
       choice output_c {
         case output-tag {
           leaf output {
             type string;
           }
         }
         case actual-tag {
           anyxml multicast-backup-pe-groups-information;
         }
         case multichassis-tag {
           anyxml multi-routing-engine-results;
         }
       }
     }
   }
   rpc get-multicast-backup-pe-group-information {
     description "Show information for specified group";
     input {
       choice daemon-select {
         case logical-system {
           leaf logical-system {
             description "Name of logical system, or 'all'";
             type string {
             }
           }
         }
       }
       leaf instance {
         description "Name of instance";
         type string;
       }
       leaf group_name {
         description "Name of the group";
         type string;
         mandatory true;
       }
     }
     output {
       choice output_c {
         case output-tag {
           leaf output {
             type string;
           }
         }
         case actual-tag {
           anyxml multicast-backup-pe-groups-information;
         }
         case multichassis-tag {
           anyxml multi-routing-engine-results;
         }
       }
     }
   }
   rpc get-multicast-backup-pe-address-information {
     description "Show groups a PE address is associated with";
     input {
       choice daemon-select {
         case logical-system {
           leaf logical-system {
             description "Name of logical system, or 'all'";
             type string {
             }
           }
         }
       }
       leaf pe_address {
         description "IP address of the PE";
         type jt:ipaddr;
         mandatory true;
       }
     }
     output {
       choice output_c {
         case output-tag {
           leaf output {
             type string;
           }
         }
         case actual-tag {
           anyxml multicast-backup-pe-address-information;
         }
         case multichassis-tag {
           anyxml multi-routing-engine-results;
         }
       }
     }
   }
   rpc get-multicast-snooping-route-information {
     description "Show the multicast snooping routing table";
     input {
       leaf logical-system {
         description "Name of logical system, or 'all'";
         type string {
         }
       }
       leaf mode {
         default "data";
         type enumeration {
           enum "all" {
             description "Display all route entries";
           }
           enum "active" {
             description "Display active route entries";
           }
           enum "inactive" {
             description "Display inactive route entries";
           }
           enum "control" {
             description "Display control route entries";
           }
           enum "data" {
             description "Display data route entries";
           }
         }
       }
       leaf verbosity_level {
         default "brief";
         type enumeration {
           enum "brief" {
             description "Display brief output (default)";
           }
           enum "detail" {
             description "Display detailed output";
           }
           enum "extensive" {
             description "Display extensive output";
           }
         }
       }
       leaf family {
         description "Address family";
         type enumeration {
           enum "inet" {
             description "Display IPv4 information";
           }
           enum "inet6" {
             description "Display IPv6 information";
           }
         }
       }
       leaf vlan-id {
         description "VLAN ID for a learning domain";
         type union {
           type string {
             pattern "<.*>|$.*";
           }
           type uint32 {
             range "0 .. 4094";
           }
         }
       }
       leaf qualified-vlan {
         description "VLAN ID for a Qualified VLAN";
         type union {
           type string {
             pattern "<.*>|$.*";
           }
           type uint32 {
             range "0 .. 4094";
           }
         }
       }
       leaf mesh-group {
         description "Name of a mesh-group";
         type string;
       }
       leaf group {
         description "IP address and optional prefix length of group";
         type jt:ipprefix;
       }
       leaf source-prefix {
         description "IP address and optional prefix length of source";
         type jt:ipprefix;
       }
       leaf regexp {
         description "Regular expression for session to match";
         type string;
       }
       leaf bridge-domain {
         description "Name of bridge-domain";
         type string;
       }
       leaf vlan {
         description "Name of VLAN";
         type string;
       }
       leaf instance {
         description "Name of routing-instance";
         type string;
       }
     }
     output {
       choice output_c {
         case output-tag {
           leaf output {
             type string;
           }
         }
         case actual-tag {
           anyxml multicast-route-information;
         }
         case multichassis-tag {
           anyxml multi-routing-engine-results;
         }
       }
     }
   }
   rpc get-satellite-control-multicast {
     description "Show the satellite multicast snooping information";
     input {
       leaf verbosity_level {
         default "brief";
         type enumeration {
           enum "brief" {
             description "Display brief output (default)";
           }
           enum "detail" {
             description "Display detailed output";
           }
           enum "extensive" {
             description "Display extensive output";
           }
         }
       }
       leaf vswitch-name {
         description "Virtual switch name";
         type string;
       }
       leaf bridge-domain-name {
         description "Bridge domain name";
         type string;
       }
       leaf vlan-name {
         description "Vlan name";
         type string;
       }
       leaf group {
         description "Multicast Group Address";
         type jt:ipaddr;
       }
       leaf source {
         description "Source Address";
         type jt:ipaddr;
       }
     }
     output {
       choice output_c {
         case output-tag {
           leaf output {
             type string;
           }
         }
         case actual-tag {
           anyxml satellite-control-multicast;
         }
         case multichassis-tag {
           anyxml multi-routing-engine-results;
         }
       }
     }
   }
   rpc get-multicast-snooping-next-hops-information {
     description "Show the multicast next-hop snooping table";
     input {
       leaf verbosity_level {
         default "brief";
         type enumeration {
           enum "brief" {
             description "Display brief output (default)";
           }
           enum "detail" {
             description "Display detailed output";
           }
         }
       }
       leaf identifier {
         description "ID of next hop";
         type union {
           type uint32;
           type string {
             pattern "<.*>|$.*";
           }
         }
       }
       leaf family {
         description "Address family";
         type enumeration {
           enum "inet" {
             description "Display IPv4 information";
           }
           enum "inet6" {
             description "Display IPv6 information";
           }
         }
       }
     }
     output {
       choice output_c {
         case output-tag {
           leaf output {
             type string;
           }
         }
         case actual-tag {
           anyxml multicast-next-hops-information;
         }
         case multichassis-tag {
           anyxml multi-routing-engine-results;
         }
       }
     }
   }
   rpc get-satellite-control-indirect-next-hop {
     description "Show satellite multicast next-hops";
     input {
       leaf verbosity_level {
         default "brief";
         type enumeration {
           enum "brief" {
             description "Display brief output (default)";
           }
           enum "detail" {
             description "Display detailed output";
           }
           enum "extensive" {
             description "Display extensive output";
           }
         }
       }
       leaf nexthop-id {
         description "Next-hop ID";
         type union {
           type int32;
           type string {
             pattern "<.*>|$.*";
           }
         }
       }
     }
     output {
       choice output_c {
         case output-tag {
           leaf output {
             type string;
           }
         }
         case actual-tag {
           anyxml satellite-control-indirect-next-hop;
         }
         case multichassis-tag {
           anyxml multi-routing-engine-results;
         }
       }
     }
   }
   rpc get-satellite-control-ecid {
     description "Show the satellite multicast ECID mapping database";
     input {
       leaf verbosity_level {
         default "brief";
         type enumeration {
           enum "brief" {
             description "Display brief output (default)";
           }
           enum "detail" {
             description "Display detailed output";
           }
           enum "extensive" {
             description "Display extensive output";
           }
         }
       }
       leaf device-id {
         description "Device ID";
         type union {
           type int32;
           type string {
             pattern "<.*>|$.*";
           }
         }
       }
       leaf ecid {
         description "ECID";
         type union {
           type int32;
           type string {
             pattern "<.*>|$.*";
           }
         }
       }
       leaf reference-id {
         description "Reference ID";
         type union {
           type int32;
           type string {
             pattern "<.*>|$.*";
           }
         }
       }
     }
     output {
       choice output_c {
         case output-tag {
           leaf output {
             type string;
           }
         }
         case actual-tag {
           anyxml satellite-control-ecid;
         }
         case multichassis-tag {
           anyxml multi-routing-engine-results;
         }
       }
     }
   }
   rpc get-satellite-control-summary {
     description "Show satellite multicast summary information";
     input {
       leaf verbosity_level {
         default "detail";
         type enumeration {
           enum "brief" {
             description "Display brief output (default)";
           }
           enum "detail" {
             description "Display detailed output";
           }
         }
       }
     }
     output {
       choice output_c {
         case output-tag {
           leaf output {
             type string;
           }
         }
         case actual-tag {
           anyxml satellite-control-summary;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
