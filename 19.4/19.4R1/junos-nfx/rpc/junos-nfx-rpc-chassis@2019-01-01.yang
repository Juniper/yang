/*
 * Copyright (c) 2019 Juniper Networks, Inc.
 * All rights reserved.
 */
 module junos-nfx-rpc-chassis {
   namespace "http://yang.juniper.net/junos-nfx/rpc/chassis";

   prefix chassis;

   import junos-common-types {
     prefix jt;
     revision-date 2019-01-01;
   }

   organization "Juniper Networks, Inc.";

   contact "yang-support@juniper.net";

   description "Junos RPC YANG module for chassis command(s)";

   revision 2019-01-01 {
     description "Junos: 19.4R1.9";
   }

   rpc get-personality-information {
     description "Show chassis's current personality";
     output {
       choice output_c {
         case output-tag {
           leaf output {
             type string;
           }
         }
         case actual-tag {
           anyxml personality-information;
         }
         case multichassis-tag {
           anyxml multi-routing-engine-results;
         }
       }
     }
   }
   rpc get-uft-information {
     description "Show member's current UFT configuration";
     output {
       choice output_c {
         case output-tag {
           leaf output {
             type string;
           }
         }
         case actual-tag {
           anyxml uft-information;
         }
         case multichassis-tag {
           anyxml multi-routing-engine-results;
         }
       }
     }
   }
   rpc get-system-mode-information {
     description "Show member's current system-mode configuration";
     output {
       choice output_c {
         case output-tag {
           leaf output {
             type string;
           }
         }
         case actual-tag {
           anyxml system-mode-information;
         }
         case multichassis-tag {
           anyxml multi-routing-engine-results;
         }
       }
     }
   }
   rpc get-power-usage-information {
     description "Show Chassis Power Usages";
     output {
       choice output_c {
         case output-tag {
           leaf output {
             type string;
           }
         }
         case actual-tag {
           anyxml power-usage-information;
         }
         case multichassis-tag {
           anyxml multi-routing-engine-results;
         }
       }
     }
   }
   rpc get-power-usage-information-detail {
     description "Show chassis power usage detail";
     output {
       choice output_c {
         case output-tag {
           leaf output {
             type string;
           }
         }
         case actual-tag {
           anyxml power-usage-information-detail;
         }
         case multichassis-tag {
           anyxml multi-routing-engine-results;
         }
       }
     }
   }
   rpc get-fru-power-on-sequence {
     description "Show chassis fru power on sequence";
     output {
       choice output_c {
         case output-tag {
           leaf output {
             type string;
           }
         }
         case actual-tag {
           anyxml fru-power-on-sequence;
         }
         case multichassis-tag {
           anyxml multi-routing-engine-results;
         }
       }
     }
   }
   rpc get-alarm-information {
     description "Show alarm status";
     output {
       choice output_c {
         case output-tag {
           leaf output {
             type string;
           }
         }
         case actual-tag {
           anyxml alarm-information;
         }
         case multichassis-tag {
           anyxml multi-routing-engine-results;
         }
       }
     }
   }
   rpc get-fpc-alarm-information {
     description "Show alarm status for a FPC";
     input {
       leaf fpc-slot {
         description "Flexible PIC Controller slot number";
         type union {
           type string {
             pattern "<.*>|$.*";
           }
           type uint32;
         }
         mandatory true;
       }
     }
     output {
       choice output_c {
         case output-tag {
           leaf output {
             type string;
           }
         }
         case actual-tag {
           anyxml alarm-information;
         }
         case multichassis-tag {
           anyxml multi-routing-engine-results;
         }
       }
     }
   }
   rpc get-chassis-alarm-satellite-information {
     description "Show alarm status for satellite devices";
     input {
       leaf fpc-slot {
         description "Satellite slot number";
         type union {
           type string {
             pattern "<.*>|$.*";
           }
           type uint16 {
             range "65 .. 254";
           }
         }
       }
     }
     output {
       choice output_c {
         case output-tag {
           leaf output {
             type string;
           }
         }
         case actual-tag {
           anyxml chassis-alarm-satellite-information;
         }
         case multichassis-tag {
           anyxml multi-routing-engine-results;
         }
       }
     }
   }
   rpc get-jam-test-information {
     description "Show Jam API test result";
     input {
       leaf detail {
         description "Display detailed output";
         type empty;
       }
       leaf fpc-slot {
         description "FPC slot number";
         type union {
           type string {
             pattern "<.*>|$.*";
           }
           type uint32;
         }
       }
     }
     output {
       choice output_c {
         case output-tag {
           leaf output {
             type string;
           }
         }
         case actual-tag {
           anyxml jam-test-information;
         }
         case multichassis-tag {
           anyxml multi-routing-engine-results;
         }
       }
     }
   }
   rpc get-chassis-errors {
     description "Show chassis errors";
     input {
       leaf error-id {
         description "Error identifier for the error to be cleared";
         type string {
           length "1 .. 255";
         }
         mandatory true;
       }
       leaf fpc-slot {
         description "Slot number of FPC";
         type union {
           type string {
             pattern "<.*>|$.*";
           }
           type uint32;
         }
         mandatory true;
       }
     }
     output {
       choice output_c {
         case output-tag {
           leaf output {
             type string;
           }
         }
         case actual-tag {
           anyxml chassis-error-information;
         }
         case multichassis-tag {
           anyxml multi-routing-engine-results;
         }
       }
     }
   }
   rpc get-chassis-active-errors {
     description "Show active errors";
     input {
       leaf fpc-slot {
         description "Slot number of FPC";
         type union {
           type string {
             pattern "<.*>|$.*";
           }
           type uint32;
         }
       }
     }
     output {
       choice output_c {
         case output-tag {
           leaf output {
             type string;
           }
         }
         case actual-tag {
           anyxml chassis-active-error-information;
         }
         case multichassis-tag {
           anyxml multi-routing-engine-results;
         }
       }
     }
   }
   rpc get-active-error-information-detail {
     description "Show detailed output";
     input {
       leaf fpc-slot {
         description "Slot number of FPC";
         type union {
           type string {
             pattern "<.*>|$.*";
           }
           type uint32;
         }
       }
     }
     output {
       choice output_c {
         case output-tag {
           leaf output {
             type string;
           }
         }
         case actual-tag {
           anyxml chassis-errors-detail-information;
         }
         case multichassis-tag {
           anyxml multi-routing-engine-results;
         }
       }
     }
   }
   rpc get-chassis-beacon-information {
     description "Show beacon status";
     input {
       choice which-arg {
         case all {
           leaf all {
             description "Beacons in ON/OFF state";
             type enumeration {
               enum "off" {
                 description "Beacons in OFF state";
               }
               enum "on" {
                 description "Beacons in ON state";
               }
             }
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
           leaf service-node {
             description "Service Node slot number";
             type union {
               type string {
                 pattern "<.*>|$.*";
               }
               type uint32 {
                 range "0 .. 1";
               }
             }
           }
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       choice output_c {
         case output-tag {
           leaf output {
             type string;
           }
         }
         case actual-tag {
           anyxml chassis-beacon-information;
         }
         case multichassis-tag {
           anyxml multi-routing-engine-results;
         }
       }
     }
   }
   rpc network-services {
     description "Show chassis network services";
     output {
       choice output_c {
         case output-tag {
           leaf output {
             type string;
           }
         }
         case actual-tag {
           anyxml network-services;
         }
         case multichassis-tag {
           anyxml multi-routing-engine-results;
         }
       }
     }
   }
   rpc ambient-temperature {
     description "Show chassis ambient temperature";
     output {
       choice output_c {
         case output-tag {
           leaf output {
             type string;
           }
         }
         case actual-tag {
           anyxml ambient-temperature;
         }
         case multichassis-tag {
           anyxml multi-routing-engine-results;
         }
       }
     }
   }
   rpc get-clock-synchronization-information {
     description "Show clock synchronization information";
     input {
       uses command-forwarding;
       leaf interface {
         description "Name of physical interface";
         type string;
       }
       leaf extensive {
         description "Show clock synchronization information in detail";
         type empty;
       }
     }
     output {
       choice output_c {
         case output-tag {
           leaf output {
             type string;
           }
         }
         case actual-tag {
           anyxml clock-synchronization-information;
         }
         case multichassis-tag {
           anyxml multi-routing-engine-results;
         }
       }
     }
   }
   rpc get-craft-information {
     description "Show craft interface status";
     output {
       choice output_c {
         case output-tag {
           leaf output {
             type string;
           }
         }
         case actual-tag {
           anyxml craft-information;
         }
         case multichassis-tag {
           anyxml multi-routing-engine-results;
         }
       }
     }
   }
   rpc get-ethernet-switch-information {
     description "Show Ethernet switch information";
     input {
       uses command-forwarding;
       leaf ethernet-switch-type {
         description "Show Ethernet switch information";
         type enumeration {
           enum "get-ethernet-switch-cb-information" {
             description "Show Ethernet switch Control Board information";
           }
           enum "get-ethernet-switch-fpc-information" {
             description "Show Ethernet switch Front Card information";
           }
         }
         mandatory true;
       }
       leaf detail {
         description "Show Ethernet switch traffic statistics";
         type empty;
       }
       leaf port {
         description "Port number";
         type union {
           type string {
             pattern "<.*>|$.*";
           }
           type uint32 {
             range "1 .. 28";
           }
         }
       }
       leaf slot {
         description "Front card FPC slot number";
         type union {
           type string {
             pattern "<.*>|$.*";
           }
           type uint32 {
             range "0 .. 7";
           }
         }
       }
     }
     output {
       choice output_c {
         case output-tag {
           leaf output {
             type string;
           }
         }
         case actual-tag {
           anyxml ethernet-switch-information;
         }
         case multichassis-tag {
           anyxml multi-routing-engine-results;
         }
       }
     }
   }
   rpc get-ethernet-switch-statistics-information {
     description "Show Ethernet switch traffic statistics";
     input {
       uses command-forwarding;
       leaf switch {
         description "Switch number";
         type union {
           type string {
             pattern "<.*>|$.*";
           }
           type uint32;
         }
       }
       leaf port {
         description "Port number";
         type union {
           type string {
             pattern "<.*>|$.*";
           }
           type uint32;
         }
       }
     }
     output {
       choice output_c {
         case output-tag {
           leaf output {
             type string;
           }
         }
         case actual-tag {
           anyxml ethernet-switch-statistics-information;
         }
         case multichassis-tag {
           anyxml multi-routing-engine-results;
         }
       }
     }
   }
   rpc get-ethernet-switch-error-information {
     description "Show accumulated Ethernet switch errors";
     input {
       uses command-forwarding;
       leaf switch {
         description "Switch number";
         type union {
           type string {
             pattern "<.*>|$.*";
           }
           type uint32;
         }
       }
       leaf port {
         description "Port number";
         type union {
           type string {
             pattern "<.*>|$.*";
           }
           type uint32;
         }
       }
     }
     output {
       choice output_c {
         case output-tag {
           leaf output {
             type string;
           }
         }
         case actual-tag {
           anyxml ethernet-switch-error-information;
         }
         case multichassis-tag {
           anyxml multi-routing-engine-results;
         }
       }
     }
   }
   rpc get-feb-redundancy-information {
     description "Show Forwarding Engine Board redundancy information";
     output {
       choice output_c {
         case output-tag {
           leaf output {
             type string;
           }
         }
         case actual-tag {
           anyxml feb-redundancy-information;
         }
         case multichassis-tag {
           anyxml multi-routing-engine-results;
         }
       }
     }
   }
   rpc get-feb-redundancy-error-information {
     description "Show error information";
     output {
       choice output_c {
         case output-tag {
           leaf output {
             type string;
           }
         }
         case actual-tag {
           anyxml feb-redundancy-error-information;
         }
         case multichassis-tag {
           anyxml multi-routing-engine-results;
         }
       }
     }
   }
   rpc get-feb-redundancy-group-information {
     description "Show FEB redundancy group information";
     input {
       leaf group {
         description "Name of FEB redundancy group";
         type string;
         mandatory true;
       }
       leaf errors {
         description "Include error information";
         type empty;
       }
     }
     output {
       choice output_c {
         case output-tag {
           leaf output {
             type string;
           }
         }
         case actual-tag {
           anyxml feb-redundancy-group-information;
         }
         case multichassis-tag {
           anyxml multi-routing-engine-results;
         }
       }
     }
   }
   rpc get-fpc-feb-connectivity-information {
     description "Show connectivity between Flexible PIC Concentrators and Forwarding Engine boards";
     output {
       choice output_c {
         case output-tag {
           leaf output {
             type string;
           }
         }
         case actual-tag {
           anyxml fpc-feb-connectivity;
         }
         case multichassis-tag {
           anyxml multi-routing-engine-results;
         }
       }
     }
   }
   rpc get-ioc-npc-connectivity-information {
     description "Show connectivity between IOC and NPC";
     output {
       choice output_c {
         case output-tag {
           leaf output {
             type string;
           }
         }
         case actual-tag {
           anyxml ioc-npc-connectivity;
         }
         case multichassis-tag {
           anyxml multi-routing-engine-results;
         }
       }
     }
   }
   rpc get-chassis-memory-usage-chassisd {
     description "Dump LMLD data to /var/log/chassisd_memory_usage";
     input {
       leaf root {
         type string;
       }
     }
     output {
       choice output_c {
         case output-tag {
           leaf output {
             type string;
           }
         }
         case multichassis-tag {
           anyxml multi-routing-engine-results;
         }
       }
     }
   }
   rpc get-chassis-zones-information {
     description "Show chassis cooling zones information";
     input {
       uses command-forwarding;
       leaf detail {
         description "Display detailed output";
         type empty;
       }
     }
     output {
       choice output_c {
         case output-tag {
           leaf output {
             type string;
           }
         }
         case actual-tag {
           anyxml chassis-zones-information;
         }
         case multichassis-tag {
           anyxml multi-routing-engine-results;
         }
       }
     }
   }
   rpc get-environment-information {
     description "Show component status and temperature, cooling system speeds";
     input {
       uses command-forwarding;
       leaf monitored {
         description "Show items whose temperatures are monitored";
         type empty;
       }
     }
     output {
       choice output_c {
         case output-tag {
           leaf output {
             type string;
           }
         }
         case actual-tag {
           anyxml environment-information;
         }
         case multichassis-tag {
           anyxml multi-routing-engine-results;
         }
       }
     }
   }
   rpc get-environment-sib-information {
     description "Show Switch Interface Board information";
     input {
       uses command-forwarding;
       leaf sib-slot {
         description "SIB slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-fan-information {
     description "Show fan status";
     input {
       uses command-forwarding;
       leaf slot {
         description "Fantray slot number";
         type union {
           type string {
             pattern "<.*>|$.*";
           }
           type uint32 {
             range "0 .. 6";
           }
         }
       }
     }
     output {
       choice output_c {
         case output-tag {
           leaf output {
             type string;
           }
         }
         case actual-tag {
           anyxml fan-information;
         }
         case multichassis-tag {
           anyxml multi-routing-engine-results;
         }
       }
     }
   }
   rpc get-environment-fpc-information {
     description "Show Flexible PIC Concentrator information";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-fpc-satellite-info {
     description "Show environment FPC details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-fpc-satellite-information;
         }
         case multichassis-tag {
           anyxml multi-routing-engine-results;
         }
       }
     }
   }
   rpc get-environment-fpm-information {
     description "Show craft interface information";
     output {
       choice output_c {
         case output-tag {
           leaf output {
             type string;
           }
         }
         case actual-tag {
           anyxml environment-component-information;
         }
         case multichassis-tag {
           anyxml multi-routing-engine-results;
         }
       }
     }
   }
   rpc get-environment-mcs-information {
     description "Show Miscellaneous Control Subsystem information";
     input {
       leaf slot {
         description "MCS slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-pcg-information {
     description "Show Packet Forwarding Engine Clock Generator information";
     input {
       leaf slot {
         description "PCG slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-scg-information {
     description "Show SONET Clock Generator information";
     input {
       uses command-forwarding;
       leaf slot {
         description "SCG slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-ccg-information {
     description "Show clock generator information";
     input {
       leaf slot {
         description "CCG slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-cb-information {
     description "Show Control Board information";
     input {
       uses command-forwarding;
       leaf slot {
         description "CB slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-psu-information {
     description "Show Power Supply Unit information";
     input {
       uses command-forwarding;
       leaf slot {
         description "PSU slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-power-supply-unit-information {
     description "Show power supply unit information";
     input {
       leaf slot {
         description "FPC slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-pem-information {
     description "Show Power Entry Module information";
     input {
       uses command-forwarding;
       leaf slot {
         description "PEM slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-pem-satellite-info {
     description "Show environment PEM details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-pem-satellite-information;
         }
         case multichassis-tag {
           anyxml multi-routing-engine-results;
         }
       }
     }
   }
   rpc get-environment-psm-information {
     description "Show Power Supply Module information";
     input {
       uses command-forwarding;
       leaf slot {
         description "PSM slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-sfb-information {
     description "Show SFB status";
     input {
       uses command-forwarding;
       leaf sfb-slot {
         description "SFB slot number";
         type union {
           type string {
             pattern "<.*>|$.*";
           }
           type uint32 {
             range "0 .. 7";
           }
         }
       }
     }
     output {
       choice output_c {
         case output-tag {
           leaf output {
             type string;
           }
         }
         case actual-tag {
           anyxml sfb-information;
         }
         case multichassis-tag {
           anyxml multi-routing-engine-results;
         }
       }
     }
   }
   rpc get-environment-adc-information {
     description "Show adc status";
     input {
       uses command-forwarding;
       leaf adc-slot {
         description "ADC slot number";
         type union {
           type string {
             pattern "<.*>|$.*";
           }
           type uint32;
         }
       }
     }
     output {
       choice output_c {
         case output-tag {
           leaf output {
             type string;
           }
         }
         case actual-tag {
           anyxml sfb-information;
         }
         case multichassis-tag {
           anyxml multi-routing-engine-results;
         }
       }
     }
   }
   rpc get-environment-pdu-information {
     description "Show Power Distribution Unit information";
     input {
       leaf slot {
         description "PDU slot number";
         type union {
           type string {
             pattern "<.*>|$.*";
           }
           type uint32 {
             range "0 .. 3";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-re-information {
     description "Show Routing Engine information";
     input {
       uses command-forwarding;
       leaf slot {
         description "Routing Engine slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-re-satellite-info {
     description "Show environment routing engine details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-routing-engine-satellite-information;
         }
         case multichassis-tag {
           anyxml multi-routing-engine-results;
         }
       }
     }
   }
   rpc get-environment-sfm-information {
     description "Show Switching and Forwarding Module information";
     input {
       leaf sfm_plane {
         description "SFM slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-feb-information {
     description "Show Forwarding Engine Board information";
     input {
       leaf slot {
         description "FEB slot number";
         type union {
           type string {
             pattern "<.*>|$.*";
           }
           type uint32;
         }
       }
     }
     output {
       choice output_c {
         case output-tag {
           leaf output {
             type string;
           }
         }
         case actual-tag {
           anyxml environment-component-information;
         }
         case multichassis-tag {
           anyxml multi-routing-engine-results;
         }
       }
     }
   }
   rpc get-environment-cip-information {
     description "Show Connector Interface Panel Information";
     input {
       leaf slot {
         description "CIP slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-environment-service-node-information {
     description "Show Compute Node Environment information";
     input {
       leaf slot {
         description "Service node slot number";
         type union {
           type string {
             pattern "<.*>|$.*";
           }
           type uint32 {
             range "0 .. 1";
           }
         }
       }
     }
     output {
       choice output_c {
         case output-tag {
           leaf output {
             type string;
           }
         }
         case actual-tag {
           anyxml environment-component-information;
         }
         case multichassis-tag {
           anyxml multi-routing-engine-results;
         }
       }
     }
   }
   rpc get-chassis-environment-satellite-information {
     description "Show environment details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-environment-satellite-information;
         }
         case multichassis-tag {
           anyxml multi-routing-engine-results;
         }
       }
     }
   }
   rpc get-firmware-information {
     description "Show firmware and operating system version for components";
     input {
       uses command-forwarding;
       leaf fpc {
         description "Flexible PIC Controller slot number";
         type union {
           type string {
             pattern "<.*>|$.*";
           }
           type uint32;
         }
       }
     }
     output {
       choice output_c {
         case output-tag {
           leaf output {
             type string;
           }
         }
         case actual-tag {
           anyxml firmware-information;
         }
         case multichassis-tag {
           anyxml multi-routing-engine-results;
         }
       }
     }
   }
   rpc get-firmware-information-detail {
     description "Show detailed output";
     output {
       choice output_c {
         case output-tag {
           leaf output {
             type string;
           }
         }
         case actual-tag {
           anyxml hardware-version-information;
         }
         case multichassis-tag {
           anyxml multi-routing-engine-results;
         }
       }
     }
   }
   rpc get-chassis-firmware-satellite-information {
     description "Show FPC firmware details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-firmware-satellite-information;
         }
         case multichassis-tag {
           anyxml multi-routing-engine-results;
         }
       }
     }
   }
   rpc get-usb-storage-status {
     description "Show USB storage status";
     output {
       choice output_c {
         case output-tag {
           leaf output {
             type string;
           }
         }
         case actual-tag {
           anyxml usb-storage-status;
         }
         case multichassis-tag {
           anyxml multi-routing-engine-results;
         }
       }
     }
   }
   rpc get-fpc-information {
     description "Show Flexible PIC Concentrator status";
     input {
       uses command-forwarding;
       leaf detail {
         description "Display detailed output";
         type empty;
       }
       leaf fpc-slot {
         description "FPC slot number";
         type union {
           type string {
             pattern "<.*>|$.*";
           }
           type uint32;
         }
       }
     }
     output {
       choice output_c {
         case output-tag {
           leaf output {
             type string;
           }
         }
         case actual-tag {
           anyxml fpc-information;
         }
         case multichassis-tag {
           anyxml multi-routing-engine-results;
         }
       }
     }
   }
   rpc get-pic-information {
     description "Show Physical Interface Cards installed in FPC";
     input {
       uses command-forwarding;
       leaf slot {
         description "FPC slot number";
         type union {
           type string {
             pattern "<.*>|$.*";
           }
           type uint32;
         }
       }
     }
     output {
       choice output_c {
         case output-tag {
           leaf output {
             type string;
           }
         }
         case actual-tag {
           anyxml fpc-information;
         }
         case multichassis-tag {
           anyxml multi-routing-engine-results;
         }
       }
     }
   }
   rpc get-fpc-ether-types-information {
     description "Show Ether Types";
     input {
       leaf slot {
         description "FPC slot number";
         type union {
           type string {
             pattern "<.*>|$.*";
           }
           type uint32;
         }
       }
     }
     output {
       choice output_c {
         case output-tag {
           leaf output {
             type string;
           }
         }
         case actual-tag {
           anyxml fpc-ether-types-information;
         }
         case multichassis-tag {
           anyxml multi-routing-engine-results;
         }
       }
     }
   }
   rpc get-fpc-port-information {
     description "Show Port status installed in FPC";
     input {
       leaf slot {
         description "FPC slot number";
         type union {
           type string {
             pattern "<.*>|$.*";
           }
           type uint32;
         }
       }
     }
     output {
       choice output_c {
         case output-tag {
           leaf output {
             type string;
           }
         }
         case actual-tag {
           anyxml fpc-port-information;
         }
         case multichassis-tag {
           anyxml multi-routing-engine-results;
         }
       }
     }
   }
   rpc get-fpc-error-information {
     description "Show ASIC errors on all the FPC's";
     input {
       uses command-forwarding;
       leaf fpc-slot {
         description "FPC slot number";
         type union {
           type string {
             pattern "<.*>|$.*";
           }
           type uint32;
         }
       }
       leaf detail {
         description "Display detailed output";
         type empty;
       }
       leaf scope {
         description "Error scope";
         type enumeration {
           enum "board" {
             description "Show board errors";
           }
           enum "pfe" {
             description "Show pfe errors";
           }
         }
       }
       leaf category {
         description "Error category";
         type enumeration {
           enum "functional" {
             description "Functional category errors";
           }
           enum "memory" {
             description "Memory category errors";
           }
           enum "io" {
             description "Io category errors";
           }
           enum "storage" {
             description "Storage category errors";
           }
           enum "switch" {
             description "Switch category errors";
           }
           enum "processing" {
             description "Processing category errors";
           }
         }
       }
     }
     output {
       choice output_c {
         case output-tag {
           leaf output {
             type string;
           }
         }
         case actual-tag {
           anyxml fpc-error-information;
         }
         case multichassis-tag {
           anyxml multi-routing-engine-results;
         }
       }
     }
   }
   rpc get-fpc-error-i2c {
     description "Display I2C error statistics";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml fpc-tvp-error-information;
         }
         case multichassis-tag {
           anyxml multi-routing-engine-results;
         }
       }
     }
   }
   rpc get-fpc-optical-information {
     description "Show optical properties of the card";
     output {
       choice output_c {
         case output-tag {
           leaf output {
             type string;
           }
         }
         case actual-tag {
           anyxml fpc-optical-information;
         }
         case multichassis-tag {
           anyxml multi-routing-engine-results;
         }
       }
     }
   }
   rpc get-fpc-optical-mfg-info-information {
     description "Show mfg-info of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-mfg-info-information;
         }
         case multichassis-tag {
           anyxml multi-routing-engine-results;
         }
       }
     }
   }
   rpc get-fpc-optical-status-information {
     description "Show status of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-status-information;
         }
         case multichassis-tag {
           anyxml multi-routing-engine-results;
         }
       }
     }
   }
   rpc get-fpc-optical-alarms-information {
     description "Show alarms of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-alarms-information;
         }
         case multichassis-tag {
           anyxml multi-routing-engine-results;
         }
       }
     }
   }
   rpc get-fpc-optical-edfa-information {
     description "Show edfa of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-edfa-information;
         }
         case multichassis-tag {
           anyxml multi-routing-engine-results;
         }
       }
     }
   }
   rpc get-fpc-optical-ocm-information {
     description "Show ocm of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-ocm-information;
         }
         case multichassis-tag {
           anyxml multi-routing-engine-results;
         }
       }
     }
   }
   rpc get-fpc-optical-wss-information {
     description "Show wss of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-wss-information;
         }
         case multichassis-tag {
           anyxml multi-routing-engine-results;
         }
       }
     }
   }
   rpc get-fpc-optical-pm-current-information {
     description "Show pm-current of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-pm-current-information;
         }
         case multichassis-tag {
           anyxml multi-routing-engine-results;
         }
       }
     }
   }
   rpc get-fpc-optical-pm-interval-information {
     description "Show pm-interval of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-pm-interval-information;
         }
         case multichassis-tag {
           anyxml multi-routing-engine-results;
         }
       }
     }
   }
   rpc get-fpc-optical-pm-currentday-information {
     description "Show pm-currentday of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-pm-currentday-information;
         }
         case multichassis-tag {
           anyxml multi-routing-engine-results;
         }
       }
     }
   }
   rpc get-fpc-optical-pm-previousday-information {
     description "Show pm-previousday of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-pm-previousday-information;
         }
         case multichassis-tag {
           anyxml multi-routing-engine-results;
         }
       }
     }
   }
   rpc get-fpc-optical-amplifier-topology-information {
     description "Show amplifier-topology of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml fpc-optical-amplifier-topology-information;
         }
         case multichassis-tag {
           anyxml multi-routing-engine-results;
         }
       }
     }
   }
   rpc get-fpc-optical-topology-information {
     description "Show IPLC Topology Information";
     input {
       leaf fpc-slot {
         description "FPC slot number";
         type union {
           type string {
             pattern "<.*>|$.*";
           }
           type uint32;
         }
         mandatory true;
       }
       leaf detail {
         description "Show IPLC Topology Detailed Information";
         type empty;
       }
     }
     output {
       choice output_c {
         case output-tag {
           leaf output {
             type string;
           }
         }
         case actual-tag {
           anyxml fpc-optical-topology-information;
         }
         case multichassis-tag {
           anyxml multi-routing-engine-results;
         }
       }
     }
   }
   rpc get-fpc-optical-amplifier-chain-information {
     description "Show in-line amplifier amplifier-chain information";
     output {
       choice output_c {
         case output-tag {
           leaf output {
             type string;
           }
         }
         case actual-tag {
           anyxml fpc-optical-amplifier-chain-information;
         }
         case multichassis-tag {
           anyxml multi-routing-engine-results;
         }
       }
     }
   }
   rpc get-fpc-optical-ila-summary-information {
     description "Show summary of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-summary-information;
         }
         case multichassis-tag {
           anyxml multi-routing-engine-results;
         }
       }
     }
   }
   rpc get-fpc-optical-ila-edfa-information {
     description "Show edfa of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-edfa-information;
         }
         case multichassis-tag {
           anyxml multi-routing-engine-results;
         }
       }
     }
   }
   rpc get-fpc-optical-ila-osc-information {
     description "Show osc of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-osc-information;
         }
         case multichassis-tag {
           anyxml multi-routing-engine-results;
         }
       }
     }
   }
   rpc get-fpc-optical-ila-voa-information {
     description "Show voa of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-voa-information;
         }
         case multichassis-tag {
           anyxml multi-routing-engine-results;
         }
       }
     }
   }
   rpc get-fpc-optical-ila-alarms-information {
     description "Show alarms of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-alarms-information;
         }
         case multichassis-tag {
           anyxml multi-routing-engine-results;
         }
       }
     }
   }
   rpc get-fpc-optical-ila-pm-current-information {
     description "Show pm-current of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-pm-current-information;
         }
         case multichassis-tag {
           anyxml multi-routing-engine-results;
         }
       }
     }
   }
   rpc get-fpc-optical-ila-pm-interval-information {
     description "Show pm-interval of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-pm-interval-information;
         }
         case multichassis-tag {
           anyxml multi-routing-engine-results;
         }
       }
     }
   }
   rpc get-fpc-optical-ila-pm-currentday-information {
     description "Show pm-currentday of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-pm-currentday-information;
         }
         case multichassis-tag {
           anyxml multi-routing-engine-results;
         }
       }
     }
   }
   rpc get-fpc-optical-ila-pm-previousday-information {
     description "Show pm-previousday of ila module";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case actual-tag {
           anyxml fpc-optical-ila-pm-previousday-information;
         }
         case multichassis-tag {
           anyxml multi-routing-engine-results;
         }
       }
     }
   }
   rpc get-adc-information {
     description "Show ADC status";
     output {
       choice output_c {
         case output-tag {
           leaf output {
             type string;
           }
         }
         case actual-tag {
           anyxml adc-information;
         }
         case multichassis-tag {
           anyxml multi-routing-engine-results;
         }
       }
     }
   }
   rpc get-vcpu-information {
     description "Show Visibility CPU status";
     input {
       uses command-forwarding;
       leaf detail {
         description "Display detailed output";
         type empty;
       }
       leaf slot {
         description "VCPU slot number";
         type union {
           type string {
             pattern "<.*>|$.*";
           }
           type uint32;
         }
       }
     }
     output {
       choice output_c {
         case output-tag {
           leaf output {
             type string;
           }
         }
         case actual-tag {
           anyxml vcpu-information;
         }
         case multichassis-tag {
           anyxml multi-routing-engine-results;
         }
       }
     }
   }
   rpc get-pic-detail {
     description "Show Physical Interface Card state, type, and uptime";
     input {
       uses command-forwarding;
       leaf fpc-slot {
         description "Slot number of FPC that houses PIC";
         type union {
           type string {
             pattern "<.*>|$.*";
           }
           type uint32;
         }
       }
       leaf pic-slot {
         description "PIC slot number";
         type union {
           type string {
             pattern "<.*>|$.*";
           }
           type int32;
         }
         mandatory true;
       }
     }
     output {
       choice output_c {
         case output-tag {
           leaf output {
             type string;
           }
         }
         case actual-tag {
           anyxml fpc-information;
         }
         case multichassis-tag {
           anyxml multi-routing-engine-results;
         }
       }
     }
   }
   rpc get-pic-transport-information {
     description "Show Physical Interface Card transport information";
     input {
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type int32;
         }
         mandatory true;
       }
     }
     output {
       choice output_c {
         case output-tag {
           leaf output {
             type string;
           }
         }
         case actual-tag {
           anyxml pic-transport-information;
         }
         case multichassis-tag {
           anyxml multi-routing-engine-results;
         }
       }
     }
   }
   rpc get-spmb-information {
     description "Show Switch Processor Mezzanine Board status";
     output {
       choice output_c {
         case output-tag {
           leaf output {
             type string;
           }
         }
         case actual-tag {
           anyxml spmb-information;
         }
         case multichassis-tag {
           anyxml multi-routing-engine-results;
         }
       }
     }
   }
   rpc get-spmb-sib-information {
     description "Show Switch Interface Board status";
     output {
       choice output_c {
         case output-tag {
           leaf output {
             type string;
           }
         }
         case actual-tag {
           anyxml sib-information;
         }
         case multichassis-tag {
           anyxml multi-routing-engine-results;
         }
       }
     }
   }
   rpc get-spmb-error-information {
     description "Show errors on SPMB";
     output {
       choice output_c {
         case output-tag {
           leaf output {
             type string;
           }
         }
         case actual-tag {
           anyxml spmb-error-information;
         }
         case multichassis-tag {
           anyxml multi-routing-engine-results;
         }
       }
     }
   }
   rpc get-sib-information {
     description "Show Switch Interface Board status";
     input {
       uses command-forwarding;
       leaf detail {
         description "Display detailed output";
         type empty;
       }
       leaf slot {
         description "SIB slot number";
         type union {
           type string {
             pattern "<.*>|$.*";
           }
           type uint32;
         }
       }
     }
     output {
       choice output_c {
         case output-tag {
           leaf output {
             type string;
           }
         }
         case actual-tag {
           anyxml sib-information;
         }
         case multichassis-tag {
           anyxml multi-routing-engine-results;
         }
       }
     }
   }
   rpc get-sibs-errors {
     description "Show ASIC errors on sib";
     input {
       leaf sib-slot {
         description "SIB slot number";
         type union {
           type string {
             pattern "<.*>|$.*";
           }
           type uint32;
         }
       }
     }
     output {
       choice output_c {
         case output-tag {
           leaf output {
             type string;
           }
         }
         case actual-tag {
           anyxml sib-information;
         }
         case multichassis-tag {
           anyxml multi-routing-engine-results;
         }
       }
     }
   }
   rpc get-sfb-information {
     description "Show Switch Fabric Board status";
     input {
       uses command-forwarding;
       leaf slot {
         description "SFB slot number";
         type union {
           type string {
             pattern "<.*>|$.*";
           }
           type uint32;
         }
       }
     }
     output {
       choice output_c {
         case output-tag {
           leaf output {
             type string;
           }
         }
         case actual-tag {
           anyxml sfb-information;
         }
         case multichassis-tag {
           anyxml multi-routing-engine-results;
         }
       }
     }
   }
   rpc get-sfb-errors {
     description "Show ASIC errors on sfb";
     input {
       leaf slot {
         description "SFB slot number";
         type union {
           type string {
             pattern "<.*>|$.*";
           }
           type uint32;
         }
       }
     }
     output {
       choice output_c {
         case output-tag {
           leaf output {
             type string;
           }
         }
         case actual-tag {
           anyxml sfb-information;
         }
         case multichassis-tag {
           anyxml multi-routing-engine-results;
         }
       }
     }
   }
   rpc get-fru-information {
     description "Show Line Card Chassis (LCC) status";
     output {
       choice output_c {
         case output-tag {
           leaf output {
             type string;
           }
         }
         case actual-tag {
           anyxml fru-information;
         }
         case multichassis-tag {
           anyxml multi-routing-engine-results;
         }
       }
     }
   }
   rpc get-chassis-lcc-mode-information {
     description "Show chassis lcc mode information";
     input {
       leaf lcc {
         description "LCC number";
         type union {
           type string {
             pattern "<.*>|$.*";
           }
           type uint32;
         }
       }
     }
     output {
       choice output_c {
         case output-tag {
           leaf output {
             type string;
           }
         }
         case actual-tag {
           anyxml chassis-lcc-mode-information;
         }
         case multichassis-tag {
           anyxml multi-routing-engine-results;
         }
       }
     }
   }
   rpc get-psd-information {
     description "Show Protected System Domain (PSD) status";
     output {
       choice output_c {
         case output-tag {
           leaf output {
             type string;
           }
         }
         case actual-tag {
           anyxml psd-information;
         }
         case multichassis-tag {
           anyxml multi-routing-engine-results;
         }
       }
     }
   }
   rpc get-gnf-information {
     description "Show Network Slices status";
     output {
       choice output_c {
         case output-tag {
           leaf output {
             type string;
           }
         }
         case actual-tag {
           anyxml gnf-information;
         }
         case multichassis-tag {
           anyxml multi-routing-engine-results;
         }
       }
     }
   }
   rpc get-gnf-fpcs-information {
     description "Show FPCs assigned to GNFs";
     output {
       choice output_c {
         case output-tag {
           leaf output {
             type string;
           }
         }
         case actual-tag {
           anyxml gnf-fpcs-information;
         }
         case multichassis-tag {
           anyxml multi-routing-engine-results;
         }
       }
     }
   }
   rpc get-network-slice-description {
     description "Show GNF description";
     input {
       leaf gnf-slot {
         description "GNF slot number";
         type union {
           type string {
             pattern "<.*>|$.*";
           }
           type uint32 {
             range "1 .. 10";
           }
         }
       }
     }
     output {
       choice output_c {
         case output-tag {
           leaf output {
             type string;
           }
         }
         case actual-tag {
           anyxml gnf-description;
         }
         case multichassis-tag {
           anyxml multi-routing-engine-results;
         }
       }
     }
   }
   rpc get-afs-information {
     description "Show AFs information";
     output {
       choice output_c {
         case output-tag {
           leaf output {
             type string;
           }
         }
         case actual-tag {
           anyxml afs-information;
         }
         case multichassis-tag {
           anyxml multi-routing-engine-results;
         }
       }
     }
   }
   rpc get-fm-fpc-state-information {
     description "Show summary fabric management FPC state from Routing Engine";
     input {
       uses command-forwarding;
       leaf slot {
         description "FPC slot number";
         type union {
           type string {
             pattern "<.*>|$.*";
           }
           type uint32;
         }
       }
       leaf mode {
         type enumeration {
           enum "extended" {
             description "Show all 24 planes in output";
           }
         }
       }
     }
     output {
       choice output_c {
         case output-tag {
           leaf output {
             type string;
           }
         }
         case actual-tag {
           anyxml fm-fpc-state-information;
         }
         case multichassis-tag {
           anyxml multi-routing-engine-results;
         }
       }
     }
   }
   rpc get-fm-degradation-information {
     description "Show FPC fabric bandwidth degradation information";
     output {
       choice output_c {
         case output-tag {
           leaf output {
             type string;
           }
         }
         case actual-tag {
           anyxml fm-degradation-information;
         }
         case multichassis-tag {
           anyxml multi-routing-engine-results;
         }
       }
     }
   }
   rpc get-fm-degradation-information-details {
     description "Show fpc fabric degradation action history";
     output {
       choice output_c {
         case output-tag {
           leaf output {
             type string;
           }
         }
         case actual-tag {
           anyxml fm-degradation-information-details;
         }
         case multichassis-tag {
           anyxml multi-routing-engine-results;
         }
       }
     }
   }
   rpc get-fm-fabric-destinations-state {
     description "Show fabric destinations state for all FPCs";
     input {
       uses command-forwarding;
       leaf fpc {
         description "FPC slot number";
         type union {
           type string {
             pattern "<.*>|$.*";
           }
           type uint32;
         }
       }
       leaf mode {
         type enumeration {
           enum "extended" {
             description "Show all 24 planes in output";
           }
         }
       }
     }
     output {
       choice output_c {
         case output-tag {
           leaf output {
             type string;
           }
         }
         case actual-tag {
           anyxml fm-fabric-destinations-state;
         }
         case multichassis-tag {
           anyxml multi-routing-engine-results;
         }
       }
     }
   }
   rpc get-fm-plane-location-information {
     description "Show fabric plane location";
     output {
       choice output_c {
         case output-tag {
           leaf output {
             type string;
           }
         }
         case actual-tag {
           anyxml fm-plane-location-information;
         }
         case multichassis-tag {
           anyxml multi-routing-engine-results;
         }
       }
     }
   }
   rpc get-fm-topology {
     description "Show fabric topology for plane";
     input {
       uses command-forwarding;
       leaf plane {
         description "Fabric plane number";
         type union {
           type string {
             pattern "<.*>|$.*";
           }
           type uint32;
         }
       }
     }
     output {
       choice output_c {
         case output-tag {
           leaf output {
             type string;
           }
         }
         case actual-tag {
           anyxml fm-topology;
         }
         case multichassis-tag {
           anyxml multi-routing-engine-results;
         }
       }
     }
   }
   rpc get-fm-optical-links-state-information {
     description "Show state of fabric management optical links";
     input {
       leaf lcc {
         description "Lcc number";
         type union {
           type string {
             pattern "<.*>|$.*";
           }
           type uint32;
         }
       }
       leaf detail {
         description "Display detailed output";
         type empty;
       }
     }
     output {
       choice output_c {
         case output-tag {
           leaf output {
             type string;
           }
         }
         case actual-tag {
           anyxml fm-optical-links-state-information;
         }
         case multichassis-tag {
           anyxml multi-routing-engine-results;
         }
       }
     }
   }
   rpc get-fm-optics-port-information {
     description "Show info of fabric optical ports";
     input {
       uses command-forwarding;
       leaf display {
         type enumeration {
           enum "brief" {
             description "Show brief output";
           }
           enum "detail" {
             description "Show detailed output";
           }
         }
       }
       leaf sib-slot {
         description "SIB slot number";
         type union {
           type string {
             pattern "<.*>|$.*";
           }
           type uint32;
         }
       }
     }
     output {
       choice output_c {
         case output-tag {
           leaf output {
             type string;
           }
         }
         case actual-tag {
           anyxml fm-optics-port-information;
         }
         case multichassis-tag {
           anyxml multi-routing-engine-results;
         }
       }
     }
   }
   rpc get-fm-plane-state-information {
     description "Show state of fabric management plane";
     input {
       uses command-forwarding;
       leaf display {
         type enumeration {
           enum "terse" {
             description "Show terse output";
           }
           enum "detail" {
             description "Show detail output";
           }
           enum "extensive" {
             description "Show extensive output";
           }
         }
       }
       leaf number {
         description "Fabric plane number";
         type union {
           type string {
             pattern "<.*>|$.*";
           }
           type uint32 {
             range "0 .. 4";
           }
         }
       }
       leaf mode {
         type enumeration {
           enum "extended" {
             description "Show all 24 planes in output";
           }
         }
       }
     }
     output {
       choice output_c {
         case output-tag {
           leaf output {
             type string;
           }
         }
         case actual-tag {
           anyxml fm-plane-state-information;
         }
         case multichassis-tag {
           anyxml multi-routing-engine-results;
         }
       }
     }
   }
   rpc get-fm-mid-plane-state-information {
     description "Show state of fabric mid plane";
     output {
       choice output_c {
         case output-tag {
           leaf output {
             type string;
           }
         }
         case actual-tag {
           anyxml fm-plane-state-information;
         }
         case multichassis-tag {
           anyxml multi-routing-engine-results;
         }
       }
     }
   }
   rpc get-fm-state-information {
     description "Show summary fabric management state";
     output {
       choice output_c {
         case output-tag {
           leaf output {
             type string;
           }
         }
         case actual-tag {
           anyxml fm-state-information;
         }
         case multichassis-tag {
           anyxml multi-routing-engine-results;
         }
       }
     }
   }
   rpc get-fm-ext-state-information {
     description "Show extended summary fabric management state";
     output {
       choice output_c {
         case output-tag {
           leaf output {
             type string;
           }
         }
         case actual-tag {
           anyxml fm-ext-state-information;
         }
         case multichassis-tag {
           anyxml multi-routing-engine-results;
         }
       }
     }
   }
   rpc get-fm-state-legend {
     description "Show legend of fabric management states";
     output {
       choice output_c {
         case output-tag {
           leaf output {
             type string;
           }
         }
         case actual-tag {
           anyxml fm-state-legend;
         }
         case multichassis-tag {
           anyxml multi-routing-engine-results;
         }
       }
     }
   }
   rpc get-fm-sib-state-information {
     description "Show summary fabric management SIB state from Routing Engine";
     input {
       uses command-forwarding;
       leaf slot {
         description "SIB slot number";
         type union {
           type string {
             pattern "<.*>|$.*";
           }
           type uint32;
         }
       }
     }
     output {
       choice output_c {
         case output-tag {
           leaf output {
             type string;
           }
         }
         case actual-tag {
           anyxml fm-sib-state-information;
         }
         case multichassis-tag {
           anyxml multi-routing-engine-results;
         }
       }
     }
   }
   rpc get-chassis-fabric-topology-information {
     description "Show fabric topology information";
     input {
       uses command-forwarding;
       leaf sib-slot {
         description "SIB slot number";
         type union {
           type string {
             pattern "<.*>|$.*";
           }
           type uint32;
         }
       }
       leaf device {
         description "Device alias name or serial number";
         type string;
       }
       leaf slot {
         description "Slot number";
         type union {
           type string {
             pattern "<.*>|$.*";
           }
           type uint32 {
             range "0 .. 15";
           }
         }
       }
     }
     output {
       choice output_c {
         case output-tag {
           leaf output {
             type string;
           }
         }
         case actual-tag {
           anyxml chassis-fabric-information;
         }
         case multichassis-tag {
           anyxml multi-routing-engine-results;
         }
       }
     }
   }
   rpc get-fm-topo-tracepath-link {
     description "Show info of fabric path";
     input {
       leaf hsl2link {
         description "HSL2 Link Name as in topology command";
         type string;
         mandatory true;
       }
       leaf lcc {
         description "Lcc number. Default is 0";
         default "0";
         type union {
           type string {
             pattern "<.*>|$.*";
           }
           type uint32;
         }
       }
     }
     output {
       choice output_c {
         case output-tag {
           leaf output {
             type string;
           }
         }
         case actual-tag {
           anyxml fm-topo-tracepath-link;
         }
         case multichassis-tag {
           anyxml multi-routing-engine-results;
         }
       }
     }
   }
   rpc get-fm-topo-tracepath-fpc {
     description "Show info of fabric path";
     input {
       leaf fpcstr {
         description "FPC/PFE String as in topology cmd - e.g. FPC7PFE1";
         type string;
         mandatory true;
       }
       leaf lcc {
         description "Lcc number.";
         type union {
           type string {
             pattern "<.*>|$.*";
           }
           type uint32;
         }
         mandatory true;
       }
       leaf plane {
         description "Fabric Plane - 0/1/2/3/4 and 5=all-active-planes(Default)";
         default "5";
         type union {
           type string {
             pattern "<.*>|$.*";
           }
           type uint32 {
             range "0 .. 5";
           }
         }
       }
     }
     output {
       choice output_c {
         case output-tag {
           leaf output {
             type string;
           }
         }
         case actual-tag {
           anyxml fm-topo-tracepath-fpc;
         }
         case multichassis-tag {
           anyxml multi-routing-engine-results;
         }
       }
     }
   }
   rpc get-chassis-fabric-spray-weight-information {
     description "Show fabric spray-weights";
     output {
       choice output_c {
         case output-tag {
           leaf output {
             type string;
           }
         }
         case actual-tag {
           anyxml chassis-fabric-spray-weight-information;
         }
         case multichassis-tag {
           anyxml multi-routing-engine-results;
         }
       }
     }
   }
   rpc get-chassis-fabric-link-information {
     description "Show data-center fabric links";
     input {
       leaf link-type {
         description "Link type";
         default "all";
         type enumeration {
           enum "up" {
             description "Up links";
           }
           enum "down" {
             description "Down links";
           }
           enum "error" {
             description "Error links";
           }
           enum "all" {
             description "All links";
           }
         }
       }
       leaf device {
         description "Device alias name or serial number";
         type string;
       }
       leaf slot {
         description "Slot number";
         type union {
           type string {
             pattern "<.*>|$.*";
           }
           type uint32 {
             range "0 .. 15";
           }
         }
       }
     }
     output {
       choice output_c {
         case output-tag {
           leaf output {
             type string;
           }
         }
         case actual-tag {
           anyxml chassis-fabric-information;
         }
         case multichassis-tag {
           anyxml multi-routing-engine-results;
         }
       }
     }
   }
   rpc get-chassis-fabric-information-device {
     description "Show chassis fabric devices running FM component";
     input {
       leaf device-id {
         description "Device alias name or serial number";
         type string;
       }
     }
     output {
       choice output_c {
         case output-tag {
           leaf output {
             type string;
           }
         }
         case actual-tag {
           anyxml chassis-fabric-information-device;
         }
         case multichassis-tag {
           anyxml multi-routing-engine-results;
         }
       }
     }
   }
   rpc get-chassis-fabric-connectivity-information {
     description "Show data-center fabric connectivity";
     input {
       leaf device {
         description "Device alias name or serial number";
         type string;
       }
       leaf slot {
         description "Slot number";
         type union {
           type string {
             pattern "<.*>|$.*";
           }
           type uint32 {
             range "0 .. 15";
           }
         }
       }
       leaf inter-chassis {
         description "Inter chassis fabric link connectivity details";
         type empty;
       }
       leaf intra-chassis {
         description "Intra chassis fabric link connectivity details";
         type empty;
       }
     }
     output {
       choice output_c {
         case output-tag {
           leaf output {
             type string;
           }
         }
         case actual-tag {
           anyxml chassis-fabric-connectivity-information;
         }
         case multichassis-tag {
           anyxml multi-routing-engine-results;
         }
       }
     }
   }
   rpc get-fm-unreachable-dest-information {
     description "Show unreachable destinations on all active planes";
     output {
       choice output_c {
         case output-tag {
           leaf output {
             type string;
           }
         }
         case actual-tag {
           anyxml fm-unreachable-dest-information;
         }
         case multichassis-tag {
           anyxml multi-routing-engine-results;
         }
       }
     }
   }
   rpc get-fm-fabric-reachability-information {
     description "Show current status of fabric reachability";
     input {
       uses command-forwarding;
       leaf detail {
         description "Show reachability output in detail";
         type empty;
       }
       leaf extended {
         description "Show all 24 planes in output";
         type empty;
       }
     }
     output {
       choice output_c {
         case output-tag {
           leaf output {
             type string;
           }
         }
         case actual-tag {
           anyxml fm-fabric-reachability-information;
         }
         case multichassis-tag {
           anyxml multi-routing-engine-results;
         }
       }
     }
   }
   rpc get-fm-degraded-fabric-state-information {
     description "Show degraded fabric state on all active planes";
     output {
       choice output_c {
         case output-tag {
           leaf output {
             type string;
           }
         }
         case actual-tag {
           anyxml fm-degraded-fabric-state-information;
         }
         case multichassis-tag {
           anyxml multi-routing-engine-results;
         }
       }
     }
   }
   rpc get-fm-sib-errors {
     description "Show Switch Interface Board errors";
     input {
       uses command-forwarding;
       leaf sib-slot {
         description "SIB slot number";
         type union {
           type string {
             pattern "<.*>|$.*";
           }
           type uint32;
         }
         mandatory true;
       }
     }
     output {
       choice output_c {
         case output-tag {
           leaf output {
             type string;
           }
         }
         case actual-tag {
           anyxml fm-fru-errors;
         }
         case multichassis-tag {
           anyxml multi-routing-engine-results;
         }
       }
     }
   }
   rpc get-fm-fpc-errors {
     description "Show Flexible PIC Controller errors";
     input {
       uses command-forwarding;
       leaf slot {
         description "FPC slot number";
         type union {
           type string {
             pattern "<.*>|$.*";
           }
           type uint32;
         }
         mandatory true;
       }
     }
     output {
       choice output_c {
         case output-tag {
           leaf output {
             type string;
           }
         }
         case actual-tag {
           anyxml fm-fru-errors;
         }
         case multichassis-tag {
           anyxml multi-routing-engine-results;
         }
       }
     }
   }
   rpc get-fm-plane-autoheal-errors {
     description "Show Planes autoheal state";
     output {
       choice output_c {
         case output-tag {
           leaf output {
             type string;
           }
         }
         case actual-tag {
           anyxml fm-fru-errors;
         }
         case multichassis-tag {
           anyxml multi-routing-engine-results;
         }
       }
     }
   }
   rpc get-chassis-inventory {
     description "Show installed hardware components";
     input {
       uses command-forwarding;
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
       leaf fpc {
         description "Flexible PIC Controller slot number";
         type union {
           type string {
             pattern "<.*>|$.*";
           }
           type uint32;
         }
       }
     }
     output {
       choice output_c {
         case output-tag {
           leaf output {
             type string;
           }
         }
         case actual-tag {
           anyxml chassis-inventory;
         }
         case multichassis-tag {
           anyxml multi-routing-engine-results;
         }
       }
     }
   }
   rpc get-chassis-hardware-satellite-information {
     description "Show hardware details";
     input {
       leaf fpc-slot {
         description "Satellite slot number";
         type union {
           type string {
             pattern "<.*>|$.*";
           }
           type uint16 {
             range "65 .. 254";
           }
         }
       }
       leaf device-alias {
         description "Device alias";
         type string;
       }
       leaf verbosity {
         type enumeration {
           enum "detail" {
             description "Include RAM and disk information in output";
           }
           enum "extensive" {
             description "Display ID EEPROM information";
           }
           enum "models" {
             description "Display serial number and model number for orderable FRUs";
           }
           enum "clei-models" {
             description "Display CLEI barcode and model number for orderable FRUs";
           }
         }
       }
     }
     output {
       choice output_c {
         case output-tag {
           leaf output {
             type string;
           }
         }
         case actual-tag {
           anyxml chassis-hardware-satellite-information;
         }
         case multichassis-tag {
           anyxml multi-routing-engine-results;
         }
       }
     }
   }
   rpc get-power-budget-information {
     description "Show power budget chassis information";
     output {
       choice output_c {
         case output-tag {
           leaf output {
             type string;
           }
         }
         case actual-tag {
           anyxml power-budget-information;
         }
         case multichassis-tag {
           anyxml multi-routing-engine-results;
         }
       }
     }
   }
   rpc get-chassis-ae-lb-information {
     description "Show multicast load balancing settings";
     output {
       choice output_c {
         case output-tag {
           leaf output {
             type string;
           }
         }
         case actual-tag {
           anyxml chassis-ae-lb-information;
         }
         case multichassis-tag {
           anyxml multi-routing-engine-results;
         }
       }
     }
   }
   rpc get-rps-chassis-information {
     description "Show redundant power system chassis information";
     output {
       choice output_c {
         case output-tag {
           leaf output {
             type string;
           }
         }
         case actual-tag {
           anyxml rps-chassis-information;
         }
         case multichassis-tag {
           anyxml multi-routing-engine-results;
         }
       }
     }
   }
   rpc get-chassis-mac-addresses {
     description "Show media access control addresses";
     output {
       choice output_c {
         case output-tag {
           leaf output {
             type string;
           }
         }
         case actual-tag {
           anyxml chassis-mac-addresses;
         }
         case multichassis-tag {
           anyxml multi-routing-engine-results;
         }
       }
     }
   }
   rpc get-raid-status {
     description "Show RAID status";
     output {
       choice output_c {
         case output-tag {
           leaf output {
             type string;
           }
         }
         case actual-tag {
           anyxml raid-information;
         }
         case multichassis-tag {
           anyxml multi-routing-engine-results;
         }
       }
     }
   }
   rpc get-raid-members {
     description "Show RAID members";
     output {
       choice output_c {
         case output-tag {
           leaf output {
             type string;
           }
         }
         case actual-tag {
           anyxml raid-information;
         }
         case multichassis-tag {
           anyxml multi-routing-engine-results;
         }
       }
     }
   }
   rpc get-route-engine-information {
     description "Show Routing Engine status";
     input {
       uses command-forwarding;
       leaf slot {
         description "Routing Engine slot number";
         type union {
           type string {
             pattern "<.*>|$.*";
           }
           type uint32;
         }
       }
     }
     output {
       choice output_c {
         case output-tag {
           leaf output {
             type string;
           }
         }
         case actual-tag {
           anyxml route-engine-information;
         }
         case multichassis-tag {
           anyxml multi-routing-engine-results;
         }
       }
     }
   }
   rpc get-bios-version-information {
     description "Show BIOS firmware version";
     output {
       choice output_c {
         case output-tag {
           leaf output {
             type string;
           }
         }
         case multichassis-tag {
           anyxml multi-routing-engine-results;
         }
       }
     }
   }
   rpc get-chassis-routing-engine-bios-satellite-info {
     description "Show routing engine bios details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-routing-engine-bios-satellite-information;
         }
         case multichassis-tag {
           anyxml multi-routing-engine-results;
         }
       }
     }
   }
   rpc show-chassis-hard-disk-test {
     description "Show smartd self tests status on hard disks";
     input {
       leaf status {
         description "Display status of test";
         type empty;
         mandatory true;
       }
       leaf disk {
         description "Name of hard disk";
         type string;
         mandatory true;
       }
     }
     output {
       choice output_c {
         case output-tag {
           leaf output {
             type string;
           }
         }
         case actual-tag {
           anyxml raid-information;
         }
         case multichassis-tag {
           anyxml multi-routing-engine-results;
         }
       }
     }
   }
   rpc get-chassis-routing-engine-errors {
     description "Show RE errors";
     output {
       choice output_c {
         case output-tag {
           leaf output {
             type string;
           }
         }
         case actual-tag {
           anyxml errors;
         }
         case multichassis-tag {
           anyxml multi-routing-engine-results;
         }
       }
     }
   }
   rpc get-chassis-routing-engine-satellite-information {
     description "Show routing engine details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-routing-engine-satellite-information;
         }
         case multichassis-tag {
           anyxml multi-routing-engine-results;
         }
       }
     }
   }
   rpc get-service-node-information {
     description "Show service node information";
     input {
       leaf version {
         description "Show service-node version information";
         type empty;
       }
       leaf slot {
         description "Service node slot number";
         type union {
           type string {
             pattern "<.*>|$.*";
           }
           type uint32 {
             range "0 .. 1";
           }
         }
       }
     }
     output {
       choice output_c {
         case output-tag {
           leaf output {
             type string;
           }
         }
         case actual-tag {
           anyxml service-node-information;
         }
         case multichassis-tag {
           anyxml multi-routing-engine-results;
         }
       }
     }
   }
   rpc get-ssb-information {
     description "Show System and Switch Board status";
     input {
       leaf slot {
         description "SSB slot number";
         type union {
           type string {
             pattern "<.*>|$.*";
           }
           type uint32 {
             range "0 .. 1";
           }
         }
       }
     }
     output {
       choice output_c {
         case output-tag {
           leaf output {
             type string;
           }
         }
         case actual-tag {
           anyxml scb-information;
         }
         case multichassis-tag {
           anyxml multi-routing-engine-results;
         }
       }
     }
   }
   rpc get-scb-information {
     description "Show System Control Board status";
     output {
       choice output_c {
         case output-tag {
           leaf output {
             type string;
           }
         }
         case actual-tag {
           anyxml scb-information;
         }
         case multichassis-tag {
           anyxml multi-routing-engine-results;
         }
       }
     }
   }
   rpc get-fwdd-information {
     description "Show forwarding process (fwdd) status";
     output {
       choice output_c {
         case output-tag {
           leaf output {
             type string;
           }
         }
         case actual-tag {
           anyxml scb-information;
         }
         case multichassis-tag {
           anyxml multi-routing-engine-results;
         }
       }
     }
   }
   rpc get-sfm-information {
     description "Show Switching and Forwarding Module status";
     output {
       choice output_c {
         case output-tag {
           leaf output {
             type string;
           }
         }
         case actual-tag {
           anyxml scb-information;
         }
         case multichassis-tag {
           anyxml multi-routing-engine-results;
         }
       }
     }
   }
   rpc get-feb-brief-information {
     description "Show Forwarding Engine Board status";
     output {
       choice output_c {
         case output-tag {
           leaf output {
             type string;
           }
         }
         case actual-tag {
           anyxml scb-information;
         }
         case multichassis-tag {
           anyxml multi-routing-engine-results;
         }
       }
     }
   }
   rpc get-feb-information {
     description "Show detailed output";
     input {
       leaf feb_slot {
         description "FEB slot number";
         type union {
           type string {
             pattern "<.*>|$.*";
           }
           type uint32;
         }
       }
     }
     output {
       choice output_c {
         case output-tag {
           leaf output {
             type string;
           }
         }
         case actual-tag {
           anyxml scb-information;
         }
         case multichassis-tag {
           anyxml multi-routing-engine-results;
         }
       }
     }
   }
   rpc get-cfeb-information {
     description "Show Compact Forwarding Engine Board status";
     output {
       choice output_c {
         case output-tag {
           leaf output {
             type string;
           }
         }
         case actual-tag {
           anyxml scb-information;
         }
         case multichassis-tag {
           anyxml multi-routing-engine-results;
         }
       }
     }
   }
   rpc get-afeb-information {
     description "Show Compact Forwarding Engine Board status";
     output {
       choice output_c {
         case output-tag {
           leaf output {
             type string;
           }
         }
         case actual-tag {
           anyxml scb-information;
         }
         case multichassis-tag {
           anyxml multi-routing-engine-results;
         }
       }
     }
   }
   rpc get-tfeb-information {
     description "Show Compact Forwarding Engine Board status";
     output {
       choice output_c {
         case output-tag {
           leaf output {
             type string;
           }
         }
         case actual-tag {
           anyxml scb-information;
         }
         case multichassis-tag {
           anyxml multi-routing-engine-results;
         }
       }
     }
   }
   rpc get-chassis-fan-satellite-information {
     description "Show fan details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-fan-satellite-information;
         }
         case multichassis-tag {
           anyxml multi-routing-engine-results;
         }
       }
     }
   }
   rpc get-chassis-location {
     description "Show physical location of chassis";
     output {
       choice output_c {
         case output-tag {
           leaf output {
             type string;
           }
         }
         case actual-tag {
           anyxml chassis-location;
         }
         case multichassis-tag {
           anyxml multi-routing-engine-results;
         }
       }
     }
   }
   rpc get-interface-location-name-information {
     description "Show physical location given interface name";
     input {
       leaf interface-name {
         description "Interface name";
         type string;
         mandatory true;
       }
     }
     output {
       choice output_c {
         case output-tag {
           leaf output {
             type string;
           }
         }
         case actual-tag {
           anyxml interface-location-name-information;
         }
         case multichassis-tag {
           anyxml multi-routing-engine-results;
         }
       }
     }
   }
   rpc get-interface-location-information {
     description "Show interface name given location";
     input {
       leaf lcc {
         description "LCC number";
         type union {
           type string {
             pattern "<.*>|$.*";
           }
           type uint32;
         }
         mandatory true;
       }
       leaf fpc {
         description "FPC number";
         type union {
           type string {
             pattern "<.*>|$.*";
           }
           type uint32;
         }
         mandatory true;
       }
     }
     output {
       choice output_c {
         case output-tag {
           leaf output {
             type string;
           }
         }
         case actual-tag {
           anyxml interface-location-slot-information;
         }
         case multichassis-tag {
           anyxml multi-routing-engine-results;
         }
       }
     }
   }
   rpc get-temperature-threshold-information {
     description "Show chassis temperature threshold settings";
     input {
       uses command-forwarding;
       leaf fpc {
         description "Flexible PIC Controller slot number";
         type union {
           type string {
             pattern "<.*>|$.*";
           }
           type uint32;
         }
       }
     }
     output {
       choice output_c {
         case output-tag {
           leaf output {
             type string;
           }
         }
         case actual-tag {
           anyxml temperature-threshold-information;
         }
         case multichassis-tag {
           anyxml multi-routing-engine-results;
         }
       }
     }
   }
   rpc get-chassis-temp-thresholds-satellite-info {
     description "Show temperature thresholds details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-temperature-thresholds-satellite-information;
         }
         case multichassis-tag {
           anyxml multi-routing-engine-results;
         }
       }
     }
   }
   rpc get-power-management {
     description "Show power ratings for the router";
     output {
       choice output_c {
         case output-tag {
           leaf output {
             type string;
           }
         }
         case actual-tag {
           anyxml power-management-information;
         }
         case multichassis-tag {
           anyxml multi-routing-engine-results;
         }
       }
     }
   }
   rpc get-in-service-upgrade-status {
     description "Show In Service upgrade status";
     output {
       choice output_c {
         case output-tag {
           leaf output {
             type string;
           }
         }
         case actual-tag {
           anyxml in-service-upgrade-status;
         }
         case multichassis-tag {
           anyxml multi-routing-engine-results;
         }
       }
     }
   }
   rpc get-chassis-mode-status {
     description "Show chassis mode status";
     output {
       choice output_c {
         case output-tag {
           leaf output {
             type string;
           }
         }
         case actual-tag {
           anyxml chassis-mode-status;
         }
         case multichassis-tag {
           anyxml multi-routing-engine-results;
         }
       }
     }
   }
   rpc get-nonstop-upgrade-status {
     description "Show nonstop upgrade status";
     output {
       choice output_c {
         case output-tag {
           leaf output {
             type string;
           }
         }
         case actual-tag {
           anyxml in-service-upgrade-status;
         }
         case multichassis-tag {
           anyxml multi-routing-engine-results;
         }
       }
     }
   }
   rpc get-dedicated-ukern-status {
     description "Show ukernel dedicated CPU core assignment status ";
     output {
       choice output_c {
         case output-tag {
           leaf output {
             type string;
           }
         }
         case actual-tag {
           anyxml dedicated-ukern-cpu;
         }
         case multichassis-tag {
           anyxml multi-routing-engine-results;
         }
       }
     }
   }
   rpc get-realtime-ukern-status {
     description "Show ukernel realtime thread assignment status ";
     output {
       choice output_c {
         case output-tag {
           leaf output {
             type string;
           }
         }
         case actual-tag {
           anyxml realtime-ukern-thread;
         }
         case multichassis-tag {
           anyxml multi-routing-engine-results;
         }
       }
     }
   }
   rpc get-chassis-oss-map {
     description "Show Operation Supported System's translated model";
     output {
       choice output_c {
         case output-tag {
           leaf output {
             type string;
           }
         }
         case actual-tag {
           anyxml chassis-oss-map;
         }
         case multichassis-tag {
           anyxml multi-routing-engine-results;
         }
       }
     }
   }
   rpc security-uefi-variables {
     description "Show platform UEFI variables";
     output {
       choice output_c {
         case output-tag {
           leaf output {
             type string;
           }
         }
         case actual-tag {
           anyxml uefi-vars;
         }
         case multichassis-tag {
           anyxml multi-routing-engine-results;
         }
       }
     }
   }
   rpc get-gnf-description {
     description "Show GNF information";
     output {
       choice output_c {
         case output-tag {
           leaf output {
             type string;
           }
         }
         case actual-tag {
           anyxml gnf-description;
         }
         case multichassis-tag {
           anyxml multi-routing-engine-results;
         }
       }
     }
   }
   rpc get-chassis-cluster-interfaces {
     description "Display chassis cluster interfaces";
     output {
       choice output_c {
         case output-tag {
           leaf output {
             type string;
           }
         }
         case actual-tag {
           anyxml chassis-cluster-interface-statistics;
         }
         case multichassis-tag {
           anyxml multi-routing-engine-results;
         }
       }
     }
   }
   rpc get-chassis-cluster-control-plane-statistics {
     description "Display control-plane statistics";
     output {
       choice output_c {
         case output-tag {
           leaf output {
             type string;
           }
         }
         case actual-tag {
           anyxml chassis-cluster-statistics;
         }
         case multichassis-tag {
           anyxml multi-routing-engine-results;
         }
       }
     }
   }
   rpc get-chassis-cluster-data-plane-statistics {
     description "Display data-plane statistics";
     output {
       choice output_c {
         case output-tag {
           leaf output {
             type string;
           }
         }
         case actual-tag {
           anyxml services-synchronized;
         }
         case multichassis-tag {
           anyxml multi-routing-engine-results;
         }
       }
     }
   }
   rpc get-chassis-cluster-data-plane-interfaces {
     description "Display data-plane interfaces";
     output {
       choice output_c {
         case output-tag {
           leaf output {
             type string;
           }
         }
         case actual-tag {
           anyxml chassis-cluster-dataplane-interfaces;
         }
         case multichassis-tag {
           anyxml multi-routing-engine-results;
         }
       }
     }
   }
   rpc get-chassis-cluster-statistics {
     description "Display chassis cluster statistics";
     output {
       choice output_c {
         case output-tag {
           leaf output {
             type string;
           }
         }
         case actual-tag {
           anyxml chassis-cluster-statistics;
         }
         case multichassis-tag {
           anyxml multi-routing-engine-results;
         }
       }
     }
   }
   rpc get-chassis-cluster-status {
     description "Display chassis cluster status";
     input {
       leaf redundancy-group {
         description "Display chassis cluster status per redundancy-group";
         type union {
           type string {
             pattern "<.*>|$.*";
           }
           type uint8;
         }
       }
     }
     output {
       choice output_c {
         case output-tag {
           leaf output {
             type string;
           }
         }
         case actual-tag {
           anyxml chassis-cluster-status;
         }
         case multichassis-tag {
           anyxml multi-routing-engine-results;
         }
       }
     }
   }
   rpc get-chassis-cluster-information {
     description "Show chassis cluster information";
     output {
       choice output_c {
         case output-tag {
           leaf output {
             type string;
           }
         }
         case actual-tag {
           anyxml chassis-cluster-information;
         }
         case multichassis-tag {
           anyxml multi-routing-engine-results;
         }
       }
     }
   }
   rpc get-chassis-cluster-configuration-synchronization-information {
     description "Display configuration synchronization information";
     output {
       choice output_c {
         case output-tag {
           leaf output {
             type string;
           }
         }
         case actual-tag {
           anyxml configuration-synchronization-information;
         }
         case multichassis-tag {
           anyxml multi-routing-engine-results;
         }
       }
     }
   }
   rpc get-chassis-cluster-issu-information {
     description "Display ISSU information";
     output {
       choice output_c {
         case output-tag {
           leaf output {
             type string;
           }
         }
         case actual-tag {
           anyxml issu-information;
         }
         case multichassis-tag {
           anyxml multi-routing-engine-results;
         }
       }
     }
   }
   rpc get-chassis-cluster-detail-information {
     description "Display all chassis cluster information";
     input {
       uses command-forwarding;
       leaf redundancy-group {
         description "Display chassis cluster status per redundancy-group";
         type union {
           type string {
             pattern "<.*>|$.*";
           }
           type uint8;
         }
       }
     }
     output {
       choice output_c {
         case output-tag {
           leaf output {
             type string;
           }
         }
         case actual-tag {
           anyxml chassis-cluster-detail-information;
         }
         case multichassis-tag {
           anyxml multi-routing-engine-results;
         }
       }
     }
   }
   rpc get-chassis-cluster-cold-synchronization-information {
     description "Display coldsync information";
     output {
       choice output_c {
         case output-tag {
           leaf output {
             type string;
           }
         }
         case actual-tag {
           anyxml cold-synchronization-monitoring-information;
         }
         case multichassis-tag {
           anyxml multi-routing-engine-results;
         }
       }
     }
   }
   rpc get-chassis-cluster-spu-information {
     description "Display SPU information";
     output {
       choice output_c {
         case output-tag {
           leaf output {
             type string;
           }
         }
         case actual-tag {
           anyxml spu-monitoring-information;
         }
         case multichassis-tag {
           anyxml multi-routing-engine-results;
         }
       }
     }
   }
   rpc get-chassis-cluster-loopback-information {
     description "Display loopback monitoring information";
     output {
       choice output_c {
         case output-tag {
           leaf output {
             type string;
           }
         }
         case actual-tag {
           anyxml loopback-information;
         }
         case multichassis-tag {
           anyxml multi-routing-engine-results;
         }
       }
     }
   }
   rpc get-chassis-cluster-hardware-monitoring-information {
     description "Display hardware monitoring information";
     output {
       choice output_c {
         case output-tag {
           leaf output {
             type string;
           }
         }
         case actual-tag {
           anyxml hardware-monitoring-information;
         }
         case multichassis-tag {
           anyxml multi-routing-engine-results;
         }
       }
     }
   }
   rpc get-chassis-cluster-schedule-monitoring-information {
     description "Display schedule monitoring information";
     output {
       choice output_c {
         case output-tag {
           leaf output {
             type string;
           }
         }
         case actual-tag {
           anyxml schedule-monitoring-information;
         }
         case multichassis-tag {
           anyxml multi-routing-engine-results;
         }
       }
     }
   }
   rpc get-chassis-cluster-interface-monitoring-information {
     description "Display interface monitoring information";
     output {
       choice output_c {
         case output-tag {
           leaf output {
             type string;
           }
         }
         case actual-tag {
           anyxml interface-monitoring-information;
         }
         case multichassis-tag {
           anyxml multi-routing-engine-results;
         }
       }
     }
   }
   rpc get-chassis-cluster-control-link-information {
     description "Display control link information";
     output {
       choice output_c {
         case output-tag {
           leaf output {
             type string;
           }
         }
         case actual-tag {
           anyxml control-link-information;
         }
         case multichassis-tag {
           anyxml multi-routing-engine-results;
         }
       }
     }
   }
   rpc get-chassis-cluster-fabric-link-information {
     description "Display fabric link information";
     output {
       choice output_c {
         case output-tag {
           leaf output {
             type string;
           }
         }
         case actual-tag {
           anyxml fabric-link-information;
         }
         case multichassis-tag {
           anyxml multi-routing-engine-results;
         }
       }
     }
   }
   rpc get-chassis-cluster-command-history-information {
     description "Display command history";
     output {
       choice output_c {
         case output-tag {
           leaf output {
             type string;
           }
         }
         case actual-tag {
           anyxml command-history-information;
         }
         case multichassis-tag {
           anyxml multi-routing-engine-results;
         }
       }
     }
   }
   rpc get-chassis-cluster-ip-monitoring-status {
     description "Display IP monitoring status";
     output {
       choice output_c {
         case output-tag {
           leaf output {
             type string;
           }
         }
         case actual-tag {
           anyxml chassis-cluster-ip-monitoring;
         }
         case multichassis-tag {
           anyxml multi-routing-engine-results;
         }
       }
     }
   }
   rpc get-chassis-cluster-ip-monitoring-status-redundancy-group {
     description "Show IP monitoring status of a specific redundancy-group";
     input {
       uses command-forwarding;
       leaf redundancy-group-identifier {
         description "Redundancy-group identifier";
         type union {
           type string {
             pattern "<.*>|$.*";
           }
           type uint8;
         }
         mandatory true;
       }
     }
     output {
       choice output_c {
         case output-tag {
           leaf output {
             type string;
           }
         }
         case actual-tag {
           anyxml chassis-cluster-ip-monitoring;
         }
         case multichassis-tag {
           anyxml multi-routing-engine-results;
         }
       }
     }
   }
   rpc get-chassis-cluster-ethernet-switching-status {
     description "Display chassis cluster ethernet switching status";
     output {
       choice output_c {
         case output-tag {
           leaf output {
             type string;
           }
         }
         case actual-tag {
           anyxml chassis-cluster-ethernet-switching-status;
         }
         case multichassis-tag {
           anyxml multi-routing-engine-results;
         }
       }
     }
   }
   rpc get-chassis-cluster-switch-fabric-probe-statistics {
     description "Display chassis cluster switch fabric probe statistics";
     output {
       choice output_c {
         case output-tag {
           leaf output {
             type string;
           }
         }
         case actual-tag {
           anyxml chassis-cluster-switch-switching-statistics;
         }
         case multichassis-tag {
           anyxml multi-routing-engine-results;
         }
       }
     }
   }
   rpc get-chassis-cluster-switch-fabric-link-interfaces {
     description "Display chassis cluster switch fabric link interfaces";
     output {
       choice output_c {
         case output-tag {
           leaf output {
             type string;
           }
         }
         case actual-tag {
           anyxml chassis-cluster-switch-switching-interfaces;
         }
         case multichassis-tag {
           anyxml multi-routing-engine-results;
         }
       }
     }
   }
   rpc get-chassis-cluster-port-peering-status {
     description "Display chassis cluster port peering";
     output {
       choice output_c {
         case output-tag {
           leaf output {
             type string;
           }
         }
         case actual-tag {
           anyxml chassis-cluster-port-peering-status;
         }
         case multichassis-tag {
           anyxml multi-routing-engine-results;
         }
       }
     }
   }
   rpc get-chassis-L3-ha-mode-fabric-statistics {
     description "Display fabric statistics";
     output {
       choice output_c {
         case output-tag {
           leaf output {
             type string;
           }
         }
         case actual-tag {
           anyxml chassis-cluster-fabric;
         }
         case multichassis-tag {
           anyxml multi-routing-engine-results;
         }
       }
     }
   }
   rpc get-chassis-L3-ha-mode-fabric-status {
     description "Display chassis fabric interfaces status";
     output {
       choice output_c {
         case output-tag {
           leaf output {
             type string;
           }
         }
         case actual-tag {
           anyxml dataplane-interfaces;
         }
         case multichassis-tag {
           anyxml multi-routing-engine-results;
         }
       }
     }
   }
   rpc get-chassis-L3-ha-mode-fabric-status-detail {
     description "Display chassis L3-ha-mode fabric interface details";
     output {
       choice output_c {
         case output-tag {
           leaf output {
             type string;
           }
         }
         case actual-tag {
           anyxml fabric-link-information;
         }
         case multichassis-tag {
           anyxml multi-routing-engine-results;
         }
       }
     }
   }
   rpc get-chassis-l3-ha-info {
     description "Display l3-ha information";
     output {
       choice output_c {
         case output-tag {
           leaf output {
             type string;
           }
         }
         case actual-tag {
           anyxml chassis-l3-ha-info;
         }
         case multichassis-tag {
           anyxml multi-routing-engine-results;
         }
       }
     }
   }
   rpc get-lcd-information {
     description "Show LCD display";
     output {
       choice output_c {
         case output-tag {
           leaf output {
             type string;
           }
         }
         case actual-tag {
           anyxml craft-lcd-led-information;
         }
         case multichassis-tag {
           anyxml multi-routing-engine-results;
         }
       }
     }
   }
   rpc get-lcd-fpc-information {
     description "Show LCD display for FPC slot number";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml craft-lcd-led-information;
         }
         case multichassis-tag {
           anyxml multi-routing-engine-results;
         }
       }
     }
   }
   rpc get-lcd-menu-information {
     description "Show active LCD menu items";
     output {
       choice output_c {
         case output-tag {
           leaf output {
             type string;
           }
         }
         case actual-tag {
           anyxml lcd-information;
         }
         case multichassis-tag {
           anyxml multi-routing-engine-results;
         }
       }
     }
   }
   rpc get-led-information {
     description "Show LED status";
     output {
       choice output_c {
         case output-tag {
           leaf output {
             type string;
           }
         }
         case actual-tag {
           anyxml craft-lcd-led-information;
         }
         case multichassis-tag {
           anyxml multi-routing-engine-results;
         }
       }
     }
   }
   rpc get-led-fpc-information {
     description "Show LED status for FPC slot number";
     input {
       uses command-forwarding;
       leaf fpc-slot {
         description "FPC slot number";
         type union {
           type string {
             pattern "<.*>|$.*";
           }
           type uint32;
         }
       }
     }
     output {
       choice output_c {
         case output-tag {
           leaf output {
             type string;
           }
         }
         case actual-tag {
           anyxml craft-lcd-led-information;
         }
         case multichassis-tag {
           anyxml multi-routing-engine-results;
         }
       }
     }
   }
   rpc get-chassis-led-satellite-information {
     description "Show led details";
     input {
       leaf fpc-slot {
         description "Satellite slot number";
         type union {
           type string {
             pattern "<.*>|$.*";
           }
           type uint16 {
             range "65 .. 254";
           }
         }
       }
       leaf device-alias {
         description "Device alias";
         type string;
       }
     }
     output {
       choice output_c {
         case output-tag {
           leaf output {
             type string;
           }
         }
         case actual-tag {
           anyxml chassis-led-satellite-information;
         }
         case multichassis-tag {
           anyxml multi-routing-engine-results;
         }
       }
     }
   }
   rpc get-chassis-satellite-information {
     description "Show Satellite Devices information";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
       leaf since {
         description "Show history since YYYY-MM-DD.HH:MM:SS";
         type jt:time;
       }
       leaf level {
         default "brief";
         type enumeration {
           enum "terse" {
             description "Display terse output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml satellite-information;
         }
         case multichassis-tag {
           anyxml multi-routing-engine-results;
         }
       }
     }
   }
   rpc get-chassis-satellite-unprovision-information {
     description "Display unprovisioned satellites";
     input {
       leaf system-id {
         description "Satellite system id";
         type jt:mac-addr;
       }
       leaf since {
         description "Show history since YYYY-MM-DD.HH:MM:SS";
         type jt:time;
       }
       leaf level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml satellite-information;
         }
         case multichassis-tag {
           anyxml multi-routing-engine-results;
         }
       }
     }
   }
   rpc get-chassis-satellite-statistics {
     description "Display device statistics information";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf cluster {
         description "Cluster name";
         type string;
       }
     }
     output {
       choice output_c {
         case output-tag {
           leaf output {
             type string;
           }
         }
         case actual-tag {
           anyxml device-statistics;
         }
         case multichassis-tag {
           anyxml multi-routing-engine-results;
         }
       }
     }
   }
   rpc get-chassis-satellite-redundancy-group-info {
     description "Display multi-chassis cluster information";
     input {
       leaf since {
         description "Show history since YYYY-MM-DD.HH:MM:SS";
         type jt:time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-information;
         }
         case multichassis-tag {
           anyxml multi-routing-engine-results;
         }
       }
     }
   }
   rpc get-chassis-satellite-redundacy-grp-devices-info {
     description "Display satellite device information";
     input {
       leaf fpc-slot {
         description "Satellite slot number";
         type union {
           type string {
             pattern "<.*>|$.*";
           }
           type uint32 {
             range "65 .. 254";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-device-information;
         }
         case multichassis-tag {
           anyxml multi-routing-engine-results;
         }
       }
     }
   }
   rpc get-chassis-satellite-redundancy-grp-dev-history {
     description "Display device history information";
     input {
       leaf verbosity_level {
         default "brief";
         type enumeration {
           enum "brief" {
             description "Display brief output (default)";
           }
           enum "detail" {
             description "Display detailed output";
           }
           enum "extensive" {
             description "Display extensive output";
           }
         }
       }
       leaf serial-number {
         description "Device Serial Number";
         type string;
       }
       leaf global {
         description "Global history";
         type empty;
       }
     }
     output {
       choice output_c {
         case output-tag {
           leaf output {
             type string;
           }
         }
         case actual-tag {
           anyxml multi-chassis-cluster-device-history-information;
         }
         case multichassis-tag {
           anyxml multi-routing-engine-results;
         }
       }
     }
   }
   rpc get-chassis-satellite-redundacy-grp-if-info {
     description "Display satellite interface information";
     input {
       leaf interface-name {
         description "Name of interface";
         type union {
           type jt:interface-name;
           type string {
             pattern "<.*>|$.*";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml multi-chassis-cluster-interface-information;
         }
         case multichassis-tag {
           anyxml multi-routing-engine-results;
         }
       }
     }
   }
   rpc get-chassis-satellite-extended-port-information {
     description "Display extended-port information";
     input {
       leaf interface-name {
         description "Interface name";
         type string;
       }
       leaf since {
         description "Show history since YYYY-MM-DD.HH:MM:SS";
         type jt:time;
       }
       leaf fpc-slot {
         description "Satellite slot number";
         type union {
           type string {
             pattern "<.*>|$.*";
           }
           type uint32 {
             range "65 .. 254";
           }
         }
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml extended-port-information;
         }
         case multichassis-tag {
           anyxml multi-routing-engine-results;
         }
       }
     }
   }
   rpc get-chassis-satellite-upgrade-group-information {
     description "Display upgrade group information";
     input {
       leaf level {
         default "terse";
         type enumeration {
           enum "terse" {
             description "Display terse output (default)";
           }
           enum "brief" {
             description "Display brief output";
           }
           enum "detail" {
             description "Display detailed output";
           }
           enum "extensive" {
             description "Display extensive output";
           }
         }
       }
       leaf group-name {
         description "Upgrade group name";
         type string;
       }
     }
     output {
       choice output_c {
         case output-tag {
           leaf output {
             type string;
           }
         }
         case actual-tag {
           anyxml upgrade-group-information;
         }
         case multichassis-tag {
           anyxml multi-routing-engine-results;
         }
       }
     }
   }
   rpc get-chassis-satellite-neighbor-information {
     description "Display satellite adjacency information";
     input {
       leaf interface-name {
         description "Name of interface";
         type string;
       }
       leaf since {
         description "Show history since YYYY-MM-DD.HH:MM:SS";
         type jt:time;
       }
       leaf level {
         default "terse";
         type enumeration {
           enum "terse" {
             description "Display terse output (default)";
           }
           enum "brief" {
             description "Display brief output";
           }
           enum "detail" {
             description "Display detailed output";
           }
           enum "extensive" {
             description "Display extensive output";
           }
         }
       }
     }
     output {
       choice output_c {
         case output-tag {
           leaf output {
             type string;
           }
         }
         case actual-tag {
           anyxml adjacency-information;
         }
         case multichassis-tag {
           anyxml multi-routing-engine-results;
         }
       }
     }
   }
   rpc get-chassis-satellite-neighbor-statistics {
     description "Display adjacency statistics information";
     input {
       leaf interface-name {
         description "Name of interface";
         type string;
       }
     }
     output {
       choice output_c {
         case output-tag {
           leaf output {
             type string;
           }
         }
         case actual-tag {
           anyxml adjacency-statistics;
         }
         case multichassis-tag {
           anyxml multi-routing-engine-results;
         }
       }
     }
   }
   rpc get-chassis-satellite-interface-information {
     description "Display satellite protocol interface information";
     input {
       leaf verbosity_level {
         default "brief";
         type enumeration {
           enum "brief" {
             description "Display brief output (default)";
           }
           enum "detail" {
             description "Display detailed output";
           }
           enum "extensive" {
             description "Display extensive output";
           }
         }
       }
       leaf interface-name {
         description "Name of interface";
         type string;
       }
       leaf since {
         description "Show history since YYYY-MM-DD.HH:MM:SS";
         type jt:time;
       }
     }
     output {
       choice output_c {
         case output-tag {
           leaf output {
             type string;
           }
         }
         case actual-tag {
           anyxml satellite-interface-information;
         }
         case multichassis-tag {
           anyxml multi-routing-engine-results;
         }
       }
     }
   }
   rpc get-satellite-management-software-information {
     description "Show satellite software installed";
     input {
       leaf level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml satellite-software-information;
         }
         case multichassis-tag {
           anyxml multi-routing-engine-results;
         }
       }
     }
   }
   rpc get-satellite-power-budget-information {
     description "Show power budget chassis satellite information";
     input {
       leaf fpc-slot {
         description "Satellite slot number";
         type union {
           type string {
             pattern "<.*>|$.*";
           }
           type uint16 {
             range "65 .. 254";
           }
         }
       }
     }
     output {
       choice output_c {
         case output-tag {
           leaf output {
             type string;
           }
         }
         case actual-tag {
           anyxml power-budget-information;
         }
         case multichassis-tag {
           anyxml multi-routing-engine-results;
         }
       }
     }
   }
   rpc get-chassis-satellite-cluster-information {
     description "Show Satellite Cluster information";
     input {
       leaf cluster {
         description "Cluster name";
         type string;
       }
       leaf level {
         default "brief";
         type enumeration {
           enum "terse" {
             description "Display terse output";
           }
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml satellite-cluster-information;
         }
         case multichassis-tag {
           anyxml multi-routing-engine-results;
         }
       }
     }
   }
   rpc get-chassis-satellite-cluster-route {
     description "Display cluster route information";
     input {
       leaf cluster {
         description "Cluster name";
         type string;
       }
       leaf fpc-slot {
         description "Satellite slot number";
         type union {
           type string {
             pattern "<.*>|$.*";
           }
           type uint32 {
             range "65 .. 254";
           }
         }
       }
     }
     output {
       choice output_c {
         case output-tag {
           leaf output {
             type string;
           }
         }
         case actual-tag {
           anyxml cluster-statistics-route;
         }
         case multichassis-tag {
           anyxml multi-routing-engine-results;
         }
       }
     }
   }
   rpc get-chassis-satellite-cluster-statistics {
     description "Display cluster statistics information";
     input {
       leaf cluster {
         description "Cluster name";
         type string;
       }
       leaf fpc-slot {
         description "Satellite slot number";
         type union {
           type string {
             pattern "<.*>|$.*";
           }
           type uint32 {
             range "65 .. 254";
           }
         }
       }
     }
     output {
       choice output_c {
         case output-tag {
           leaf output {
             type string;
           }
         }
         case actual-tag {
           anyxml cluster-statistics;
         }
         case multichassis-tag {
           anyxml multi-routing-engine-results;
         }
       }
     }
   }
   rpc get-chassis-pic-mode-information {
     description "Show a member's chassis pic-mode";
     output {
       choice output_c {
         case output-tag {
           leaf output {
             type string;
           }
         }
         case actual-tag {
           anyxml chassis-pic-mode-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
