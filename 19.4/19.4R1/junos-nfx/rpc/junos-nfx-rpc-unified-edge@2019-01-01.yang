/*
 * Copyright (c) 2019 Juniper Networks, Inc.
 * All rights reserved.
 */
 module junos-nfx-rpc-unified-edge {
   namespace "http://yang.juniper.net/junos-nfx/rpc/unified-edge";

   prefix unified-edge;

   import junos-common-types {
     prefix jt;
     revision-date 2019-01-01;
   }

   organization "Juniper Networks, Inc.";

   contact "yang-support@juniper.net";

   description "Junos RPC YANG module for unified-edge command(s)";

   revision 2019-01-01 {
     description "Junos: 19.4R1.9";
   }

   rpc get-mobile-gateway-aaa-statistics {
     description "Show AAA statistics";
     input {
       leaf statistics-type {
         description "Specify statistics type";
         type enumeration {
           enum "authentication" {
             description "Authentication statistics";
           }
           enum "accounting" {
             description "Accounting statistics";
           }
           enum "dynamic-requests" {
             description "Dynamic Authorization requests statistics";
           }
         }
         mandatory true;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml mobile-gateway-aaa-statistics;
         }
         case multichassis-tag {
           anyxml multi-routing-engine-results;
         }
       }
     }
   }
   rpc get-mobile-gateway-aaa-radius-statistics {
     description "Show RADIUS server statistics";
     input {
       leaf statistics-type {
         description "Specify statistics type";
         type enumeration {
           enum "authentication" {
             description "Authentication statistics";
           }
           enum "accounting" {
             description "Accounting statistics";
           }
           enum "dynamic-requests" {
             description "Dynamic Authorization requests statistics";
           }
         }
         mandatory true;
       }
       leaf radius-server-name {
         description "Show statistics related to the RADIUS server";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-radius-statistics;
         }
         case multichassis-tag {
           anyxml multi-routing-engine-results;
         }
       }
     }
   }
   rpc get-mobile-gateway-aaa-network-element-status {
     description "Display network element status";
     input {
       leaf network-element-name {
         description "Show status related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
     }
     output {
       choice output_c {
         case output-tag {
           leaf output {
             type string;
           }
         }
         case actual-tag {
           anyxml mobile-gateway-aaa-network-element-status;
         }
         case multichassis-tag {
           anyxml multi-routing-engine-results;
         }
       }
     }
   }
   rpc get-mobile-gateway-aaa-network-element-group-status {
     description "Display network element group status";
     input {
       leaf network-element-name {
         description "Show status related to the network element group";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-network-element-group-status;
         }
         case multichassis-tag {
           anyxml multi-routing-engine-results;
         }
       }
     }
   }
   rpc get-mobile-gateway-charging-xfer-stats {
     description "Show charging transfer statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging stats of transport-profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-xfer-stats;
         }
         case multichassis-tag {
           anyxml multi-routing-engine-results;
         }
       }
     }
   }
   rpc get-mobile-gateway-charging-xfer-status {
     description "Show charging transfer status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging transport-profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-xfer-status;
         }
         case multichassis-tag {
           anyxml multi-routing-engine-results;
         }
       }
     }
   }
   rpc get-mobile-gateway-charging-path-stats {
     description "Show charging path statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-path-stats;
         }
         case multichassis-tag {
           anyxml multi-routing-engine-results;
         }
       }
     }
   }
   rpc get-mobile-gateway-charging-path-status {
     description "Show charging path status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-path-status;
         }
         case multichassis-tag {
           anyxml multi-routing-engine-results;
         }
       }
     }
   }
   rpc get-mobile-gateway-charging-local-persist-stats {
     description "Show charging local-persistent-storage statistics";
     input {
       leaf gateway {
         description "Gateway name";
         type string {
           length "1 .. 64";
         }
       }
     }
     output {
       choice output_c {
         case output-tag {
           leaf output {
             type string;
           }
         }
         case actual-tag {
           anyxml mobile-gateway-charging-local-persist-stats;
         }
         case multichassis-tag {
           anyxml multi-routing-engine-results;
         }
       }
     }
   }
   rpc get-ggsn-pgw-charging-service-mode {
     description "Show service mode status for a profile";
     input {
       leaf gateway {
         description "Gateway name";
         type string {
           length "1 .. 64";
         }
         mandatory true;
       }
       leaf charging-profile {
         description "Charging profile name";
         type string {
           length "1 .. 128";
         }
       }
       leaf transport-profile {
         description "Transport profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ggsn-pgw-charging-service-mode;
         }
         case multichassis-tag {
           anyxml multi-routing-engine-results;
         }
       }
     }
   }
   rpc get-mobile-gateway-charging-global-stats {
     description "Show charging global statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-global-stats;
         }
         case multichassis-tag {
           anyxml multi-routing-engine-results;
         }
       }
     }
   }
   rpc get-gtpc-statistics {
     description "Show GTP statistics";
     input {
       leaf gateway {
         description "Show statistics for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtp-show-interface-stats {
         description "Specify the GTP interface to display statistics";
         type enumeration {
           enum "gn" {
             description "GTP gn interface statistics";
           }
           enum "gp" {
             description "GTP gp interface statistics";
           }
           enum "s5" {
             description "GTP s5 interface statistics";
           }
           enum "s8" {
             description "GTP s8 interface statistics";
           }
         }
       }
       leaf gtp-show-stats-version {
         description "Specify the GTP version to display statistics";
         type enumeration {
           enum "v0" {
             description "GTP version 0 statistics";
           }
           enum "v1" {
             description "GTP version 1 statistics";
           }
           enum "v2" {
             description "GTP version 2 statistics";
           }
         }
       }
       leaf detail {
         description "GTP cause stats included";
         type empty;
       }
     }
     output {
       choice output_c {
         case output-tag {
           leaf output {
             type string;
           }
         }
         case actual-tag {
           anyxml gtpc-statistics;
         }
         case multichassis-tag {
           anyxml multi-routing-engine-results;
         }
       }
     }
   }
   rpc get-gtpc-peer-information {
     description "Show GTP Peer Information ";
     input {
       leaf gateway {
         description "Show gtp peer information for a gateway";
         type string {
           length "1 .. 64";
         }
       }
       leaf local-address {
         description "Local IP address for peer";
         type string;
       }
       leaf remote-address {
         description "Remote IP address of peer";
         type string;
       }
       leaf routing-instance {
         description "Routing Instance of peer";
         type string;
       }
       leaf detail {
         description "Scratch pad statistics included";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gn {
         description "GTP gn Interface Peers";
         type empty;
       }
       leaf gp {
         description "GTP gp Interface Peers";
         type empty;
       }
       leaf s5 {
         description "GTP s5 Interface Peers";
         type empty;
       }
       leaf s8 {
         description "GTP s8 Interface Peers";
         type empty;
       }
     }
     output {
       choice output_c {
         case output-tag {
           leaf output {
             type string;
           }
         }
         case actual-tag {
           anyxml gtpc-peer-information;
         }
         case multichassis-tag {
           anyxml multi-routing-engine-results;
         }
       }
     }
   }
   rpc get-gtpc-peer-history-information-pgw {
     description "History of previous peers ";
     input {
       leaf local-address {
         description "Local IP address for peer";
         type string;
       }
       leaf remote-address {
         description "Remote IP address of peer";
         type string;
       }
       leaf routing-instance {
         description "Routing Instance of peer";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show gtp peer information for a gateway";
         type string {
           length "1 .. 64";
         }
       }
       leaf detail {
         description "Scratch pad statistics included";
         type empty;
       }
     }
     output {
       choice output_c {
         case output-tag {
           leaf output {
             type string;
           }
         }
         case actual-tag {
           anyxml gtpc-peer-history-information;
         }
         case multichassis-tag {
           anyxml multi-routing-engine-results;
         }
       }
     }
   }
   rpc get-gtpc-peer-count {
     description "Show GTP Peer Count";
     output {
       choice output_c {
         case output-tag {
           leaf output {
             type string;
           }
         }
         case actual-tag {
           anyxml gtpc-peer-count;
         }
         case multichassis-tag {
           anyxml multi-routing-engine-results;
         }
       }
     }
   }
   rpc get-gtpc-peer-statistics {
     description "Show GTP Peer statistics";
     input {
       leaf gateway {
         description "Show gtp peer statistics for a gateway";
         type string {
           length "1 .. 64";
         }
       }
       leaf remote-address {
         description "Remote IP address of peer";
         type string;
         mandatory true;
       }
       leaf local-address {
         description "Local IP address for peer";
         type string;
       }
       leaf routing-instance {
         description "Routing Instance of peer";
         type string;
       }
       leaf fpc-slot {
         description "FPC slot number";
         type union {
           type uint32;
           type string {
             pattern "<.*>|$.*";
           }
         }
       }
       leaf history {
         description "History of previous peers";
         type empty;
       }
       leaf pic-slot {
         description "PIC slot number";
         type union {
           type uint32;
           type string {
             pattern "<.*>|$.*";
           }
         }
       }
       leaf gtp-version {
         description "Specify the GTP version to display statistics";
         default "gtp-all";
         type enumeration {
           enum "v0" {
             description "GTP version 0 statistics";
           }
           enum "v1" {
             description "GTP version 1 statistics";
           }
           enum "v2" {
             description "GTP version 2 statistics";
           }
           enum "gtp-all" {
             description "GTP all version statistics";
           }
         }
       }
       leaf detail {
         description "GTP cause stats included";
         type empty;
       }
     }
     output {
       choice output_c {
         case output-tag {
           leaf output {
             type string;
           }
         }
         case actual-tag {
           anyxml gtpc-peer-statistics;
         }
         case multichassis-tag {
           anyxml multi-routing-engine-results;
         }
       }
     }
   }
   rpc get-mobile-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-service-mode;
         }
         case multichassis-tag {
           anyxml multi-routing-engine-results;
         }
       }
     }
   }
   rpc get-ggsn-pdn-gateway-interfaces-information {
     description "Show system interfaces";
     input {
       leaf gateway {
         description "Show system interfaces for a gateway";
         type string {
           length "1 .. 64";
         }
       }
     }
     output {
       choice output_c {
         case output-tag {
           leaf output {
             type string;
           }
         }
         case actual-tag {
           anyxml mobile-gateway-interfaces;
         }
         case multichassis-tag {
           anyxml multi-routing-engine-results;
         }
       }
     }
   }
   rpc get-mobile-ggsn-pdn-gateway-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml gateway-system-interface-service-mode;
         }
         case multichassis-tag {
           anyxml multi-routing-engine-results;
         }
       }
     }
   }
   rpc get-mobile-gateways-ip-reassembly-statistics {
     description "Show IP reassembly statistics";
     input {
       leaf family {
         type enumeration {
           enum "inet" {
             description "Family inet";
           }
         }
       }
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-ip-reassembly-statistics;
         }
         case multichassis-tag {
           anyxml multi-routing-engine-results;
         }
       }
     }
   }
   rpc get-cac-statistics {
     description "Display CAC statistics";
     input {
       leaf gateway {
         description "Show statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       choice output_c {
         case output-tag {
           leaf output {
             type string;
           }
         }
         case actual-tag {
           anyxml cac-statistics;
         }
         case multichassis-tag {
           anyxml multi-routing-engine-results;
         }
       }
     }
   }
   rpc get-mobile-gateway-aaa-diam-stats-gx {
     description "Show diameter statistics related to Gx";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-stats-gx;
         }
         case multichassis-tag {
           anyxml multi-routing-engine-results;
         }
       }
     }
   }
   rpc get-mobile-gateway-aaa-diam-stats-gy {
     description "Show diameter statistics related to Gy";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-stats-gy;
         }
         case multichassis-tag {
           anyxml multi-routing-engine-results;
         }
       }
     }
   }
   rpc get-mobile-gateway-aaa-diam-ne-statistics {
     description "Show network-element specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-ne-statistics;
         }
         case multichassis-tag {
           anyxml multi-routing-engine-results;
         }
       }
     }
   }
   rpc get-mobile-gateway-aaa-diam-ne-status {
     description "Show Diameter network-element status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
     }
     output {
       choice output_c {
         case output-tag {
           leaf output {
             type string;
           }
         }
         case actual-tag {
           anyxml mobile-gateway-aaa-diam-ne-status;
         }
         case multichassis-tag {
           anyxml multi-routing-engine-results;
         }
       }
     }
   }
   rpc get-mobile-gateway-aaa-diam-peer-statistics {
     description "Show peer specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-peer-statistics;
         }
         case multichassis-tag {
           anyxml multi-routing-engine-results;
         }
       }
     }
   }
   rpc get-mobile-gateway-aaa-diam-peer-status {
     description "Show the peer status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-peer-status;
         }
         case multichassis-tag {
           anyxml multi-routing-engine-results;
         }
       }
     }
   }
   rpc get-mobile-ggsn-pdn-gateway-status {
     description "Show gateway status";
     input {
       leaf gateway {
         description "Show subscriber for a gateway";
         type string {
           length "1 .. 64";
         }
       }
       leaf apn-name {
         description "Name of APN";
         type string {
           length "1 .. 100";
         }
       }
       leaf qci {
         description "Show status per QCI";
         type empty;
       }
       leaf gtpv2-priority-level {
         description "Show status per gtpv2 priority level";
         type empty;
       }
       leaf traffic-class {
         description "Show status for a traffic class level";
         type empty;
       }
       leaf gtpv1-arp {
         description "Show status per gtp v1 ARP";
         type empty;
       }
       leaf rat-type {
         description "Show status per RAT-Type";
         type empty;
       }
       leaf pdn-type {
         description "Display status per PDN-Type";
         type empty;
       }
       leaf roaming-status {
         description "Display status per roaming status type";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml mobile-gateway-status;
         }
         case multichassis-tag {
           anyxml multi-routing-engine-results;
         }
       }
     }
   }
   rpc get-mobile-gateways-preemption-list-pgw {
     description "Show gateway preemption list";
     input {
       leaf gateway {
         description "Show preemption list for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-preemption-list-status-pgw;
         }
         case multichassis-tag {
           anyxml multi-routing-engine-results;
         }
       }
     }
   }
   rpc get-mobile-gateway-gtp-peer-apfe-distribution-pgw {
     description "Show bearer anchor PFE distribution per GTP peer";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show bearer APFE distribution per GTP peer for gateway";
         type string {
           length "1 .. 64";
         }
       }
       leaf remote-address {
         description "Remote IP address of peer";
         type string;
         mandatory true;
       }
       leaf local-address {
         description "Local IP address for peer";
         type string;
       }
       leaf routing-instance {
         description "Routing Instance of Peer";
         type union {
           type uint32;
           type string {
             pattern "<.*>|$.*";
           }
         }
       }
     }
     output {
       choice output_c {
         case output-tag {
           leaf output {
             type string;
           }
         }
         case actual-tag {
           anyxml mobile-gateway-gtp-peer-apfe-distribution;
         }
         case multichassis-tag {
           anyxml multi-routing-engine-results;
         }
       }
     }
   }
   rpc get-mobile-gateways-session-state-pgw {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-status;
         }
         case multichassis-tag {
           anyxml multi-routing-engine-results;
         }
       }
     }
   }
   rpc get-mobile-ggsn-pdn-gateway-subscriber-traffic-class {
     description "Show subscribers at traffic class level";
     input {
       leaf gtpv1-traffic-class {
         description "Show subscribers for a particular traffic class";
         type enumeration {
           enum "background" {
             description "Traffic class background";
           }
           enum "conversational" {
             description "Traffic class conversational";
           }
           enum "streaming" {
             description "Traffic class streaming";
           }
           enum "interactive" {
             description "Traffic class interactive";
           }
         }
         mandatory true;
       }
       leaf traffic-handling-priority {
         description "Traffic handling priority";
         type union {
           type string {
             pattern "<.*>|$.*";
           }
           type uint32 {
             range "1 .. 3";
           }
         }
       }
     }
     output {
       choice output_c {
         case output-tag {
           leaf output {
             type string;
           }
         }
         case actual-tag {
           anyxml mobile-ggsn-pdn-gateway-subscriber-traffic-class;
         }
         case multichassis-tag {
           anyxml multi-routing-engine-results;
         }
       }
     }
   }
   rpc get-mobile-gateways-apn-statistics {
     description "Show APN statistics";
     input {
       leaf gateway {
         description "Show apn statistics of the gateway";
         type string {
           length "1 .. 64";
         }
       }
       leaf access-point-name {
         description "APN name";
         type string {
           length "1 .. 100";
         }
         mandatory true;
       }
     }
     output {
       choice output_c {
         case output-tag {
           leaf output {
             type string;
           }
         }
         case actual-tag {
           anyxml mobile-gateways-apn-statistics;
         }
         case multichassis-tag {
           anyxml multi-routing-engine-results;
         }
       }
     }
   }
   rpc get-mobile-gateways-apn-call-rate-statistics {
     input {
       leaf gateway {
         description "Show apn call rate statistics of the gateway";
         type string {
           length "1 .. 64";
         }
         mandatory true;
       }
       leaf apn-name {
         description "APN name";
         type string {
           length "1 .. 100";
         }
         mandatory true;
       }
     }
     output {
       choice output_c {
         case output-tag {
           leaf output {
             type string;
           }
         }
         case actual-tag {
           anyxml mobile-gateway-call-rate-statistics;
         }
         case multichassis-tag {
           anyxml multi-routing-engine-results;
         }
       }
     }
   }
   rpc get-mobile-gateways-apn-service-mode {
     description "Show service mode status for an APN";
     input {
       leaf gateway {
         description "Gateway name";
         type string {
           length "1 .. 64";
         }
       }
       leaf apn-name {
         description "APN name";
         type string {
           length "1 .. 100";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-apn-service-mode;
         }
         case multichassis-tag {
           anyxml multi-routing-engine-results;
         }
       }
     }
   }
   rpc get-mobile-gateways-statistics {
     description "Show statistics";
     input {
       leaf gateway {
         description "Show statistics for a gateway";
         type string {
           length "1 .. 64";
         }
       }
       leaf apn {
         description "APN name";
         type string {
           length "1 .. 100";
         }
       }
       leaf qci {
         description "QCI value";
         type union {
           type string {
             pattern "<.*>|$.*";
           }
           type int32 {
             range "1 .. 9";
           }
         }
       }
       leaf gtpv2-priority-level {
         description "GTPv2 priority level";
         type union {
           type string {
             pattern "<.*>|$.*";
           }
           type uint32 {
             range "1 .. 15";
           }
         }
       }
       leaf gtpv1-arp {
         description "GTPv1 ARP Value";
         type union {
           type string {
             pattern "<.*>|$.*";
           }
           type uint32 {
             range "1 .. 3";
           }
         }
       }
     }
     output {
       choice output_c {
         case output-tag {
           leaf output {
             type string;
           }
         }
         case actual-tag {
           anyxml mobile-gateways-statistics;
         }
         case multichassis-tag {
           anyxml multi-routing-engine-results;
         }
       }
     }
   }
   rpc get-mobile-ggsn-pdn-gateway-statistics-traffic-class {
     description "Show statistics at traffic class level";
     input {
       leaf gtpv1-traffic-class {
         description "Show statistics for a traffic class level";
         type enumeration {
           enum "background" {
             description "Traffic class background";
           }
           enum "conversational" {
             description "Traffic class conversational";
           }
           enum "streaming" {
             description "Traffic class streaming";
           }
           enum "interactive" {
             description "Traffic class interactive";
           }
         }
         mandatory true;
       }
       leaf traffic-handling-priority {
         description "Traffic handling priority";
         type union {
           type string {
             pattern "<.*>|$.*";
           }
           type uint32 {
             range "1 .. 3";
           }
         }
       }
     }
     output {
       choice output_c {
         case output-tag {
           leaf output {
             type string;
           }
         }
         case actual-tag {
           anyxml mobile-ggsn-pdn-gateway-statistics-traffic-class;
         }
         case multichassis-tag {
           anyxml multi-routing-engine-results;
         }
       }
     }
   }
   rpc get-mobile-ggsn-pdn-gateway-call-rate-statistics {
     description "Show gateway call-rate statistics";
     input {
       leaf history {
         description "History of statistics collected";
         type empty;
       }
       leaf gateway {
         description "Gateway name";
         type string {
           length "1 .. 64";
         }
       }
     }
     output {
       choice output_c {
         case output-tag {
           leaf output {
             type string;
           }
         }
         case actual-tag {
           anyxml mobile-gateway-call-rate-statistics;
         }
         case multichassis-tag {
           anyxml multi-routing-engine-results;
         }
       }
     }
   }
   rpc get-ggssn-pgw-address-assign-service-mode {
     description "Show service mode status for a pool";
     input {
       leaf pool {
         description "Address pool name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ggsn-pgw-address-assign-service-mode;
         }
         case multichassis-tag {
           anyxml multi-routing-engine-results;
         }
       }
     }
   }
   rpc get-mobile-gateway-sm-ippool-pool-information {
     description "Show pool specific information";
     input {
       leaf pool-name {
         description "Show information for a specific pool";
         type string {
           length "1 .. 64";
         }
       }
       leaf all_ranges {
         type enumeration {
           enum "ranges" {
             description "Show information for all ranges in the pool";
           }
         }
       }
       leaf range-name {
         description "Show information for a range in the pool";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "summary" {
             description "Display summary output";
           }
           enum "brief" {
             description "Display brief output (default)";
           }
           enum "detail" {
             description "Display detailed output";
           }
         }
       }
     }
     output {
       choice output_c {
         case output-tag {
           leaf output {
             type string;
           }
         }
         case actual-tag {
           anyxml mobile-gateway-sm-ippool-pool-information;
         }
         case multichassis-tag {
           anyxml multi-routing-engine-results;
         }
       }
     }
   }
   rpc get-mobile-gateway-sm-ippool-group-information {
     description "Show group specific information";
     input {
       leaf group-name {
         description "Show information for a specific group";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-sm-ippool-group-information;
         }
         case multichassis-tag {
           anyxml multi-routing-engine-results;
         }
       }
     }
   }
   rpc get-mobile-gateway-sm-ippool-statistics {
     description "Show address assignment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-sm-ippool-statistics;
         }
         case multichassis-tag {
           anyxml multi-routing-engine-results;
         }
       }
     }
   }
   rpc get-mobile-gateway-pgw-rmm-client-status {
     description "Show all the resource controller clients state info";
     input {
       leaf gateway {
         description "Show resource controller clients state info for a gateway";
         type string {
           length "1 .. 64";
         }
       }
     }
     output {
       choice output_c {
         case output-tag {
           leaf output {
             type string;
           }
         }
         case actual-tag {
           anyxml rmpsd-show-rmm-client-command;
         }
         case multichassis-tag {
           anyxml multi-routing-engine-results;
         }
       }
     }
   }
   rpc get-tdf-gateway-aaa-statistics {
     description "TDF aaa statistics";
     input {
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml tdf-gateway-aaa-statistics;
         }
         case multichassis-tag {
           anyxml multi-routing-engine-results;
         }
       }
     }
   }
   rpc radius-client-statistics {
     description "TDF radius client statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf client {
         description "Radius client name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml radius-client-statistics;
         }
         case multichassis-tag {
           anyxml multi-routing-engine-results;
         }
       }
     }
   }
   rpc get-aaa-radius-client-status {
     description "Display radius client status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf client {
         description "Radius client name";
         type string {
           length "1 .. 32";
         }
       }
     }
     output {
       choice output_c {
         case output-tag {
           leaf output {
             type string;
           }
         }
         case actual-tag {
           anyxml aaa-radius-client-status;
         }
         case multichassis-tag {
           anyxml multi-routing-engine-results;
         }
       }
     }
   }
   rpc get-aaa-radius-element-status {
     description "Display radius network-element status";
     input {
       leaf network-element-name {
         description "Show status related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
     }
     output {
       choice output_c {
         case output-tag {
           leaf output {
             type string;
           }
         }
         case actual-tag {
           anyxml aaa-radius-network-element-status;
         }
         case multichassis-tag {
           anyxml multi-routing-engine-results;
         }
       }
     }
   }
   rpc get-aaa-radius-element-statistics {
     description "Display radius network-element statistics";
     input {
       leaf network-element-name {
         description "Show statistics related to the network element";
         type string {
           length "1 .. 32";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml aaa-radius-network-element-statistics;
         }
         case multichassis-tag {
           anyxml multi-routing-engine-results;
         }
       }
     }
   }
   rpc radius-server-statistics {
     description "TDF radius server statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf radius-server-name {
         description "Show statistics related to the radius server";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml radius-server-statistics;
         }
         case multichassis-tag {
           anyxml multi-routing-engine-results;
         }
       }
     }
   }
   rpc get-aaa-radius-server-status {
     description "Display radius server status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf radius-server-name {
         description "Show status related to the radius server";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml aaa-radius-server-status;
         }
         case multichassis-tag {
           anyxml multi-routing-engine-results;
         }
       }
     }
   }
   rpc radius-snoop-segment-statistics {
     description "TDF radius snoop-segment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf segment {
         description "Radius snoop-segment";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml radius-snoop-segment-statistics;
         }
         case multichassis-tag {
           anyxml multi-routing-engine-results;
         }
       }
     }
   }
   rpc get-tdf-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml sgw-gateway-service-mode;
         }
         case multichassis-tag {
           anyxml multi-routing-engine-results;
         }
       }
     }
   }
   rpc get-tdf-interfaces-information {
     description "Show system interfaces";
     input {
       leaf gateway {
         description "Show system interfaces for a gateway";
         type string {
           length "1 .. 64";
         }
       }
     }
     output {
       choice output_c {
         case output-tag {
           leaf output {
             type string;
           }
         }
         case actual-tag {
           anyxml mobile-gateway-interfaces;
         }
         case multichassis-tag {
           anyxml multi-routing-engine-results;
         }
       }
     }
   }
   rpc get-mobile-tdf-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml gateway-system-interface-service-mode;
         }
         case multichassis-tag {
           anyxml multi-routing-engine-results;
         }
       }
     }
   }
   rpc get-tdf-cac-statistics {
     description "Display CAC statistics";
     input {
       leaf gateway {
         description "Show statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       choice output_c {
         case output-tag {
           leaf output {
             type string;
           }
         }
         case actual-tag {
           anyxml cac-statistics;
         }
         case multichassis-tag {
           anyxml multi-routing-engine-results;
         }
       }
     }
   }
   rpc get-diameter-statistics-gx {
     description "Show diameter statistics related to gx";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-stats-gx;
         }
         case multichassis-tag {
           anyxml multi-routing-engine-results;
         }
       }
     }
   }
   rpc get-diameter-network-element-statistics {
     description "Show network-element specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-ne-statistics;
         }
         case multichassis-tag {
           anyxml multi-routing-engine-results;
         }
       }
     }
   }
   rpc get-diamieter-network-element-status {
     description "Show diameter network-element status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf network-element-name {
         description "Diameter network element name";
         type string {
           length "1 .. 32";
         }
       }
     }
     output {
       choice output_c {
         case output-tag {
           leaf output {
             type string;
           }
         }
         case actual-tag {
           anyxml mobile-gateway-aaa-diam-ne-status;
         }
         case multichassis-tag {
           anyxml multi-routing-engine-results;
         }
       }
     }
   }
   rpc get-gateway-diameter-peer-statistics {
     description "Show peer specific statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-peer-statistics;
         }
         case multichassis-tag {
           anyxml multi-routing-engine-results;
         }
       }
     }
   }
   rpc get-diameter-peer-status {
     description "Show the peer status";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 63";
         }
       }
       leaf peer-name {
         description "Diameter peer name";
         type string {
           length "1 .. 32";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-aaa-diam-peer-status;
         }
         case multichassis-tag {
           anyxml multi-routing-engine-results;
         }
       }
     }
   }
   rpc get-tdf-gateway-subscribers {
     description "Show information related to subscribers";
     input {
       leaf gateway {
         description "Show subscribers for a gateway";
         type string {
           length "1 .. 64";
         }
       }
       leaf domain {
         description "Name of TDF domain";
         type string {
           length "1 .. 63";
         }
       }
       leaf subscriber-name {
         description "IFL subscriber name";
         type string;
       }
       leaf business-subscribers {
         description "Show only business subscribers";
         type empty;
       }
       leaf v4-addr {
         description "Show  subscribers for matching address";
         type jt:ipaddr;
       }
       leaf routing-instance {
         description "Name of routing instance";
         type string;
       }
       leaf v6-addr {
         description "Show subscribers for matching address";
         type jt:ipv6addr;
       }
       leaf pdn-type {
         description "Show subscribers by PDN-Type";
         type enumeration {
           enum "ipv4" {
             description "Show ipv4 subscribers";
           }
           enum "ipv6" {
             description "Show ipv6 subscribers";
           }
           enum "ipv4-v6" {
             description "Show ipv4-v6 subscribers";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case multichassis-tag {
           anyxml multi-routing-engine-results;
         }
       }
     }
   }
   rpc get-tdf-gateway-subscriber-dataplane-statistics {
     description "Show dataplane statistics";
     input {
       leaf gateway {
         description "Show subscribers for a gateway";
         type string {
           length "1 .. 64";
         }
       }
       leaf subscriber-name {
         description "IFL subscriber name";
         type string;
       }
       leaf v4-addr {
         description "Show  subscribers for matching address";
         type jt:ipaddr;
       }
       leaf routing-instance {
         description "Name of data routing instance";
         type string;
       }
       leaf business-subscribers {
         description "Show only business subscribers";
         type empty;
       }
       leaf v6-addr {
         description "Show subscribers for matching address";
         type jt:ipv6addr;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc get-tdf-gateway-stuck-subscribers {
     description "Show stuck subscribers";
     output {
       choice output_c {
         case output-tag {
           leaf output {
             type string;
           }
         }
         case multichassis-tag {
           anyxml multi-routing-engine-results;
         }
       }
     }
   }
   rpc get-tdf-gateway-status {
     description "Show gateway status";
     input {
       leaf gateway {
         description "Show subscriber for a gateway";
         type string {
           length "1 .. 64";
         }
       }
       leaf domain {
         description "Name of TDF domain";
         type string {
           length "1 .. 100";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
           enum "extensive" {
             description "Display extensive output";
           }
         }
       }
     }
     output {
       choice output_c {
         case output-tag {
           leaf output {
             type string;
           }
         }
         case actual-tag {
           anyxml tdf-gateway-status;
         }
         case multichassis-tag {
           anyxml multi-routing-engine-results;
         }
       }
     }
   }
   rpc get-tdf-gateways-status-state {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       choice output_c {
         case output-tag {
           leaf output {
             type string;
           }
         }
         case actual-tag {
           anyxml tdf-gateway-status;
         }
         case multichassis-tag {
           anyxml multi-routing-engine-results;
         }
       }
     }
   }
   rpc get-tdf-statistics {
     description "Show TDF statistics";
     input {
       leaf gateway {
         description "Gateway name";
         type string {
           length "1 .. 64";
         }
       }
       leaf domain {
         description "Domain name";
         type string {
           length "1 .. 63";
         }
       }
     }
     output {
       choice output_c {
         case output-tag {
           leaf output {
             type string;
           }
         }
         case actual-tag {
           anyxml mobile-gateways-statistics;
         }
         case multichassis-tag {
           anyxml multi-routing-engine-results;
         }
       }
     }
   }
   rpc get-tdf-call-rate-statistics {
     description "Show TDF call rate statistics";
     input {
       leaf gateway {
         description "Gateway name";
         type string {
           length "1 .. 64";
         }
         mandatory true;
       }
       leaf domain {
         description "Domain name";
         type string {
           length "1 .. 63";
         }
       }
     }
     output {
       choice output_c {
         case output-tag {
           leaf output {
             type string;
           }
         }
         case actual-tag {
           anyxml tdf-call-rate-statistics-root;
         }
         case multichassis-tag {
           anyxml multi-routing-engine-results;
         }
       }
     }
   }
   rpc get-mobile-gateways-domain-service-mode {
     description "Show service mode status for a domain";
     input {
       leaf gateway {
         description "Gateway name";
         type string {
           length "1 .. 64";
         }
       }
       leaf domain-name {
         description "Domain name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-domain-service-mode;
         }
         case multichassis-tag {
           anyxml multi-routing-engine-results;
         }
       }
     }
   }
   rpc get-mobile-gateways-domain-statistics {
     description "Show statistics for a tdf domain";
     input {
       leaf gateway {
         description "Gateway name";
         type string {
           length "1 .. 64";
         }
       }
       leaf domain-name {
         description "Domain name";
         type string {
           length "1 .. 63";
         }
         mandatory true;
       }
     }
     output {
       choice output_c {
         case output-tag {
           leaf output {
             type string;
           }
         }
         case actual-tag {
           anyxml mobile-gateways-domain-statistics;
         }
         case multichassis-tag {
           anyxml multi-routing-engine-results;
         }
       }
     }
   }
   rpc get-tdf-address-assign-service-mode {
     description "Show service mode status for a pool";
     input {
       leaf pool {
         description "Address pool name";
         type string {
           length "1 .. 64";
         }
       }
       leaf routing-instance {
         description "Name of the routing-instance";
         type string;
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ggsn-pgw-address-assign-service-mode;
         }
         case multichassis-tag {
           anyxml multi-routing-engine-results;
         }
       }
     }
   }
   rpc get-tdf-gateway-sm-ippool-pool-information {
     description "Show pool specific information";
     input {
       leaf pool-name {
         description "Show information for a specific pool";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf routing-instance {
         description "Name of the routing-instance";
         type string;
       }
       leaf verbosity_level {
         default "brief";
         type enumeration {
           enum "summary" {
             description "Display summary output";
           }
           enum "brief" {
             description "Display brief output (default)";
           }
           enum "detail" {
             description "Display detailed output";
           }
         }
       }
     }
     output {
       choice output_c {
         case output-tag {
           leaf output {
             type string;
           }
         }
         case actual-tag {
           anyxml mobile-gateway-sm-ippool-pool-information;
         }
         case multichassis-tag {
           anyxml multi-routing-engine-results;
         }
       }
     }
   }
   rpc get-tdf-gateway-sm-ippool-statistics {
     description "Show address assignment statistics";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Gateway name";
         type string {
           length "1 .. 64";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-sm-ippool-statistics;
         }
         case multichassis-tag {
           anyxml multi-routing-engine-results;
         }
       }
     }
   }
   rpc get-mobile-gateway-tdf-client-status-information {
     description "Show all the resource controller clients state info";
     input {
       leaf gateway {
         description "Show resource controller clients state info for a gateway";
         type string {
           length "1 .. 64";
         }
       }
     }
     output {
       choice output_c {
         case output-tag {
           leaf output {
             type string;
           }
         }
         case actual-tag {
           anyxml mobile-gateway-tdf-client-status;
         }
         case multichassis-tag {
           anyxml multi-routing-engine-results;
         }
       }
     }
   }
   rpc get-mobile-gateway-sgw-charging-xfer-stats {
     description "Show charging transfer statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging stats of transport-profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-xfer-stats;
         }
         case multichassis-tag {
           anyxml multi-routing-engine-results;
         }
       }
     }
   }
   rpc get-mobile-gateway-sgw-charging-xfer-status {
     description "Show charging transfer status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf transport-profile-name {
         description "Charging transport-profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-xfer-status;
         }
         case multichassis-tag {
           anyxml multi-routing-engine-results;
         }
       }
     }
   }
   rpc get-mobile-gateway-sgw-charging-path-stats {
     description "Show charging path statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-path-stats;
         }
         case multichassis-tag {
           anyxml multi-routing-engine-results;
         }
       }
     }
   }
   rpc get-mobile-gateway-sgw-charging-path-status {
     description "Show charging path status";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtpp-peer-addr {
         description "Charging stats matching gtpp peer address";
         type jt:ipaddr;
       }
       leaf gtpp-peer-name {
         description "Charging stats matching this gtpp peer name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-path-status;
         }
         case multichassis-tag {
           anyxml multi-routing-engine-results;
         }
       }
     }
   }
   rpc get-mobile-gateway-sgw-charging-local-persist-stats {
     description "Show charging local-persistent-storage statistics";
     input {
       leaf gateway {
         description "Gateway name";
         type string {
           length "1 .. 64";
         }
       }
     }
     output {
       choice output_c {
         case output-tag {
           leaf output {
             type string;
           }
         }
         case actual-tag {
           anyxml mobile-gateway-charging-local-persist-stats;
         }
         case multichassis-tag {
           anyxml multi-routing-engine-results;
         }
       }
     }
   }
   rpc show-mobile-gateway-sgw-charging-trigger-profile {
     description "Show information of trigger profile";
     input {
       leaf gateway {
         description "Gateway name";
         type string {
           length "1 .. 64";
         }
       }
       leaf trigger-profile-name {
         description "Charging trigger profile matching this name";
         type string {
           length "1 .. 128";
         }
       }
     }
     output {
       choice output_c {
         case output-tag {
           leaf output {
             type string;
           }
         }
         case actual-tag {
           anyxml mobile-gateway-charging-trigger-profile;
         }
         case multichassis-tag {
           anyxml multi-routing-engine-results;
         }
       }
     }
   }
   rpc get-sgw-charging-service-mode {
     description "Show service mode status for a profile";
     input {
       leaf gateway {
         description "Gateway name";
         type string {
           length "1 .. 64";
         }
         mandatory true;
       }
       leaf charging-profile {
         description "Charging profile name";
         type string {
           length "1 .. 128";
         }
       }
       leaf transport-profile {
         description "Transport profile name";
         type string {
           length "1 .. 128";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml sgw-charging-service-mode;
         }
         case multichassis-tag {
           anyxml multi-routing-engine-results;
         }
       }
     }
   }
   rpc get-mobile-gateway-sgw-charging-global-stats {
     description "Show charging global statistics";
     input {
       leaf gateway {
         description "Gateway name";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-charging-global-stats;
         }
         case multichassis-tag {
           anyxml multi-routing-engine-results;
         }
       }
     }
   }
   rpc get-sgw-gtpc-statistics {
     description "Show GTP statistics";
     input {
       leaf gateway {
         description "Show gtp statistics for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gtp-show-interface-stats {
         description "Specify the GTP interface to display statistics";
         type enumeration {
           enum "s5" {
             description "GTP s5 interface statistics";
           }
           enum "s8" {
             description "GTP s8 interface statistics";
           }
           enum "s11" {
             description "GTP s11 interface statistics";
           }
           enum "s4" {
             description "GTP s4 interface statistics";
           }
         }
       }
       leaf gtp-show-stats-version {
         description "Specify the GTP version to display statistics";
         type enumeration {
           enum "v1" {
             description "GTP version 1 statistics";
           }
           enum "v2" {
             description "GTP version 2 statistics";
           }
         }
       }
       leaf detail {
         description "GTP cause stats included";
         type empty;
       }
     }
     output {
       choice output_c {
         case output-tag {
           leaf output {
             type string;
           }
         }
         case actual-tag {
           anyxml gtpc-statistics;
         }
         case multichassis-tag {
           anyxml multi-routing-engine-results;
         }
       }
     }
   }
   rpc get-sgw-gtpc-peer-information {
     description "Show GTP Peer Information ";
     input {
       leaf gateway {
         description "Show gtp peer information for a gateway";
         type string {
           length "1 .. 64";
         }
       }
       leaf local-address {
         description "Local IP address for peer";
         type string;
       }
       leaf remote-address {
         description "Remote IP address of peer";
         type string;
       }
       leaf routing-instance {
         description "Routing Instance of peer";
         type string;
       }
       leaf detail {
         description "Scratch pad statistics included";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf s11 {
         description "GTP s11 Interface Peers";
         type empty;
       }
       leaf s4 {
         description "GTP s4 Interface Peers";
         type empty;
       }
       leaf s11-s4 {
         description "GTP s11-s4 Interface Peers";
         type empty;
       }
       leaf s5 {
         description "GTP s5 Interface Peers";
         type empty;
       }
       leaf s8 {
         description "GTP s8 Interface Peers";
         type empty;
       }
       leaf s1u {
         description "GTP s1u Interface Peers";
         type empty;
       }
       leaf s12 {
         description "GTP s12 Interface Peers";
         type empty;
       }
     }
     output {
       choice output_c {
         case output-tag {
           leaf output {
             type string;
           }
         }
         case actual-tag {
           anyxml gtpc-peer-information;
         }
         case multichassis-tag {
           anyxml multi-routing-engine-results;
         }
       }
     }
   }
   rpc get-gtpc-peer-history-information-sgw {
     description "History of previous peers ";
     input {
       leaf local-address {
         description "Local IP address for peer";
         type string;
       }
       leaf remote-address {
         description "Remote IP address of peer";
         type string;
       }
       leaf routing-instance {
         description "Routing Instance of peer";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show gtp peer information for a gateway";
         type string {
           length "1 .. 64";
         }
       }
       leaf detail {
         description "Scratch pad statistics included";
         type empty;
       }
     }
     output {
       choice output_c {
         case output-tag {
           leaf output {
             type string;
           }
         }
         case actual-tag {
           anyxml gtpc-peer-history-information;
         }
         case multichassis-tag {
           anyxml multi-routing-engine-results;
         }
       }
     }
   }
   rpc get-sgw-gtpc-peer-count {
     description "Show GTP Peer Count";
     output {
       choice output_c {
         case output-tag {
           leaf output {
             type string;
           }
         }
         case actual-tag {
           anyxml gtpc-peer-count;
         }
         case multichassis-tag {
           anyxml multi-routing-engine-results;
         }
       }
     }
   }
   rpc get-sgw-gtpc-peer-statistics {
     description "Show GTP Peer statistics";
     input {
       leaf gateway {
         description "Show gtp peer statistics for a gateway";
         type string {
           length "1 .. 64";
         }
       }
       leaf remote-address {
         description "Remote IP address of peer";
         type string;
         mandatory true;
       }
       leaf local-address {
         description "Local IP address for peer";
         type string;
       }
       leaf routing-instance {
         description "Routing Instance of peer";
         type string;
       }
       leaf fpc-slot {
         description "FPC slot number";
         type union {
           type uint32;
           type string {
             pattern "<.*>|$.*";
           }
         }
       }
       leaf history {
         description "History of previous peers";
         type empty;
       }
       leaf pic-slot {
         description "PIC slot number";
         type union {
           type uint32;
           type string {
             pattern "<.*>|$.*";
           }
         }
       }
       leaf detail {
         description "GTP cause stats included";
         type empty;
       }
     }
     output {
       choice output_c {
         case output-tag {
           leaf output {
             type string;
           }
         }
         case actual-tag {
           anyxml gtpc-peer-statistics;
         }
         case multichassis-tag {
           anyxml multi-routing-engine-results;
         }
       }
     }
   }
   rpc get-sgw-gateway-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml sgw-gateway-service-mode;
         }
         case multichassis-tag {
           anyxml multi-routing-engine-results;
         }
       }
     }
   }
   rpc get-serving-gateway-interfaces-information {
     description "Show system interfaces";
     input {
       leaf gateway {
         description "Show system interfaces for a gateway";
         type string {
           length "1 .. 64";
         }
       }
     }
     output {
       choice output_c {
         case output-tag {
           leaf output {
             type string;
           }
         }
         case actual-tag {
           anyxml mobile-gateway-interfaces;
         }
         case multichassis-tag {
           anyxml multi-routing-engine-results;
         }
       }
     }
   }
   rpc get-mobile-serving-gateway-interface-service-mode {
     description "Show service mode status for a gateway";
     input {
       leaf gateway {
         description "Gateway Name";
         type string {
           length "1 .. 63";
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml gateway-system-interface-service-mode;
         }
         case multichassis-tag {
           anyxml multi-routing-engine-results;
         }
       }
     }
   }
   rpc get-mobile-gateways-sgw-ip-reassembly-statistics {
     description "Show IP reassembly statistics";
     input {
       leaf family {
         type enumeration {
           enum "inet" {
             description "Family inet";
           }
         }
       }
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-ip-reassembly-statistics;
         }
         case multichassis-tag {
           anyxml multi-routing-engine-results;
         }
       }
     }
   }
   rpc get-sgw-cac-statistics {
     description "Display CAC statistics";
     input {
       leaf gateway {
         description "Show cac statistics for a gateway";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf style {
         type enumeration {
           enum "detail" {
             description "Show detailed SPIC level statistics";
           }
         }
       }
     }
     output {
       choice output_c {
         case output-tag {
           leaf output {
             type string;
           }
         }
         case actual-tag {
           anyxml cac-statistics;
         }
         case multichassis-tag {
           anyxml multi-routing-engine-results;
         }
       }
     }
   }
   rpc get-mobile-gw-sgw-idle-mode-buffering-statistics {
     description "Idle mode buffering statistics";
     input {
       leaf gateway {
         description "Gateway name";
         type string {
           length "1 .. 63";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-sgw-idle-mode-buffering-statistics;
         }
         case multichassis-tag {
           anyxml multi-routing-engine-results;
         }
       }
     }
   }
   rpc get-mobile-serving-gateway-status {
     description "Show gateway status";
     input {
       leaf gateway {
         description "Show subscriber for a gateway";
         type string {
           length "1 .. 64";
         }
       }
       leaf roaming-status {
         description "Display status per roaming status type";
         type empty;
       }
       leaf qci {
         description "Show status per QCI";
         type empty;
       }
       leaf gtpv2-priority-level {
         description "Show status per gtpv2 priority-level";
         type empty;
       }
       leaf rat-type {
         description "Display status per RAT-Type";
         type empty;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-status;
         }
         case multichassis-tag {
           anyxml multi-routing-engine-results;
         }
       }
     }
   }
   rpc get-mobile-gateways-preemption-list-sgw {
     description "Show gateway preemption list";
     input {
       leaf gateway {
         description "Show preemption list for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-preemption-list-status-sgw;
         }
         case multichassis-tag {
           anyxml multi-routing-engine-results;
         }
       }
     }
   }
   rpc get-mobile-gateway-gtp-peer-apfe-distribution-sgw {
     description "Show bearer anchor PFE distribution per GTP peer";
     input {
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf gateway {
         description "Show bearer APFE distribution per GTP peer for gateway";
         type string {
           length "1 .. 64";
         }
       }
       leaf remote-address {
         description "Remote IP address of peer";
         type string;
         mandatory true;
       }
       leaf local-address {
         description "Local IP address for peer";
         type string;
       }
       leaf routing-instance {
         description "Routing Instance of Peer";
         type union {
           type uint32;
           type string {
             pattern "<.*>|$.*";
           }
         }
       }
     }
     output {
       choice output_c {
         case output-tag {
           leaf output {
             type string;
           }
         }
         case actual-tag {
           anyxml mobile-gateway-gtp-peer-apfe-distribution;
         }
         case multichassis-tag {
           anyxml multi-routing-engine-results;
         }
       }
     }
   }
   rpc get-mobile-gateways-session-state-sgw {
     description "Show subscribers by state";
     input {
       leaf gateway {
         description "Show subscribers by state for a gateway";
         type string {
           length "1 .. 64";
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateway-status;
         }
         case multichassis-tag {
           anyxml multi-routing-engine-results;
         }
       }
     }
   }
   rpc get-mobile-gateways-sgw-statistics {
     description "Show statistics";
     input {
       leaf gateway {
         description "Show statistics for a gateway";
         type string {
           length "1 .. 64";
         }
       }
     }
     output {
       choice output_c {
         case output-tag {
           leaf output {
             type string;
           }
         }
         case actual-tag {
           anyxml mobile-gateways-sgw-statistics;
         }
         case multichassis-tag {
           anyxml multi-routing-engine-results;
         }
       }
     }
   }
   rpc get-mobile-serving-gateway-call-rate-statistics {
     description "Show gateway call-rate statistics";
     input {
       leaf history {
         description "History of statistics collected";
         type empty;
       }
       leaf gateway {
         description "Gateway name";
         type string {
           length "1 .. 64";
         }
       }
     }
     output {
       choice output_c {
         case output-tag {
           leaf output {
             type string;
           }
         }
         case actual-tag {
           anyxml mobile-gateway-call-rate-statistics;
         }
         case multichassis-tag {
           anyxml multi-routing-engine-results;
         }
       }
     }
   }
   rpc get-mobile-gateway-sgw-rmm-client-status {
     description "Show all the resource controller clients state info";
     input {
       leaf gateway {
         description "Show resource controller clients state info for a gateway";
         type string {
           length "1 .. 64";
         }
       }
     }
     output {
       choice output_c {
         case output-tag {
           leaf output {
             type string;
           }
         }
         case actual-tag {
           anyxml rmpsd-show-rmm-client-command;
         }
         case multichassis-tag {
           anyxml multi-routing-engine-results;
         }
       }
     }
   }
   rpc get-mobile-gateway-information {
     description "Display information about all configured gateways";
     input {
       leaf level {
         default "brief";
         type enumeration {
           enum "brief" {
             description "Display brief output (default)";
           }
           enum "detail" {
             description "Display detail output";
           }
         }
       }
     }
     output {
       choice output_c {
         case output-tag {
           leaf output {
             type string;
           }
         }
         case actual-tag {
           anyxml mobile-gateway-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
