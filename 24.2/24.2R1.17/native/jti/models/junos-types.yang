module junos-types {
  yang-version 1.1;
  namespace "http://yang.juniper.net/junos/types";
  prefix jt;

  import junos-base-extensions {
    prefix junos-base;
  }

  organization
    "Juniper Networks, Inc.";

  contact
    "Juniper Networks, Inc.

     1133 Innovation Way
     Sunnyvale, CA 94089

     +1 888 314-5822

     E-mail: yang-support@juniper.net";

  description
    "This module contains a collection of common JUNOS types.

     Copyright (c) 2023 Juniper Networks, Inc.
     All rights reserved.";

  revision 2023-12-21 {
    description
      "Addition of percentage-dec2 typedef.";
    reference "0.4.0";
  }

  revision 2023-10-30 {
    description
      "Addition of data measurement types.";
    reference "0.3.0";
  }

  revision 2023-08-17 {
    description
      "Addition of initial distinct absolute time types. Marking
       timeticks64 as deprecated.";
    reference "0.2.0";
  }

  revision 2023-06-08 {
    description
      "Initial revision";
    reference "0.1.0";
  }

  junos-base:version "0.4.0";

  typedef timeticks64 {
    type uint64;
    status deprecated;
    description
      "The timeticks64 represents the time, modulo 2^64 between two
       epochs.  The leaf using this type must define the epochs that
       tests are relative to as well as the precision units.";
  }

  typedef absolute-time-seconds {
    type uint64;
    units "seconds";
    description
      "The absolute timestamp in seconds, modulo 2^64 expressed relative
       to the Unix Epoch (Jan 1, 1970 00:00:00 UTC).";
  }

  typedef absolute-time-milliseconds {
    type uint64;
    units "milliseconds";
    description
      "The absolute timestamp in milliseconds, modulo 2^64 expressed
       relative to the Unix Epoch (Jan 1, 1970 00:00:00 UTC).";
  }

  typedef absolute-time-microseconds {
    type uint64;
    units "microseconds";
    description
      "The absolute timestamp in microseconds, modulo 2^64 expressed
       relative to the Unix Epoch (Jan 1, 1970 00:00:00 UTC).";
  }

  typedef bytes {
    type uint64;
    units "bytes";
    description
      "Measurement in bytes (B).";
  }

  typedef kilobytes {
    type uint64;
    units "kilobytes";
    description
      "Measurement in kilobytes (KB). This is equivalent to 2^10 B or
       KiB.";
  }

  typedef megabytes {
    type uint64;
    units "megabytes";
    description
      "Measurement in megabytes (MB). This is equivalent to 2^20 B or
       MiB.";
  }

  typedef gigabytes {
    type uint64;
    units "gigabytes";
    description
      "Measurement in gigabytes (GB). This is equivalent to 2^30 B or
       GiB.";
  }

  typedef irix-percentage {
    type decimal64 {
      fraction-digits 2;
    }
    units "percentage";
    description
      "Measurement of CPU usage for a process in percentage, in IRIX
       mode. In IRIX mode depending on the number of CPUs and threads of
       a process that are running, this value can be greater than
       100.00.";
  }

  typedef percentage-dec2 {
    type decimal64 {
      fraction-digits 2;
      range "0..100";
    }
    units "percentage";
    description
      "Decimal percentage value with 2 fraction-digits";
  }
}
