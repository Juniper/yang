module junos-state-routing-tables {
  yang-version 1.1;
  namespace "http://yang.juniper.net/junos/state/routing-tables";
  prefix js-rtt;

  import ietf-yang-types {
    prefix yang;
  }

  import junos-base-extensions {
    prefix junos-base;
  }

  import junos-state {
    prefix js;
  }

  import junos-l2-types {
    prefix jl2t;
  }

  import junos-state-routing-instances {
    prefix js-ri;
  }

  import junos-state-routing-tables-types {
    prefix js-rtt-types;
  }

  organization
    "Juniper Networks, Inc.";

  contact
    "Juniper Networks, Inc.

     1133 Innovation Way
     Sunnyvale, CA 94089

     +1 888 314-5822

     E-mail: yang-support@juniper.net";

  description
    "This module contains a collection of top level nodes for JUNOS
     Routing Table state data.

     Copyright (c) 2024 Juniper Networks, Inc.
     All rights reserved.";

  revision 2024-01-26 {
    description
      "Initial revision.";
    reference "0.1.0";
  }

  junos-base:version "0.1.0";

  grouping programmed-summary-counts {
    description
      "Grouping for programmed route count information.";

    leaf primary {
      type yang:gauge32;
      description
        "Count of progammed routes in this routing-table.";
    }

    leaf secondary {
      type yang:gauge32;
      description
        "Count of programmed routes that are leaked into this routing-table.";
    }
  }

  grouping programmed-vni-counts {
    description
      "Grouping for per-VNI route counts.";
    container vnis {
      description
        "Container for list of VNIs.";
      list vni {
        key "id";

        leaf id {
          type jl2t:vni-id;
          description
            "VNI is uniquely identified by a 24-bit id.";
        }
        leaf count {
          type yang:gauge32;
          description
            "Programmed route count with specific VNI.";
        }
      }
    }
  }

  grouping programmed-protocol-counts {
    description
      "Grouping for programmed protocol information.";
    container protocols {
      description
        "Container for list of programmed protocols.";
      list protocol {
        key "name";
        leaf name {
          type identityref {
            base js-rtt-types:programmed-protocol-name;
          }
          description
            "Programmed protocol name. E.g., static or bgp-static.";

        }
        uses programmed-summary-counts;
        uses programmed-vni-counts;
      }
    }
  }

  grouping programmed-top {
    description
      "Top-level grouping for programmed routes information.";

    container programmed {
      description
        "Container for programmed routes summary information.";
      uses programmed-summary-counts;

      container clients {
        description
          "Container for programmable-rpd clients.";
        list client {
          description
            "List of programmable-rpd clients.";
          key id;
          leaf id {
            type string;
            description
              "Unique string identifier for programmable-rpd client.";
          }
          uses programmed-protocol-counts;
        }
      }
    }
  }

  grouping routing-tables-top {
    description
      "Top-level grouping for JUNOS routing-tables state data.";

    container routing-tables {
      description
        "Encapsulating container for all JUNOS routing-tables state.";

      list routing-table {
        key "name family rib-id";

        description
          "List of all JUNOS routing-tables.";

        leaf name {
          type string;
          description
            "Name of the routing table.
            Name can be 'default' when routing table belongs to default routing-instance.
            Name can be the name of the routing-intance eg. vrf1, vrfA etc.
            Name can include routing-instance name appended with ':' followed by topology name.
            eg. vrf1:gribi, vrf2:abc, default:gribi etc.
            Name can be 'bgp' when referring to bgp specific tables. eg. bgp.l3vpn.0";
        }
        leaf family {
          type js-rtt-types:address-family;
          description
            "Address family of the routing table.";
        }
        leaf rib-id {
          type uint16;
          description
            "Rib-id of the routing table.";
        }
        container summaries {
          description
            "Encapsulating container for all JUNOS routing-tables summary information.";

          uses programmed-top;
        }
      }
    }
  }

  augment "/js:state/js-ri:routing-instances/js-ri:routing-instance" {
    description
      "Adds routing-tables domain to top-level routing-instance state.";

    uses routing-tables-top;
  }
}
