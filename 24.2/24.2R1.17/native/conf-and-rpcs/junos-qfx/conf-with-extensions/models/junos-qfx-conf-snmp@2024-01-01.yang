/*
 * Copyright (c) 2024 Juniper Networks, Inc.
 * All rights reserved.
 */
 module junos-qfx-conf-snmp {
   namespace "http://yang.juniper.net/junos-qfx/conf/snmp";

   prefix jc-snmp;

   import junos-common-ddl-extensions {
     prefix junos;
     revision-date 2024-01-01;
   }

   import junos-common-types {
     prefix jt;
     revision-date 2024-01-01;
   }

   import junos-qfx-conf-root {
     prefix jc;
     revision-date 2024-01-01;
   }

   organization "Juniper Networks, Inc.";

   contact "yang-support@juniper.net";

   description "Junos snmp configuration module";

   revision 2024-01-01 {
     description "Junos: 24.2R1.17";
   }

   augment /jc:configuration {
     uses snmp-group;
   }
   augment /jc:configuration/jc:groups {
     uses snmp-group;
   }
   grouping snmp-group {
     container snmp {
       description "Simple Network Management Protocol configuration";
       uses apply-advanced;
       leaf system-name {
         description "System name override";
         type string;
       }
       leaf description {
         description "System description";
         type string;
       }
       leaf location {
         description "Physical location of system";
         type string;
       }
       leaf contact {
         description "Contact information for administrator";
         type string;
       }
       leaf-list interface {
         ordered-by user;
         description "Restrict SNMP requests to interfaces";
         type union {
           type jt:interface-name;
           type string {
             pattern "<.*>|$.*";
           }
         }
       }
       leaf packet-size {
         description "Maximum SNMP send message size";
         default "65535";
         type union {
           type string {
             pattern "<.*>|$.*";
           }
           type uint32 {
             range "484 .. 65535";
           }
         }
       }
       container alarm-management {
         description "Alarm management";
         uses apply-advanced;
         list alarm-list-name {
           key name;
           ordered-by user;
           description "Alarm list name";
           leaf name {
             description "Alarm list name";
             junos:cli-feature "nokeyword";
             type string {
               length "1 .. 32";
             }
           }
           uses apply-advanced;
           list alarm-id {
             key name;
             ordered-by user;
             description "Alarm id";
             leaf name {
               description "Alarm id";
               junos:cli-feature "nokeyword";
               type union {
                 type string {
                   pattern "<.*>|$.*";
                 }
                 type uint32 {
                   range "1 .. 4294967295";
                 }
               }
             }
             uses apply-advanced;
             list alarm-state {
               key name;
               ordered-by user;
               description "Alarm model state, configure state value as 1 for clear alarm";
               leaf name {
                 description "Alarm state";
                 junos:cli-feature "nokeyword";
                 type union {
                   type string {
                     pattern "<.*>|$.*";
                   }
                   type uint32 {
                     range "1 .. 4294967295";
                   }
                 }
               }
               uses apply-advanced;
               leaf notification-id {
                 description "Notification id of alarm";
                 type string {
                   length "1 .. 254";
                 }
               }
               leaf varbind-index {
                 description "Varbind index in alarm varbind list";
                 default "0";
                 junos:must "(\".. varbind-value\")";
                 junos:must-message "[varbind-value] must be configured for varbind-index";
                 type union {
                   type string {
                     pattern "<.*>|$.*";
                   }
                   type uint32 {
                     range "0 .. 4294967295";
                   }
                 }
               }
               leaf varbind-value {
                 description "Alarm varbind value";
                 default "0";
                 junos:must "(\".. varbind-index\")";
                 junos:must-message "[varbind-index] must be configured for varbind-value";
                 type union {
                   type string {
                     pattern "<.*>|$.*";
                   }
                   type int32 {
                     range "0 .. 2147483647";
                   }
                 }
               }
               leaf description {
                 description "Alarm description";
                 type string {
                   length "1 .. 2048";
                 }
               }
               leaf varbind-subtree {
                 description "Alarm varbind subtree";
                 junos:must "((\".. resource-prefix\" && \".. varbind-index\"))";
                 junos:must-message "resource-prefix and varbind-index must be configured for varbind-subtree";
                 type string {
                   length "1 .. 254";
                 }
               }
               leaf resource-prefix {
                 description "Alarm resource prefix";
                 type string {
                   length "1 .. 254";
                 }
               }
             }
           }
         }
       }
       container filter-interfaces {
         presence "enable filter-interfaces";
         description "List of interfaces that needs to be filtered";
         uses apply-advanced;
         list interfaces {
           key name;
           ordered-by user;
           junos:cli-feature "homogeneous";
           description "Filter specified interfaces";
           leaf name {
             junos:cli-feature "nokeyword";
             type string;
           }
           uses apply-advanced;
         }
         leaf all-internal-interfaces {
           description "Filter all internal interfaces";
           type empty;
         }
       }
       leaf if-count-with-filter-interfaces {
         description "Filter interfaces config for ifNumber and ipv6Interfaces";
         type empty;
       }
       leaf filter-duplicates {
         description "Filter requests with duplicate source address/port and request ID";
         type empty;
       }
       container nonvolatile {
         description "Configure the handling of nonvolatile SNMP Set requests";
         uses apply-advanced;
         leaf commit-delay {
           description "Delay between affirmative SNMP Set reply and start of commit";
           default "5";
           units "seconds";
           type union {
             type uint32;
             type string {
               pattern "<.*>|$.*";
             }
           }
         }
       }
       container v3 {
         description "SNMPv3 configuration information";
         uses apply-advanced;
         container usm {
           description "User-based security model (USM) information";
           uses apply-advanced;
           container local-engine {
             description "Local engine user configuration";
             uses apply-advanced;
             list user {
               key name;
               ordered-by user;
               description "SNMPv3 USM user information";
               uses v3-user-config;
             }
           }
           list remote-engine {
             key name;
             ordered-by user;
             description "Remote engine user configuration";
             leaf name {
               description "Remote engine id (Hex format)";
               junos:cli-feature "nokeyword";
               type string {
                 junos:posix-pattern "^.{5,64}$";
                 junos:pattern-message "Must be a string of 5 to 64 hex characters";
               }
             }
             uses apply-advanced;
             list user {
               key name;
               ordered-by user;
               description "SNMPv3 USM user information";
               uses v3-user-config;
             }
           }
         }
         container vacm {
           description "View-based access control model (VACM) information";
           uses apply-advanced;
           container security-to-group {
             description "Assigns security names to group";
             uses apply-advanced;
             list security-model {
               key name;
               ordered-by user;
               description "Security model context for group assignment";
               leaf name {
                 description "SNMPv3 security-to-group model name";
                 junos:cli-feature "nokeyword";
                 type enumeration {
                   enum "usm" {
                     description "User-based security model";
                   }
                   enum "v1" {
                     description "SNMPv1 model";
                   }
                   enum "v2c" {
                     description "SNMPv2c model";
                   }
                 }
               }
               uses apply-advanced;
               list security-name {
                 key name;
                 ordered-by user;
                 description "Security name to assign to group";
                 leaf name {
                   description "Security name";
                   junos:cli-feature "nokeyword";
                   type string {
                     length "1 .. 32";
                   }
                 }
                 uses apply-advanced;
                 leaf group {
                   description "Group to which to assign security name";
                   type string {
                     length "1 .. 32";
                   }
                 }
               }
             }
           }
           container access {
             description "Specify SNMP access limits";
             uses apply-advanced;
             list group {
               key name;
               ordered-by user;
               description "Group access configuration";
               leaf name {
                 description "SNMPv3 VACM group name";
                 junos:cli-feature "nokeyword";
                 type string {
                   length "1 .. 32";
                 }
               }
               uses apply-advanced;
               container default-context-prefix {
                 description "Default context-prefix access configuration";
                 uses apply-advanced;
                 list security-model {
                   key name;
                   ordered-by user;
                   description "Security model access configuration";
                   uses security-model-access;
                 }
               }
               list context-prefix {
                 key name;
                 ordered-by user;
                 description "Context-prefix access configuration";
                 leaf name {
                   description "SNMPv3 VACM context prefix";
                   junos:cli-feature "nokeyword";
                   type string {
                     junos:posix-pattern "^.{1,32}$";
                     junos:pattern-message "Must be a string of 32 characters or less";
                   }
                 }
                 uses apply-advanced;
                 list security-model {
                   key name;
                   ordered-by user;
                   description "Security model access configuration";
                   uses security-model-access;
                 }
               }
             }
           }
         }
         list target-address {
           key name;
           ordered-by user;
           description "Identifies notification targets as well as allowed management stations";
           leaf name {
             description "SNMP target address name";
             junos:cli-feature "nokeyword";
             type string {
               length "1 .. 32";
             }
           }
           uses apply-advanced;
           leaf address {
             description "SNMP target address";
             type jt:ipaddr;
           }
           leaf port {
             description "SNMP target port number";
             default "162";
             type union {
               type uint16;
               type string {
                 pattern "<.*>|$.*";
               }
             }
           }
           leaf timeout {
             description "Acknowledgment timeout for confirmed SNMP notifications";
             default "15";
             units "seconds";
             type union {
               type uint32;
               type string {
                 pattern "<.*>|$.*";
               }
             }
           }
           leaf retry-count {
             description "Maximum retry count for confirmed SNMP notifications";
             default "3";
             type union {
               type string {
                 pattern "<.*>|$.*";
               }
               type uint32 {
                 range "0 .. 255";
               }
             }
           }
           leaf tag-list {
             description "SNMP tag list used to select target addresses";
             type string {
               length "0 .. 255";
             }
           }
           leaf address-mask {
             description "Mask range of addresses for community string access control.";
             type jt:ipaddr;
           }
           leaf routing-instance {
             description "Routing instance for trap destination";
             type string {
               junos:posix-pattern "!^(([*]{1,})|(__.*__)|(.{194,}))$";
               junos:pattern-message "Must be a non-reserved string of 193 characters or less";
             }
           }
           leaf logical-system {
             description "Logical-system name for trap destination";
             type string {
               junos:posix-pattern "^[a-zA-Z0-9_-]{1,63}$";
               junos:pattern-message "Logical-system name is a string consisting of up to 63 letters, numbers, dashes and underscores";
             }
           }
           leaf target-parameters {
             description "SNMPv3 target parameter name in the target parameters table";
             type string {
               length "1 .. 32";
             }
           }
         }
         list target-parameters {
           key name;
           ordered-by user;
           description "Parameters and filter name used when sending notifications";
           leaf name {
             description "SNMPv3 target parameters name";
             junos:cli-feature "nokeyword";
             type string {
               length "1 .. 32";
             }
           }
           uses apply-advanced;
           container parameters {
             description "Parameters used when sending notifications";
             uses apply-advanced;
             leaf message-processing-model {
               description "The message processing model to be used when generating SNMP notifications";
               type enumeration {
                 enum "v1" {
                   description "SNMPv1 model";
                 }
                 enum "v2c" {
                   description "SNMPv2c model";
                 }
                 enum "v3" {
                   description "SNMPv3 model";
                 }
               }
             }
             leaf security-model {
               description "Security-model used when generating SNMP notifications";
               type enumeration {
                 enum "usm" {
                   description "User-based security model";
                 }
                 enum "v1" {
                   description "SNMPv1 model";
                 }
                 enum "v2c" {
                   description "SNMPv2c model";
                 }
               }
             }
             leaf security-level {
               description "Security-level used when generating SNMP notifications";
               type enumeration {
                 enum "none" {
                   description "None (noAuthNoPriv)";
                 }
                 enum "authentication" {
                   description "Authentication (authNoPriv)";
                 }
                 enum "privacy" {
                   description "Privacy and authentication (authPriv)";
                 }
               }
             }
             leaf security-name {
               description "Security name used when generating SNMP notifications";
               type string {
                 length "1 .. 32";
               }
             }
           }
           container notify-filter {
             junos:cli-feature "oneliner";
             description "Notify filter to apply to notifications";
             leaf filter {
               description "Filter name to apply to notifications";
               junos:cli-feature "nokeyword";
               type string {
                 length "1 .. 32";
               }
             }
           }
         }
         list notify {
           key name;
           ordered-by user;
           description "Used to select management targets for notifications as well as the type of notifications";
           leaf name {
             description "Notify name";
             junos:cli-feature "nokeyword";
             type string {
               length "1 .. 32";
             }
           }
           uses apply-advanced;
           leaf type {
             description "Notification type";
             default "trap";
             type enumeration {
               enum "trap" {
                 description "SNMP trap";
               }
               enum "inform" {
                 description "Inform request";
               }
             }
           }
           leaf tag {
             description "Notifications will be sent to all targets configured with this tag";
             type string {
               length "0 .. 255";
             }
           }
         }
         list notify-filter {
           key name;
           ordered-by user;
           description "Filters to apply to SNMP notifications";
           leaf name {
             description "SNMP profile name in the notify filter table";
             junos:cli-feature "nokeyword";
             type string {
               length "1 .. 32";
             }
           }
           uses apply-advanced;
           list oid {
             key name;
             ordered-by user;
             junos:cli-feature "oneliner";
             description "OID include/exclude list";
             leaf name {
               description "OID to include/exclude from notify filter";
               junos:cli-feature "nokeyword";
               type string {
                 junos:posix-pattern "^(.?1|[a-zA-Z][a-zA-Z0-9]*)(.[0-9]+|[.][*]|[.][a-zA-Z])*$";
                 junos:pattern-message "Must be an OID of the form 1.x.*.z... or objname[.x.*.z]";
               }
             }
             choice filter-action {
               case case_1 {
                 leaf include {
                   description "Include this OID in the notify filter";
                   type empty;
                 }
               }
               case case_2 {
                 leaf exclude {
                   description "Exclude this OID from the notify filter";
                   type empty;
                 }
               }
             }
           }
         }
         leaf management-routing-instance {
           description "Enable SNMPv3 access for all routing instances from this default context";
           junos:must "(\"routing-instances $$\")";
           junos:must-message "Referenced routing instance must be defined under [edit routing-instances] hierarchy level";
           type string {
             junos:posix-pattern "!^((__.*__)|(all)|(.*[ ].*)|(\"\")|(.{129,}))$";
             junos:pattern-message "Must be a non-reserved string of 128 characters or less with no spaces.";
           }
         }
         list snmp-community {
           key name;
           ordered-by user;
           description "SNMP community and view-based access control model configuration";
           leaf name {
             description "Unique index value in this community table entry";
             junos:cli-feature "nokeyword";
             type string {
               length "1 .. 32";
             }
           }
           uses apply-advanced;
           leaf community-name {
             description "SNMPv1/v2c community name (default is same as community-index)";
             type jt:unreadable;
           }
           leaf security-name {
             description "Security name used when performing access control";
             type string {
               length "1 .. 32";
             }
           }
           leaf context {
             description "Context used when performing access control";
             type string {
               length "0 .. 32";
             }
           }
           leaf tag {
             description "Tag identifier for set of targets allowed to use this community string";
             type string {
               length "0 .. 255";
             }
           }
         }
       }
       list proxy {
         key name;
         ordered-by user;
         description "SNMP proxy configuration";
         leaf name {
           description "Unique proxy name";
           junos:cli-feature "nokeyword";
           type string;
         }
         uses apply-advanced;
         leaf device-name {
           description "Satellite/Proxied Device name or IP address";
           type string;
         }
         choice version {
           case case_1 {
             container version-v1 {
               description "For v1 proxy configuration define snmp-community";
               uses comm-object;
             }
           }
           case case_2 {
             container version-v2c {
               description "For v2c proxy configuration define snmp-community";
               uses comm-object;
             }
           }
           case case_3 {
             container version-v3 {
               description "For v3 proxy configuration define security-name";
               uses sec-object;
             }
           }
         }
         list routing-instance {
           key name;
           ordered-by user;
           description "Associate routing-instance name for proxy forwarding";
           leaf name {
             description "Routing-instance name for proxy forwarding";
             junos:cli-feature "nokeyword";
             type string;
           }
           uses apply-advanced;
         }
         list logical-system {
           key name;
           ordered-by user;
           description "Associate logical-system name for proxy forwarding";
           leaf name {
             description "Associate logical-system name for proxy forwarding";
             junos:cli-feature "nokeyword";
             junos:must "(\".. .. logical-system $$ routing-instance\")";
             junos:must-message "[routing-instance] must be configured for this logical-system";
             type string {
               junos:posix-pattern "^[a-zA-Z0-9_-]{1,63}$";
               junos:pattern-message "Logical-system name is a string consisting of up to 63 letters, numbers, dashes and underscores";
             }
           }
           uses apply-advanced;
           list routing-instance {
             key name;
             ordered-by user;
             description "Associate routing-instance name for proxy forwarding";
             leaf name {
               description "Routing-instance name for proxy forwarding";
               junos:cli-feature "nokeyword";
               type string;
             }
             uses apply-advanced;
           }
         }
         leaf nfx-host {
           description "Set routing-instance for NFX Host";
           type empty;
         }
       }
       container subagent {
         description "SNMP subagent configuration";
         uses apply-advanced;
         container tcp {
           presence "enable tcp";
           description "Allow SNMP subagent tcp connection";
           uses apply-advanced;
           container routing-instance {
             description "Specify routing-instance name for tcp connection";
             uses apply-advanced;
             leaf default {
               description "Allow connections over default routing-instance";
               type empty;
             }
           }
         }
       }
       container engine-id {
         description "SNMPv3 engine ID";
         uses apply-advanced;
         choice engine-id-choice {
           case case_1 {
             leaf use-mac-address {
               description "Uses management interface MAC Address for the engine ID";
               type empty;
             }
           }
           case case_2 {
             leaf use-default-ip-address {
               description "Use default IP address for the engine ID";
               type empty;
             }
           }
           case case_3 {
             leaf local {
               description "Local engine ID";
               type string {
                 junos:posix-pattern "^.{1,27}$";
                 junos:pattern-message "Must be a string of 27 characters or less";
               }
             }
           }
         }
       }
       container access {
         description "SNMPv3 access information";
         status deprecated;
         uses apply-advanced;
         list user {
           key name;
           ordered-by user;
           description "SNMPv3 USM user information";
           leaf name {
             description "SNMPv3 USM username";
             junos:cli-feature "nokeyword";
             type string {
               junos:posix-pattern "^.{1,32}$";
               junos:pattern-message "Must be a string of 32 characters or less";
             }
           }
           uses apply-advanced;
           leaf authentication-type {
             description "SNMPv3 USM authentication type";
             type enumeration {
               enum "none" {
                 description "No authentication";
               }
               enum "md5" {
                 description "MD5 hash algorithm";
               }
               enum "sha" {
                 description "SHA hash algorithm";
               }
             }
           }
           leaf authentication-password {
             description "SNMPv3 USM authentication password";
             type jt:unreadable;
           }
           leaf privacy-type {
             description "SNMPv3 USM privacy type";
             type enumeration {
               enum "none" {
                 description "No privacy";
               }
               enum "des" {
                 description "DES algorithm";
               }
             }
           }
           leaf privacy-password {
             description "SNMPv3 USM privacy password";
             type jt:unreadable;
           }
           list clients {
             key name;
             ordered-by user;
             junos:cli-feature "homogeneous";
             junos:cli-feature "oneliner";
             description "List of source address prefix ranges to accept";
             leaf name {
               description "Address or prefix";
               junos:cli-feature "nokeyword";
               type jt:ipprefix;
             }
             leaf restrict {
               description "Deny access";
               type empty;
             }
           }
         }
         list group {
           key name;
           ordered-by user;
           description "SNMPv3 USM group information";
           leaf name {
             description "SNMPv3 USM group name";
             junos:cli-feature "nokeyword";
             type string {
               junos:posix-pattern "^.{1,32}$";
               junos:pattern-message "Must be a string of 32 characters or less";
             }
           }
           uses apply-advanced;
           leaf-list user {
             ordered-by user;
             description "SNMPv3 USM username";
             type string;
           }
           leaf model {
             description "SNMPv3 security model";
             type enumeration {
               enum "usm" {
                 description "User-based security model";
               }
             }
           }
         }
         list context {
           key name;
           ordered-by user;
           description "SNMPv3 context information";
           leaf name {
             description "SNMPv3 context name";
             junos:cli-feature "nokeyword";
             type string {
               junos:posix-pattern "^.{0,32}$";
               junos:pattern-message "Must be a string of 32 characters or less";
             }
           }
           uses apply-advanced;
           leaf description {
             description "SNMPv3 context description";
             type string;
           }
           list group {
             key name;
             ordered-by user;
             description "Access group";
             leaf name {
               description "SNMPv3 USM group name";
               junos:cli-feature "nokeyword";
               type string {
                 junos:posix-pattern "^.{1,32}$";
                 junos:pattern-message "Must be a string of 32 characters or less";
               }
             }
             uses apply-advanced;
             leaf model {
               description "SNMPv3 security model";
               type enumeration {
                 enum "usm" {
                   description "User-based security model";
                 }
               }
             }
             leaf security-level {
               description "SNMPv3 security level";
               type enumeration {
                 enum "none" {
                   description "None: NoAuthNoPriv";
                 }
                 enum "authentication" {
                   description "Authentication: AuthNoPriv";
                 }
                 enum "privacy" {
                   description "Privacy: AuthPriv";
                 }
               }
             }
             leaf read-view {
               description "Read view name";
               type string {
                 junos:posix-pattern "^.{1,32}$";
                 junos:pattern-message "Must be a string of 32 characters or less";
               }
             }
             leaf write-view {
               description "Write view name";
               type string {
                 junos:posix-pattern "^.{1,32}$";
                 junos:pattern-message "Must be a string of 32 characters or less";
               }
             }
           }
         }
       }
       list view {
         key name;
         ordered-by user;
         description "Define MIB views";
         leaf name {
           description "MIB view name";
           junos:cli-feature "nokeyword";
           type string {
             junos:posix-pattern "^.{1,32}$";
             junos:pattern-message "Must be a string of 32 characters or less";
           }
         }
         uses apply-advanced;
         list oid {
           key name;
           ordered-by user;
           junos:cli-feature "oneliner";
           description "OID include/exclude list";
           leaf name {
             description "OID to include or exclude from view";
             junos:cli-feature "nokeyword";
             type string {
               junos:posix-pattern "^(.?1|[a-zA-Z][a-zA-Z0-9]*)(.[0-9]+|[.][*]|[.][a-zA-Z])*$";
               junos:pattern-message "Must be an OID of the form 1.x.*.z... or objname[.x.*.z]";
             }
           }
           choice view-action {
             case case_1 {
               leaf include {
                 description "Include this OID in the view";
                 type empty;
               }
             }
             case case_2 {
               leaf exclude {
                 description "Exclude this OID from the view";
                 type empty;
               }
             }
           }
         }
       }
       list client-list {
         key name;
         ordered-by user;
         description "Client list";
         leaf name {
           description "The name for the client list";
           junos:cli-feature "nokeyword";
           type string {
             junos:posix-pattern "^.{1,128}$";
             junos:pattern-message "Must be a string of 128 characters or less";
           }
         }
         uses apply-advanced;
         list client-address-list {
           key name;
           ordered-by user;
           description "Client address list";
           uses client-address-object;
         }
       }
       list community {
         key name;
         ordered-by user;
         description "Configure a community string";
         leaf name {
           description "Community name";
           junos:cli-feature "nokeyword";
           type string;
         }
         uses apply-advanced;
         leaf view {
           description "View name";
           type string;
         }
         leaf authorization {
           description "Authorization type";
           type enumeration {
             enum "read-only" {
               description "Allow read-only access";
             }
             enum "read-write" {
               description "Allow read and write access";
             }
           }
         }
         choice clients_choice {
           case case_1 {
             leaf client-list-name {
               description "The name of client list or prefix list";
               type string {
                 junos:posix-pattern "^.{1,128}$";
                 junos:pattern-message "Must be a string of 128 characters or less";
               }
             }
           }
           case case_2 {
             list clients {
               key name;
               ordered-by user;
               junos:cli-feature "homogeneous";
               junos:cli-feature "oneliner";
               description "List of source address prefix ranges to accept";
               leaf name {
                 description "Address or prefix";
                 junos:cli-feature "nokeyword";
                 type jt:ipprefix;
               }
               leaf restrict {
                 description "Deny access";
                 type empty;
               }
             }
           }
         }
         list routing-instances {
           key name;
           ordered-by user;
           description "Use logical-system/routing-instance for v1/v2c clients";
           status deprecated;
           leaf name {
             description "Routing instance of v1/v2c clients";
             junos:cli-feature "nokeyword";
             junos:must "(\"snmp routing-instance-access\")";
             junos:must-message "[snmp routing-instance-access] must be configured";
             type string {
               junos:posix-pattern "!^(([*]{1,})|(__.*__)|(.{194,}))$";
               junos:pattern-message "Must be a non-reserved string of 193 characters or less";
             }
           }
           uses apply-advanced;
           choice clients_choice {
             case case_1 {
               leaf client-list-name {
                 description "The name of client list or prefix list";
                 type string {
                   junos:posix-pattern "^.{1,128}$";
                   junos:pattern-message "Must be a string of 128 characters or less";
                 }
               }
             }
             case case_2 {
               list clients {
                 key name;
                 ordered-by user;
                 junos:cli-feature "homogeneous";
                 junos:cli-feature "oneliner";
                 description "List of source address prefix ranges to accept";
                 leaf name {
                   description "Address or prefix";
                   junos:cli-feature "nokeyword";
                   type jt:ipprefix;
                 }
                 leaf restrict {
                   description "Deny access";
                   type empty;
                 }
               }
             }
           }
         }
         list routing-instance {
           key name;
           ordered-by user;
           description "Use routing-instance name for v1/v2c clients";
           leaf name {
             description "Routing instance of v1/v2c clients";
             junos:cli-feature "nokeyword";
             junos:must "(\"snmp routing-instance-access\")";
             junos:must-message "[snmp routing-instance-access] must be configured";
             type string {
               junos:posix-pattern "!^((__.*__)|(all)|(.*[ ].*)|(\"\")|(.{129,}))$";
               junos:pattern-message "Must be a non-reserved string of 128 characters or less with no spaces.";
             }
           }
           uses apply-advanced;
           choice clients_choice {
             case case_1 {
               leaf client-list-name {
                 description "The name of client list or prefix list";
                 type string {
                   junos:posix-pattern "^.{1,128}$";
                   junos:pattern-message "Must be a string of 128 characters or less";
                 }
               }
             }
             case case_2 {
               list clients {
                 key name;
                 ordered-by user;
                 junos:cli-feature "homogeneous";
                 junos:cli-feature "oneliner";
                 description "List of source address prefix ranges to accept";
                 leaf name {
                   description "Address or prefix";
                   junos:cli-feature "nokeyword";
                   type jt:ipprefix;
                 }
                 leaf restrict {
                   description "Deny access";
                   type empty;
                 }
               }
             }
           }
         }
         list logical-system {
           key name;
           ordered-by user;
           description "Use logical-system name for v1/v2c clients";
           leaf name {
             description "Use logical-system name for v1/v2c clients";
             junos:cli-feature "nokeyword";
             junos:must "(\".. .. logical-system $$ routing-instance\")";
             junos:must-message "[routing-instance] must be configured for this logical-system";
             type string {
               junos:posix-pattern "^[a-zA-Z0-9_-]{1,63}$";
               junos:pattern-message "Logical-system name is a string consisting of up to 63 letters, numbers, dashes and underscores";
             }
           }
           uses apply-advanced;
           list routing-instance {
             key name;
             ordered-by user;
             description "Use routing-instance name for v1/v2c clients";
             leaf name {
               description "Routing instance of v1/v2c clients";
               junos:cli-feature "nokeyword";
               junos:must "(\"snmp routing-instance-access\")";
               junos:must-message "[snmp routing-instance-access] must be configured";
               type string {
                 junos:posix-pattern "!^((__.*__)|(all)|(.*[ ].*)|(\"\")|(.{129,}))$";
                 junos:pattern-message "Must be a non-reserved string of 128 characters or less with no spaces.";
               }
             }
             uses apply-advanced;
             choice clients_choice {
               case case_1 {
                 leaf client-list-name {
                   description "The name of client list or prefix list";
                   type string {
                     junos:posix-pattern "^.{1,128}$";
                     junos:pattern-message "Must be a string of 128 characters or less";
                   }
                 }
               }
               case case_2 {
                 list clients {
                   key name;
                   ordered-by user;
                   junos:cli-feature "homogeneous";
                   junos:cli-feature "oneliner";
                   description "List of source address prefix ranges to accept";
                   leaf name {
                     description "Address or prefix";
                     junos:cli-feature "nokeyword";
                     type jt:ipprefix;
                   }
                   leaf restrict {
                     description "Deny access";
                     type empty;
                   }
                 }
               }
             }
           }
         }
       }
       container trap-options {
         presence "enable trap-options";
         description "SNMP trap options";
         uses apply-advanced;
         container source-address {
           junos:cli-feature "oneliner-plus";
           description "IPv4/IPv6 source address for trap PDUs";
           uses apply-advanced;
           choice address-choice {
             case case_1 {
               leaf lo0 {
                 description "Use lowest address on loopback interface";
                 type empty;
               }
             }
             case case_2 {
               leaf address {
                 description "Use specified address";
                 junos:cli-feature "nokeyword";
                 type jt:ipaddr;
               }
             }
           }
         }
         leaf enterprise-oid {
           description "Add snmpTrapEnterprise oid in varbind of all traps";
           type empty;
         }
         leaf context-oid {
           description "Add context oid in varbind of all traps at the end";
           type empty;
         }
         list routing-instances {
           key name;
           ordered-by user;
           description "Use routing-instance name for source-address";
           status deprecated;
           leaf name {
             description "Routing instance of trap destination";
             junos:cli-feature "nokeyword";
             junos:must "(\".. source-address\")";
             junos:must-message "source-address must be configured";
             type string {
               junos:posix-pattern "!^(([*]{1,})|(__.*__)|(.{194,}))$";
               junos:pattern-message "Must be a non-reserved string of 193 characters or less";
             }
           }
           uses apply-advanced;
           container source-address {
             junos:cli-feature "oneliner-plus";
             description "IPv4/IPv6 source address for trap PDUs";
             uses apply-advanced;
             choice address-choice {
               case case_1 {
                 leaf lo0 {
                   description "Use lowest address on loopback interface";
                   type empty;
                 }
               }
               case case_2 {
                 leaf address {
                   description "Use specified address";
                   junos:cli-feature "nokeyword";
                   type jt:ipaddr;
                 }
               }
             }
           }
         }
         list routing-instance {
           key name;
           ordered-by user;
           description "Use routing-instance name for source-address";
           leaf name {
             description "Routing instance of trap destination";
             junos:cli-feature "nokeyword";
             junos:must "(\".. source-address\")";
             junos:must-message "source-address must be configured";
             type string {
               junos:posix-pattern "!^((__.*__)|(all)|(.*[ ].*)|(\"\")|(.{129,}))$";
               junos:pattern-message "Must be a non-reserved string of 128 characters or less with no spaces.";
             }
           }
           uses apply-advanced;
           container source-address {
             junos:cli-feature "oneliner-plus";
             description "IPv4/IPv6 source address for trap PDUs";
             uses apply-advanced;
             choice address-choice {
               case case_1 {
                 leaf lo0 {
                   description "Use lowest address on loopback interface";
                   type empty;
                 }
               }
               case case_2 {
                 leaf address {
                   description "Use specified address";
                   junos:cli-feature "nokeyword";
                   type jt:ipaddr;
                 }
               }
             }
           }
         }
         list logical-system {
           key name;
           ordered-by user;
           description "Use logical-system name for source-address";
           leaf name {
             description "Use logical-system name for source-address";
             junos:cli-feature "nokeyword";
             junos:must "(\".. .. logical-system $$ routing-instance\")";
             junos:must-message "[routing-instance] must be configured for this logical-system";
             type string {
               junos:posix-pattern "^[a-zA-Z0-9_-]{1,63}$";
               junos:pattern-message "Logical-system name is a string consisting of up to 63 letters, numbers, dashes and underscores";
             }
           }
           uses apply-advanced;
           list routing-instance {
             key name;
             ordered-by user;
             description "Use routing-instance name for source-address";
             leaf name {
               description "Routing instance of trap destination";
               junos:cli-feature "nokeyword";
               junos:must "(\".. source-address\")";
               junos:must-message "source-address must be configured";
               type string {
                 junos:posix-pattern "!^((__.*__)|(all)|(.*[ ].*)|(\"\")|(.{129,}))$";
                 junos:pattern-message "Must be a non-reserved string of 128 characters or less with no spaces.";
               }
             }
             uses apply-advanced;
             container source-address {
               junos:cli-feature "oneliner-plus";
               description "IPv4/IPv6 source address for trap PDUs";
               uses apply-advanced;
               choice address-choice {
                 case case_1 {
                   leaf lo0 {
                     description "Use lowest address on loopback interface";
                     type empty;
                   }
                 }
                 case case_2 {
                   leaf address {
                     description "Use specified address";
                     junos:cli-feature "nokeyword";
                     type jt:ipaddr;
                   }
                 }
               }
             }
           }
         }
         leaf agent-address {
           description "Agent address for v1 trap PDUs";
           type enumeration {
             enum "outgoing-interface" {
               description "Use address on outgoing interface";
             }
           }
         }
       }
       list trap-group {
         key name;
         ordered-by user;
         description "Configure traps and notifications";
         leaf name {
           description "Trap group name";
           junos:cli-feature "nokeyword";
           type string;
         }
         uses apply-advanced;
         leaf version {
           description "SNMP version";
           type enumeration {
             enum "all" {
               description "Send SNMPv1 and SNMPv2 traps";
             }
             enum "v1" {
               description "Send SNMPv1 traps";
             }
             enum "v2" {
               description "Send SNMPv2 traps";
             }
           }
         }
         leaf destination-port {
           description "SNMP trap receiver port number";
           type union {
             type int32;
             type string {
               pattern "<.*>|$.*";
             }
           }
         }
         container categories {
           description "Trap categories";
           uses apply-advanced;
           leaf authentication {
             description "Authentication failures";
             type empty;
           }
           leaf chassis {
             description "Chassis or environment notifications";
             type empty;
           }
           leaf link {
             description "Link up-down transitions";
             type empty;
           }
           leaf remote-operations {
             description "Remote operations";
             type empty;
           }
           leaf routing {
             description "Routing protocol notifications";
             type empty;
           }
           leaf startup {
             description "System warm and cold starts";
             type empty;
           }
           leaf ggsn {
             description "GGSN notifications";
             type empty;
           }
           leaf rmon-alarm {
             description "RMON rising and falling alarms";
             type empty;
           }
           leaf vrrp-events {
             description "VRRP notifications";
             type empty;
           }
           leaf configuration {
             description "Configuration notifications";
             type empty;
           }
           leaf services {
             description "Services notifications";
             type empty;
           }
           leaf timing-events {
             description "Timing defects/events notifications";
             type empty;
           }
           leaf dot3oam-events {
             description "802.3ah notifications";
             type empty;
           }
           container sonet-alarms {
             presence "enable sonet-alarms";
             description "SONET alarm trap subcategories";
             uses apply-advanced;
             leaf loss-of-light {
               description "Loss of light alarm notification";
               type empty;
             }
             leaf pll-lock {
               description "PLL lock alarm notification";
               type empty;
             }
             leaf loss-of-frame {
               description "Loss of frame alarm notification";
               type empty;
             }
             leaf loss-of-signal {
               description "Loss of signal alarm notification";
               type empty;
             }
             leaf severely-errored-frame {
               description "Severely errored frame alarm notification";
               type empty;
             }
             leaf line-ais {
               description "Line AIS alarm notification";
               type empty;
             }
             leaf path-ais {
               description "Path AIS alarm notification";
               type empty;
             }
             leaf loss-of-pointer {
               description "Loss of pointer alarm notification";
               type empty;
             }
             leaf ber-defect {
               description "Sonet bit error rate alarm defect notification";
               type empty;
             }
             leaf ber-fault {
               description "Sonet bit error rate alarm fault notification";
               type empty;
             }
             leaf line-remote-defect-indication {
               description "Line Remote Defect Indication alarm notification";
               type empty;
             }
             leaf path-remote-defect-indication {
               description "Path Remote Defect Indication alarm notification";
               type empty;
             }
             leaf remote-error-indication {
               description "Remote Error Indication alarm notification";
               type empty;
             }
             leaf unequipped {
               description "Unequipped alarm notification";
               type empty;
             }
             leaf path-mismatch {
               description "Path mismatch alarm notification";
               type empty;
             }
             leaf loss-of-cell {
               description "Loss of Cell delineation alarm notification";
               type empty;
             }
             leaf vt-ais {
               description "VT AIS alarm notification";
               type empty;
             }
             leaf vt-loss-of-pointer {
               description "VT Loss Of Pointer alarm notification";
               type empty;
             }
             leaf vt-remote-defect-indication {
               description "VT Remote Defect Indication alarm notification";
               type empty;
             }
             leaf vt-unequipped {
               description "VT Unequipped alarm notification";
               type empty;
             }
             leaf vt-label-mismatch {
               description "VT label mismatch error notification";
               type empty;
             }
             leaf vt-loss-of-cell {
               description "VT Loss of Cell delineation notification";
               type empty;
             }
           }
           container otn-alarms {
             presence "enable otn-alarms";
             description "OTN alarm trap subcategories";
             uses apply-advanced;
             leaf oc-los {
               description "Loss of signal alarm notification";
               type empty;
             }
             leaf oc-lof {
               description "Loss of frame alarm notification";
               type empty;
             }
             leaf oc-lom {
               description "Loss of multiframe alarm notification";
               type empty;
             }
             leaf wavelength-lock {
               description "Wavelength lock alarm notification";
               type empty;
             }
             leaf otu-ais {
               description "OTU Alarm indication signal alarm notification";
               type empty;
             }
             leaf otu-bdi {
               description "OTU Backward defect indication alarm notification";
               type empty;
             }
             leaf otu-ttim {
               description "OTU Trace identification mismatch alarm notification";
               type empty;
             }
             leaf otu-iae {
               description "OTU Incoming alignment error alarm notification";
               type empty;
             }
             leaf otu-sd {
               description "OTU Signal degrade alarm notification";
               type empty;
             }
             leaf otu-sf {
               description "OTU Signal fail alarm notification";
               type empty;
             }
             leaf otu-fec-exe {
               description "OTU Fec excessive errors alarm notification";
               type empty;
             }
             leaf otu-fec-deg {
               description "OTU Fec degraded errors alarm notification";
               type empty;
             }
             leaf otu-bbe-threshold {
               description "OTU Background block error threshold alarm notification";
               type empty;
             }
             leaf otu-es-threshold {
               description "OTU Errored Second threshold alarm notification";
               type empty;
             }
             leaf otu-ses-threshold {
               description "OTU Severely Errored Second threshold alarm notification";
               type empty;
             }
             leaf otu-uas-threshold {
               description "OTU Unavailable Second threshold alarm notification";
               type empty;
             }
             leaf odu-ais {
               description "ODU Alarm indication signal alarm notification";
               type empty;
             }
             leaf odu-oci {
               description "ODU Open connection indicator alarm notification";
               type empty;
             }
             leaf odu-lck {
               description "ODU Locked alarm notification";
               type empty;
             }
             leaf odu-bdi {
               description "ODU Backward defect indication alarm notification";
               type empty;
             }
             leaf odu-ttim {
               description "ODU Trace identification mismatch alarm notification";
               type empty;
             }
             leaf odu-sd {
               description "ODU Signal degrade alarm notification";
               type empty;
             }
             leaf odu-sf {
               description "ODU Signal fail alarm notification";
               type empty;
             }
             leaf odu-rx-aps-change {
               description "ODU Receive APS change notification";
               type empty;
             }
             leaf odu-bbe-threshold {
               description "ODU Background block error threshold alarm notification";
               type empty;
             }
             leaf odu-es-threshold {
               description "ODU Errored Second threshold alarm notification";
               type empty;
             }
             leaf odu-ses-threshold {
               description "ODU Severely Errored Second threshold alarm notification";
               type empty;
             }
             leaf odu-uas-threshold {
               description "ODU Unavailable Second threshold alarm notification";
               type empty;
             }
             leaf opu-ptm {
               description "ODU Payload Type Mismatch alarm notification";
               type empty;
             }
           }
         }
         list targets {
           key name;
           ordered-by user;
           junos:cli-feature "homogeneous";
           junos:cli-feature "oneliner";
           description "Targets for trap messages";
           leaf name {
             description "IP address";
             junos:cli-feature "nokeyword";
             type jt:hostname;
           }
         }
         leaf routing-instance {
           description "Routing instance for trap destination";
           type string {
             junos:posix-pattern "!^(([*]{1,})|(__.*__)|(.{194,}))$";
             junos:pattern-message "Must be a non-reserved string of 193 characters or less";
           }
         }
         leaf logical-system {
           description "Logical-system name for trap destination";
           type string {
             junos:posix-pattern "^[a-zA-Z0-9_-]{1,63}$";
             junos:pattern-message "Logical-system name is a string consisting of up to 63 letters, numbers, dashes and underscores";
           }
         }
       }
       container routing-instance-access {
         presence "enable routing-instance-access";
         description "SNMP routing-instance options";
         uses apply-advanced;
         list access-list {
           key name;
           junos:cli-feature "homogeneous";
           junos:cli-feature "oneliner";
           description "Allow/Deny SNMP access to routing-instances";
           leaf name {
             description "Routing-instance in format <name>, <prefix>* or *";
             junos:cli-feature "nokeyword";
             junos:must "(!(\"snmp routing-instance-access access-list $$={default}\"))";
             junos:must-message "default routing-instance is always allowed";
             type string {
               junos:posix-pattern "!^((__.*__)|(.{194,}))$";
               junos:pattern-message "Must be a non-reserved string of 193 characters or less";
             }
           }
           leaf restrict {
             description "Deny access";
             type empty;
           }
         }
       }
       leaf logical-system-trap-filter {
         description "Allow only logical-system specific traps";
         type empty;
       }
       container traceoptions {
         description "Trace options for SNMP";
         uses apply-advanced;
         container memory-trace {
           presence "enable memory-trace";
           junos:must "(!(\"snmp traceoptions no-default-memory-trace\"))";
           junos:must-message "remove no-default-memory-trace config to activate memory-trace";
           description "Memory tracing information";
           uses apply-advanced;
           leaf size {
             description "Memory size reserved for tracing ";
             default "5120";
             units "kilobytes";
             type union {
               type string {
                 pattern "<.*>|$.*";
               }
               type uint32 {
                 range "1250 .. 12500";
               }
             }
           }
         }
         leaf no-remote-trace {
           description "Disable remote tracing";
           junos:must "(\"system tracing\")";
           junos:must-message "'no-remote-trace' is valid only when [system tracing] is configured";
           type empty;
         }
         container file {
           junos:cli-feature "oneliner";
           description "Trace file information";
           leaf size {
             description "Maximum trace file size";
             type string;
           }
           leaf files {
             description "Maximum number of trace files";
             default "10";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           junos:cli-feature "oneliner";
           description "Tracing parameters";
           leaf name {
             junos:cli-feature "nokeyword";
             type enumeration {
               enum "timer" {
                 description "Trace internal timer events";
               }
               enum "protocol-timeouts" {
                 description "Trace SNMP request timeouts";
               }
               enum "pdu" {
                 description "Dump SNMP request/response packets";
               }
               enum "varbind-error" {
                 description "Trace varbind errors";
               }
               enum "routing-socket" {
                 description "Trace routing socket calls";
               }
               enum "interface-stats" {
                 description "Trace interface statistics (logical and physical)";
               }
               enum "subagent" {
                 description "Trace master-agent interations with sub-agents";
               }
               enum "general" {
                 description "Trace general events";
               }
               enum "nonvolatile-sets" {
                 description "Nonvolatile SNMP set request handling";
               }
               enum "all" {
                 description "Trace everything";
               }
             }
           }
         }
       }
       container rmon {
         presence "enable rmon";
         description "Remote Monitoring configuration";
         uses apply-advanced;
         list history {
           key name;
           ordered-by user;
           description "RMON history entries";
           leaf name {
             description "RMON history identifier";
             junos:cli-feature "nokeyword";
             type union {
               type string {
                 pattern "<.*>|$.*";
               }
               type uint32 {
                 range "1 .. 65535";
               }
             }
           }
           uses apply-advanced;
           leaf interface {
             description "Enable RMON on this interface";
             type union {
               type jt:interface-name;
               type string {
                 pattern "<.*>|$.*";
               }
             }
           }
           leaf bucket-size {
             description "Requested buckets for the interface";
             default "50";
             type union {
               type string {
                 pattern "<.*>|$.*";
               }
               type uint32 {
                 range "1 .. 65535";
               }
             }
           }
           leaf interval {
             description "Interval between samples";
             default "1800";
             units "seconds";
             type union {
               type string {
                 pattern "<.*>|$.*";
               }
               type uint32 {
                 range "1 .. 2147483647";
               }
             }
           }
           leaf owner {
             description "Owner name of the entry";
             type string {
               junos:posix-pattern "^[[:alnum:]._-]{0,32}$";
               junos:pattern-message "Must be an alphanumberic string of 32 characters or less";
             }
           }
         }
         list alarm {
           key name;
           ordered-by user;
           description "RMON alarm entries";
           leaf name {
             description "RMON alarm identifier";
             junos:cli-feature "nokeyword";
             type union {
               type string {
                 pattern "<.*>|$.*";
               }
               type uint32 {
                 range "1 .. 65535";
               }
             }
           }
           uses apply-advanced;
           leaf description {
             description "General description of alarm (stored in alarmOwner)";
             type string {
               junos:posix-pattern "^.{1,120}$";
               junos:pattern-message "Must be a string of 120 characters or less";
             }
           }
           leaf interval {
             description "Interval between samples";
             default "60";
             units "seconds";
             type union {
               type string {
                 pattern "<.*>|$.*";
               }
               type uint32 {
                 range "1 .. 2147483647";
               }
             }
           }
           leaf falling-threshold-interval {
             description "Interval between samples during falling-threshold test";
             default "2147483647";
             units "seconds";
             type union {
               type string {
                 pattern "<.*>|$.*";
               }
               type uint32 {
                 range "1 .. 2147483647";
               }
             }
           }
           leaf variable {
             description "OID of MIB variable to be monitored";
             type string {
               junos:posix-pattern "^([.]?1|[a-zA-Z][a-zA-Z0-9]*)([.]([a-zA-Z]|[0-9]+))*$";
               junos:pattern-message "Must be an OID of the form 1.x.y.z... or objname[.x.y.z] where x, y, & z are either numbers or a single letter";
             }
           }
           leaf sample-type {
             description "Method of sampling the selected variable";
             type enumeration {
               enum "absolute-value" {
                 description "Absolute sample value is used";
               }
               enum "delta-value" {
                 description "Difference between sampled values is used";
               }
             }
           }
           leaf request-type {
             description "Type of SNMP request to issue for alarm";
             default "get-request";
             type enumeration {
               enum "get-request" {
                 description "Get request";
               }
               enum "get-next-request" {
                 description "Get-next request";
               }
               enum "walk-request" {
                 description "Walk request";
               }
             }
           }
           leaf startup-alarm {
             description "The alarm that may be sent upon entry startup";
             default "rising-or-falling-alarm";
             type enumeration {
               enum "rising-alarm" {
                 description "Rising alarm may be sent at startup";
               }
               enum "falling-alarm" {
                 description "Falling alarm may be sent at startup";
               }
               enum "rising-or-falling-alarm" {
                 description "Rising or falling alarm may be sent at startup";
               }
             }
           }
           leaf rising-threshold {
             description "The rising threshold";
             type union {
               type int32;
               type string {
                 pattern "<.*>|$.*";
               }
             }
           }
           leaf falling-threshold {
             description "The falling threshold";
             default "2147483647";
             type union {
               type int32;
               type string {
                 pattern "<.*>|$.*";
               }
             }
           }
           leaf rising-event-index {
             description "Event triggered after rising threshold is crossed";
             default "0";
             type union {
               type string {
                 pattern "<.*>|$.*";
               }
               type int32 {
                 range "0 .. 65535";
               }
             }
           }
           leaf falling-event-index {
             description "Event triggered after falling threshold is crossed";
             default "0";
             type union {
               type string {
                 pattern "<.*>|$.*";
               }
               type int32 {
                 range "0 .. 65535";
               }
             }
           }
           leaf syslog-subtag {
             description "Tag to be added to syslog messages";
             type string {
               junos:posix-pattern "^[A-Z][A-Z0-9_]{0,79}$";
               junos:pattern-message "Must be a string of 80 upper case characters or less";
             }
           }
         }
         list event {
           key name;
           ordered-by user;
           description "RMON event entries";
           leaf name {
             description "RMON event identifier";
             junos:cli-feature "nokeyword";
             type union {
               type string {
                 pattern "<.*>|$.*";
               }
               type uint32 {
                 range "1 .. 65535";
               }
             }
           }
           uses apply-advanced;
           leaf description {
             description "General description of event";
             type string {
               junos:posix-pattern "^.{1,127}$";
               junos:pattern-message "Must be a string of 127 characters or less";
             }
           }
           leaf type {
             description "The type of notification for this event";
             default "log-and-trap";
             type enumeration {
               enum "none" {
                 description "No notifications";
               }
               enum "log" {
                 description "Add entry to logTable";
               }
               enum "snmptrap" {
                 description "Send SNMP trap";
               }
               enum "log-and-trap" {
                 description "Send SNMP trap and make log entry";
               }
             }
           }
           leaf community {
             description "The community (trap group) for outgoing traps";
             type string {
               junos:posix-pattern "^.{1,127}$";
               junos:pattern-message "Must be a string of 127 characters or less";
             }
           }
         }
       }
       container health-monitor {
         presence "enable health-monitor";
         description "Health monitoring configuration";
         uses apply-advanced;
         leaf interval {
           description "Interval between samples";
           units "seconds";
           type union {
             type string {
               pattern "<.*>|$.*";
             }
             type uint32 {
               range "1 .. 2147483647";
             }
           }
         }
         leaf rising-threshold {
           description "Rising threshold applied to all monitored objects";
           units "percent";
           type union {
             type string {
               pattern "<.*>|$.*";
             }
             type uint32 {
               range "1 .. 100";
             }
           }
         }
         leaf falling-threshold {
           description "Falling threshold applied to all monitored objects";
           units "percent";
           type union {
             type string {
               pattern "<.*>|$.*";
             }
             type uint32 {
               range "0 .. 100";
             }
           }
         }
         container idp {
           presence "enable idp";
           description "IDP health monitor configuration";
           uses apply-advanced;
           leaf interval {
             description "Interval between samples";
             units "seconds";
             type union {
               type string {
                 pattern "<.*>|$.*";
               }
               type uint32 {
                 range "1 .. 2147483647";
               }
             }
           }
           leaf rising-threshold {
             description "Rising threshold applied to all monitored objects";
             units "percent";
             type union {
               type string {
                 pattern "<.*>|$.*";
               }
               type uint32 {
                 range "0 .. 100";
               }
             }
           }
           leaf falling-threshold {
             description "Falling threshold applied to all monitored objects";
             units "percent";
             type union {
               type string {
                 pattern "<.*>|$.*";
               }
               type uint32 {
                 range "0 .. 100";
               }
             }
           }
         }
       }
       container arp {
         presence "enable arp";
         description "JVision ARP settings";
         uses apply-advanced;
         leaf host-name-resolution {
           description "Enable host name resolution";
           type empty;
         }
       }
       container customization {
         description "Customize SNMP behaviour based on knob";
         uses apply-advanced;
         leaf ether-stats-ifd-only {
           description "To stop exposing IFLs as part of etherStatsTable";
           type empty;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       junos:cli-feature "nokeyword";
       type string;
     }
     list data {
       key name;
       uses macro-data-type;
     }
   }
   grouping client-address-object {
     description "Client address";
     leaf name {
       description "Address or prefix";
       junos:cli-feature "nokeyword";
       type jt:ipprefix;
     }
     uses apply-advanced;
     leaf restrict {
       description "Deny access";
       type empty;
     }
   }
   grouping comm-object {
     description "Specify snmp-community name";
     uses apply-advanced;
     leaf snmp-community {
       description "Specify community name";
       type string {
         length "1 .. 32";
       }
     }
     leaf no-default-comm-to-v3-config {
       description "No default snmp-community and v3 configuration";
       type empty;
     }
   }
   grouping macro-data-type {
     leaf name {
       description "Keyword part of the keyword-value pair";
       junos:cli-feature "nokeyword";
       type string;
     }
     leaf value {
       description "Value part of the keyword-value pair";
       junos:cli-feature "nokeyword";
       type string;
     }
   }
   grouping sec-object {
     description "Specify security-name";
     uses apply-advanced;
     leaf security-name {
       description "Specify v3 security-name";
       type string {
         length "1 .. 32";
       }
     }
     leaf context {
       description "Specify context name associated to this security-name";
       type string;
     }
   }
   grouping security-model-access {
     description "Security access configuration";
     leaf name {
       description "SNMPv3 VACM security model";
       junos:cli-feature "nokeyword";
       type enumeration {
         enum "any" {
           description "Any security model";
         }
         enum "usm" {
           description "User-based security model";
         }
         enum "v1" {
           description "SNMPv1 model";
         }
         enum "v2c" {
           description "SNMPv2c model";
         }
       }
     }
     uses apply-advanced;
     list security-level {
       key name;
       ordered-by user;
       description "Security level access configuration";
       leaf name {
         description "SNMPv3 VACM security level";
         junos:cli-feature "nokeyword";
         type enumeration {
           enum "none" {
             description "None (noAuthNoPriv)";
           }
           enum "authentication" {
             description "Authentication (authNoPriv)";
           }
           enum "privacy" {
             description "Privacy and authentication (authPriv)";
           }
         }
       }
       uses apply-advanced;
       leaf context-match {
         description "Type of match to perform on context-prefix";
         default "exact";
         type enumeration {
           enum "exact" {
             description "Exact match of prefix and context name";
           }
           enum "prefix" {
             description "Only match the context prefix";
           }
         }
       }
       leaf read-view {
         description "View used for read access";
         type string {
           junos:posix-pattern "^.{0,32}$";
           junos:pattern-message "Must be a string of 32 characters or less";
         }
       }
       leaf write-view {
         description "View used for write access";
         type string {
           junos:posix-pattern "^.{0,32}$";
           junos:pattern-message "Must be a string of 32 characters or less";
         }
       }
       leaf notify-view {
         description "View used to notifications";
         type string {
           junos:posix-pattern "^.{0,32}$";
           junos:pattern-message "Must be a string of 32 characters or less";
         }
       }
     }
   }
   grouping v3-user-config {
     description "SNMPv3 user configuration";
     leaf name {
       description "User name";
       junos:cli-feature "nokeyword";
       type string {
         length "1 .. 32";
       }
     }
     uses apply-advanced;
     choice authentication {
       case case_1 {
         container authentication-md5 {
           description "Configure MD5 authentication";
           uses auth-object;
         }
       }
       case case_2 {
         container authentication-sha {
           description "Configure SHA authentication";
           uses auth-object;
         }
       }
       case case_3 {
         container authentication-sha224 {
           description "Configure SHA224 authentication";
           uses auth-object;
         }
       }
       case case_4 {
         container authentication-sha256 {
           description "Configure SHA256 authentication";
           uses auth-object;
         }
       }
       case case_5 {
         container authentication-sha384 {
           description "Configure SHA384 authentication";
           uses auth-object;
         }
       }
       case case_6 {
         container authentication-sha512 {
           description "Configure SHA512 authentication";
           uses auth-object;
         }
       }
       case case_7 {
         leaf authentication-none {
           description "Set no authentication for the user";
           type empty;
         }
       }
     }
     choice privacy {
       case case_1 {
         container privacy-des {
           description "Configure DES privacy";
           status deprecated;
           uses priv-object;
         }
       }
       case case_2 {
         container privacy-3des {
           description "Configure Triple DES privacy";
           uses priv-object;
         }
       }
       case case_3 {
         container privacy-aes128 {
           description "Configure AES128 privacy";
           uses priv-object;
         }
       }
       case case_4 {
         container privacy-aes256 {
           description "Configure AES256 privacy";
           uses priv-object;
         }
       }
       case case_5 {
         leaf privacy-none {
           description "Set no privacy for the user";
           type empty;
         }
       }
     }
   }
   grouping auth-object {
     description "Authentication parameters";
     uses apply-advanced;
     leaf authentication-password {
       description "User's authentication password";
       type string {
         length "8 .. 1024";
       }
     }
     leaf authentication-key {
       description "Encrypted key used for user authentication";
       type jt:unreadable;
     }
   }
   grouping priv-object {
     description "Privacy parameters";
     uses apply-advanced;
     leaf privacy-password {
       description "User's privacy password";
       type string {
         length "8 .. 1024";
       }
     }
     leaf privacy-key {
       description "Encrypted key used for user privacy";
       type jt:unreadable;
     }
   }
 }
