/*
 * Copyright (c) 2024 Juniper Networks, Inc.
 * All rights reserved.
 */
 module junos-conf-chassis {
   namespace "http://yang.juniper.net/junos/conf/chassis";

   prefix jc-chassis;

   import junos-common-types {
     prefix jt;
     revision-date 2024-01-01;
   }

   import junos-conf-root {
     prefix jc;
     revision-date 2024-01-01;
   }

   organization "Juniper Networks, Inc.";

   contact "yang-support@juniper.net";

   description "Junos chassis configuration module";

   revision 2024-01-01 {
     description "Junos: 24.2R1.17";
   }

   augment /jc:configuration {
     uses chassis-group;
   }
   augment /jc:configuration/jc:groups {
     uses chassis-group;
   }
   grouping chassis-group {
     container chassis {
       description "Chassis configuration";
       uses chassis_type;
     }
   }
   grouping chassis_type {
     uses apply-advanced;
     container copy-tos-to-outer {
       description "Copy TOS from inner to outer header";
       uses apply-advanced;
       container service-type {
         description "Service type for which the TOS copy is needed";
         uses apply-advanced;
         leaf gre {
           description "Copy TOS for GRE Tunnel service";
           type empty;
         }
         leaf mt {
           description "Copy TOS for MT Tunnel service";
           type empty;
         }
       }
     }
     container nssu {
       presence "enable nssu";
       description "Nonstop Software Upgrade settings";
       uses apply-advanced;
       list upgrade-group {
         key name;
         ordered-by user;
         description "Nonstop Software Upgrade group";
         leaf name {
           type string {
             length "1 .. 254";
           }
         }
         uses apply-advanced;
         leaf-list fpcs {
           description "FPCs associated with update-group";
           type union {
             type string {
               pattern "<.*>|$.*";
             }
             type uint32;
           }
           max-elements 16;
         }
       }
       leaf rcp-count {
         description "Parallel rcp count";
         type union {
           type string {
             pattern "<.*>|$.*";
           }
           type int32 {
             range "1 .. 8";
           }
         }
       }
       leaf lc-reboot-delay {
         description "Delay between linecard reboot during NSSU";
         type union {
           type string {
             pattern "<.*>|$.*";
           }
           type int32 {
             range "0 .. 600";
           }
         }
       }
     }
     leaf no-power-budget {
       description "Disable Chassis Power Budget";
       type empty;
     }
     container psu {
       description "Power Supply Unit redundancy configuration";
       uses apply-advanced;
       container redundancy {
         description "PSU Redundancy settings";
         uses apply-advanced;
         leaf n-plus-n {
           description "PSU redundancy: N+N configuration";
           type empty;
         }
       }
     }
     leaf fpc-resync {
       description "Send and receive Nchip cells for newly onlined FPC";
       type empty;
     }
     container optics {
       presence "enable optics";
       description "Optics specific config";
       uses apply-advanced;
       leaf display-3po-pn {
         description "To display third party optics part number";
         type empty;
       }
     }
     leaf craft-lockout {
       description "Disable craft interface input";
       type empty;
     }
     container config-button {
       description "Config button behavior settings";
       leaf no-rescue {
         description "Don't reset to rescue configuration";
         type empty;
       }
       leaf no-clear {
         description "Don't reset to factory-default configuration";
         type empty;
       }
     }
     leaf routing-engine-power-off-button-disable {
       description "Disable RE power off button";
       type empty;
     }
     choice source-route-choice {
       leaf source-route {
         description "Enable IP source-route processing";
         status deprecated;
         type empty;
       }
       leaf no-source-route {
         description "Don't enable IP source-route processing";
         status deprecated;
         type empty;
       }
     }
     choice packet-scheduling-choice {
       leaf packet-scheduling {
         description "Enable DX2.0 packet scheduling";
         type empty;
       }
       leaf no-packet-scheduling {
         description "Don't enable DX2.0 packet scheduling";
         type empty;
       }
     }
     leaf route-memory-enhanced {
       description "Enhance memory allocation for routes";
       status deprecated;
       type empty;
     }
     leaf policer-drop-probability-low {
       description "Set policer probabilistic drop probability to Minimum";
       type empty;
     }
     leaf policer-limit {
       description "Limit the policer tick unit to 32 bytes";
       type empty;
     }
     leaf enhanced-policer {
       description "Enhanced Policer Counters";
       type empty;
     }
     leaf effective-shaping-rate {
       description "Report effective shaping rate";
       type empty;
     }
     container memory-enhanced {
       presence "enable memory-enhanced";
       description "Enhance memory allocation";
       uses apply-advanced;
       leaf route {
         description "Enhance memory allocation for routes";
         type empty;
       }
       leaf filter {
         description "Enhance memory allocation for filter";
         type empty;
       }
       leaf vpn-label {
         description "Enhance memory allocation for L3 VPN label";
         type empty;
       }
     }
     leaf vrf-mtu-check {
       description "Enable Internet Processor II-based MTU check";
       type empty;
     }
     container icmp {
       description "ICMP protocol";
       uses apply-advanced;
       leaf rate-limit {
         description "Icmp rate-limit for non ttl-expired pkts in range";
         default "1";
         type union {
           type string {
             pattern "<.*>|$.*";
           }
           type uint32 {
             range "1 .. 1000";
           }
         }
       }
     }
     container routing-performance {
       description "Alter routing performance";
       uses apply-advanced;
     }
     container icmp6 {
       description "ICMP version 6 protocol";
       uses apply-advanced;
       leaf rate-limit {
         description "Icmp rate-limit for non ttl-expired pkts in range";
         default "1";
         type union {
           type string {
             pattern "<.*>|$.*";
           }
           type uint32 {
             range "1 .. 1000";
           }
         }
       }
     }
     leaf maximum-ecmp {
       description "Maximum ECMP limit for nexthops";
       type enumeration {
         enum "16" {
           description "Maximum 16 ECMP routes";
         }
         enum "32" {
           description "Maximum 32 ECMP routes";
         }
         enum "64" {
           description "Maximum 64 ECMP routes";
         }
         enum "96" {
           description "Maximum 96 ECMP routes";
         }
         enum "128" {
           description "Maximum 128 ECMP routes";
         }
         enum "160" {
           description "Maximum 160 ECMP routes";
         }
         enum "192" {
           description "Maximum 192 ECMP routes";
         }
         enum "224" {
           description "Maximum 224 ECMP routes";
         }
         enum "256" {
           description "Maximum 256 ECMP routes";
         }
         enum "288" {
           description "Maximum 288 ECMP routes";
         }
         enum "320" {
           description "Maximum 320 ECMP routes";
         }
         enum "352" {
           description "Maximum 352 ECMP routes";
         }
         enum "384" {
           description "Maximum 384 ECMP routes";
         }
         enum "416" {
           description "Maximum 416 ECMP routes";
         }
         enum "448" {
           description "Maximum 448 ECMP routes";
         }
         enum "480" {
           description "Maximum 480 ECMP routes";
         }
         enum "512" {
           description "Maximum 512 ECMP routes";
         }
       }
     }
     container ecmp-alb {
       presence "enable ecmp-alb";
       description "Enable adaptive load balancing for ECMP nexthops";
       uses apply-advanced;
       leaf tolerance {
         description "Adaptive tolerance in percentage (default 20%)";
         default "20";
         units "percent";
         type union {
           type string {
             pattern "<.*>|$.*";
           }
           type uint32 {
             range "1 .. 100";
           }
         }
       }
     }
     container redundancy {
       description "Redundancy settings";
       uses chassis_redundancy_type;
     }
     container routing-engine {
       description "Routing Engine settings";
       uses chassis_routing_engine_type;
     }
     container aggregated-devices {
       description "Aggregated devices configuration";
       uses chassis_agg_dev_type;
     }
     list disk-partition {
       key name;
       ordered-by user;
       description "Chassis disk monitor configuration";
       leaf name {
         description "Choose disk partition to monitor";
         type enumeration {
           enum "/var" {
             description "Monitor /var partition";
           }
           enum "/config" {
             description "Monitor /config partition";
           }
         }
       }
       uses apply-advanced;
       list level {
         key name;
         ordered-by user;
         description "Threshold level";
         leaf name {
           type enumeration {
             enum "high" {
               description "Set high level of threshold";
             }
             enum "full" {
               description "Set full level of threshold";
             }
           }
         }
         uses apply-advanced;
         container free-space {
           description "Enter threshold value & choose the metric";
           leaf thres-free {
             description "Enter free space threshold value";
             type union {
               type string {
                 pattern "<.*>|$.*";
               }
               type uint32 {
                 range "0 .. 100";
               }
             }
           }
           choice thres-metric {
             case case_1 {
               leaf percent {
                 description "Free space threshold in %";
                 type empty;
               }
             }
             case case_2 {
               leaf mb {
                 description "Free space threshold in MB";
                 type empty;
               }
             }
           }
         }
       }
     }
     container container-devices {
       description "Container devices configuration";
       uses chassisd_agg_container_type;
     }
     container pseudowire-service {
       description "Pseudowire L3 termination device configuration";
       presence "enable pseudowire-service";
       uses chassis-pw-type;
     }
     container provider-instance-devices {
       description "Provider instance devices configuration";
       uses chassisd_provider_instance_type;
     }
     container power-off-ports-on-no-master-re {
       description "Power off line card ports at once in the absence of any master RE";
       uses chassis_power_off_ports_on_no_master_re_type;
     }
     container redundancy-group {
       description "Redundancy group configuration";
       uses chassisd-redundancy-group-type;
     }
     container fabric {
       description "Switch fabric settings";
       uses chassis_fabric_type;
     }
     list fpc {
       key name;
       description "Flexible PIC Concentrator parameters";
       uses chassis_fpc_type;
     }
     leaf node-id {
       description "Chassis identifier";
       status deprecated;
       type union {
         type string {
           pattern "<.*>|$.*";
         }
         type uint64 {
           range "1 .. 18446744073709551615";
         }
       }
     }
     container p4rt {
       presence "enable p4rt";
       description "Chassis p4rt";
       uses apply-advanced;
       leaf node-id {
         description "Chassis identifier";
         type union {
           type string {
             pattern "<.*>|$.*";
           }
           type uint64 {
             range "1 .. 18446744073709551615";
           }
         }
       }
     }
     list cb {
       key name;
       description "Control Board parameters";
       uses chassis_cb_type;
     }
     leaf disable-power-management {
       description "Disable Power Management in this chassis";
       type empty;
     }
     leaf monitor-pem-inputs {
       description "Enable low current usage monitoring";
       type empty;
     }
     container fpc-feb-connectivity {
       description "Connectivity between Flexible PIC Concentrators and Forwarding Engine Boards";
       uses apply-advanced;
       list fpc {
         key name;
         leaf name {
           description "FPC slot number";
           type union {
             type string {
               pattern "<.*>|$.*";
             }
             type uint32;
           }
         }
         uses apply-advanced;
         container feb {
           description "FEB slot number";
           choice feb-slot-choice {
             case case_1 {
               leaf none {
                 description "FPC not connected to any FEB";
                 type empty;
               }
             }
             case case_2 {
               leaf feb-slot {
                 description "FEB slot number";
                 type union {
                   type string {
                     pattern "<.*>|$.*";
                   }
                   type uint32;
                 }
               }
             }
           }
         }
       }
     }
     container pem {
       description "Power supply (PEM) parameters";
       uses chassis_pem_type;
     }
     container sib {
       description "Switch Interface Board parameters";
       uses chassis_sib_type;
     }
     list sfm {
       key name;
       description "Switching and Forwarding Module parameters";
       uses chassis_sfm_type;
     }
     container feb {
       description "Forwarding Engine Board parameters";
       uses chassis_feb_type;
     }
     container afeb {
       description "Forwarding Engine Board parameters";
       uses chassis_feb_type;
     }
     container tfeb {
       description "Taz Forwarding Engine Board parameters";
       uses chassis_feb_type;
     }
     container alarm {
       description "Global alarm settings";
       uses chassis_alarm_type;
     }
     leaf slow-pfe-alarm {
       description "Enable slow (potential) PFE alarm";
       type empty;
     }
     leaf ppp-subscriber-services {
       description "Select PPP subscriber services";
       default "disable";
       type enumeration {
         enum "disable" {
           description "Disable PPP subscriber services";
         }
         enum "enable" {
           description "Enable PPP subscriber services";
         }
       }
     }
     leaf ambient-temperature {
       description "Chassis ambient-temperature value in degree celsius";
       type enumeration {
         enum "55C" {
           description "55 degree celsius";
         }
         enum "40C" {
           description "40 degree celsius";
         }
         enum "25C" {
           description "25 degree celsius";
         }
         enum "32C" {
           description "32 degree celsius";
         }
       }
     }
     leaf network-services {
       description "Chassis network services configuration";
       type enumeration {
         enum "ip" {
           description "IP network services";
         }
         enum "ethernet" {
           description "Ethernet network services";
         }
         enum "enhanced-ip" {
           description "Enhanced IP network services";
         }
         enum "enhanced-ethernet" {
           description "Enhanced ethernet network services";
         }
         enum "enhanced-mode" {
           description "Enhanced network services";
         }
         enum "lan" {
           description "Ethernet LAN services";
         }
       }
     }
     leaf limited-ifl-scaling {
       description "Configured to limit IFL scaling to 64k";
       type empty;
     }
     container usb {
       description "USB control flags";
       uses apply-advanced;
       container storage {
         description "USB storage flags";
         uses apply-advanced;
         leaf disable {
           description "Disable USB storage";
           type empty;
         }
       }
     }
     container serdes {
       presence "enable serdes";
       description "Serdes test mode for link training";
       uses apply-advanced;
       leaf test-mode {
         description "Serdes test mode";
         type string;
       }
     }
     list lcc {
       key name;
       description "Line-card chassis configuration";
       leaf name {
         description "LCC number";
         type union {
           type string {
             pattern "<.*>|$.*";
           }
           type uint32;
         }
       }
       uses apply-advanced;
       list fpc {
         key name;
         description "Flexible PIC Concentrator parameters";
         uses chassis_fpc_type;
       }
       container pem {
         description "Power supply (PEM) parameters";
         uses chassis_pem_type;
       }
       container spmb {
         description "Switch Processor Mezzanine Board parameters";
         uses apply-advanced;
       }
       choice state {
         case case_1 {
           leaf online-expected {
             description "LCC is expected to be online";
             type empty;
           }
         }
         case case_2 {
           leaf offline {
             description "LCC is expected to be offline";
             type empty;
           }
         }
       }
     }
     container lcc-mode {
       description "Line card chassis mode T4000/T1600/EMPTY configuration";
       uses apply-advanced;
       list lcc {
         key name;
         leaf name {
           description "LCC number";
           type union {
             type string {
               pattern "<.*>|$.*";
             }
             type uint32;
           }
         }
         uses apply-advanced;
         leaf mode {
           description "Changing Mode of LCC will result in the restart of LCC";
           default "t1600";
           type enumeration {
             enum "t1600" {
               description "LCC Mode will be set to t1600";
             }
             enum "t4000" {
               description "LCC Mode will be set to t4000";
             }
             enum "empty" {
               description "Setting LCC mode to empty will offline the LCC";
             }
           }
         }
       }
     }
     list member {
       key name;
       description "Member chassis configuration";
       leaf name {
         description "Member number";
         type union {
           type string {
             pattern "<.*>|$.*";
           }
           type uint32 {
             range "0 .. 10";
           }
         }
       }
       uses apply-advanced;
       container fabric {
         description "Switch fabric settings";
         uses chassis_fabric_type;
       }
       list fpc {
         key name;
         description "Flexible PIC Concentrator parameters";
         uses chassis_fpc_type;
       }
     }
     container license {
       presence "enable license";
       description "Set license";
       uses apply-advanced;
       leaf bandwidth {
         description "Configure bandwidth of FPC";
         type union {
           type uint32;
           type string {
             pattern "<.*>|$.*";
           }
         }
       }
       leaf scale {
         description "Add scale license";
         type enumeration {
           enum "base" {
             description "Base license";
           }
           enum "advance" {
             description "Advance license";
           }
           enum "premium" {
             description "Premium license";
           }
         }
       }
     }
     container host-outbound {
       description "Host-out bound options ";
       uses apply-advanced;
       leaf media-interface {
         description "Enable processing of media interface features for Host gernated packets";
         type empty;
       }
     }
     container synchronization {
       description "Clock synchronization options";
       uses apply-advanced;
       leaf switchover-mode {
         description "Should system revert to higher priority valid source";
         default "revertive";
         type enumeration {
           enum "non-revertive" {
             description "System uses current source as long as it is valid";
           }
           enum "revertive" {
             description "Automatically switch to higher priority valid source";
           }
         }
       }
       leaf switching-mode {
         description "Should system revert to higher priority valid source";
         default "non-revertive";
         type enumeration {
           enum "non-revertive" {
             description "System uses current source as long as it is valid";
           }
           enum "revertive" {
             description "Automatically switch to higher priority valid source";
           }
         }
       }
       leaf network-option {
         description "EEC synchronization networking type";
         type enumeration {
           enum "option-1" {
             description "Option 1 (EEC1) synchronization networking";
           }
           enum "option-2" {
             description "Option 2 (EEC2) synchronization networking";
           }
         }
       }
       leaf selection-mode {
         description "Selection mode for incoming ESMC quality";
         default "configured-quality";
         type enumeration {
           enum "configured-quality" {
             description "Use source's configured ESMC quality";
           }
           enum "received-quality" {
             description "Use source's received ESMC quality";
           }
         }
       }
       leaf clock-mode {
         description "Synchronous Ethernet Clock selection mode";
         type enumeration {
           enum "free-run" {
             description "Use the free-running local oscillator";
           }
           enum "auto-select" {
             description "Select best clock source";
           }
         }
       }
       leaf quality-mode-enable {
         description "Enable Synchronous Ethernet ESMC Quality mode";
         type empty;
       }
       leaf max-transmit-quality-level {
         description "Maximum transmit quality level";
         type enumeration {
           enum "ePRTC" {
             description "Time quality of enhanced primary reference time clock";
           }
           enum "PRTC" {
             description "Time quality of primary reference time clock";
           }
           enum "ePRC" {
             description "Time quality of enhanced primary reference clock";
           }
           enum "eEEC" {
             description "Time quality of enhanced ethernet equipment clock";
           }
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "stu" {
             description "Clock traceable to unknown quality (option-2 only)";
           }
           enum "st2" {
             description "Clock traceable to stratum 2 (option-2 only)";
           }
           enum "tnc" {
             description "Clock traceable to transit node clock (option-2 only)";
           }
           enum "st3e" {
             description "Clock traceable to stratum 3E (option-2 only)";
           }
         }
       }
       leaf enable-extended-ql-tlv {
         description "Enable enhanced ESMC QL support";
         type empty;
       }
       leaf global-wait-to-restore {
         description "Global Port signal up state time before opening for ESMC";
         units "min";
         type union {
           type string {
             pattern "<.*>|$.*";
           }
           type uint32 {
             range "0 .. 12";
           }
         }
       }
       leaf minimum-quality {
         description "Minimum quality threshold";
         type enumeration {
           enum "prc" {
             description "Timing quality of a primary reference clock (option-1 only)";
           }
           enum "ssu-a" {
             description "Timing quality of a type I or IV slave clock (option-1 only)";
           }
           enum "ssu-b" {
             description "Timing quality of a type VI slave clock (option-1 only)";
           }
           enum "sec" {
             description "Timing quality of SDH equipment clock (option-1 only)";
           }
           enum "prs" {
             description "Clock traceable to primary reference source (option-2 only)";
           }
           enum "st2" {
             description "Clock traceable to stratum 2 (option-2 only)";
           }
           enum "tnc" {
             description "Clock traceable to transit node clock (option-2 only)";
           }
           enum "st3e" {
             description "Clock traceable to stratum 3E (option-2 only)";
           }
           enum "st3" {
             description "Clock traceable to stratum 3 (option-2 only)";
           }
           enum "st4" {
             description "Clock traceable to stratum 4 free-run (option-2 only)";
           }
           enum "smc" {
             description "Clock traceable to self-timed SONET (option-2 only)";
           }
           enum "stu" {
             description "Clock traceable to unknown quality (option-2 only)";
           }
         }
       }
       list port {
         key name;
         description "Clock synchronization ports";
         leaf name {
           type enumeration {
             enum "auxiliary" {
               description "Auxiliary port";
             }
             enum "gnss" {
               description "Global Navigation Satellite System - GPS or GLONASS port";
             }
             enum "time-of-day" {
               description "Time of Day(TOD) port";
             }
           }
         }
         uses apply-advanced;
         container client {
           presence "enable client";
           description "Port client receiving external signals";
           uses apply-advanced;
           container time-of-day-format {
             description "Time-of-day format as received on this port";
             uses apply-advanced;
             choice format {
               case case_1 {
                 leaf ascii {
                   description "ASCII Time-of-day message format string";
                   type string {
                     length "1 .. 80";
                   }
                 }
               }
               case case_2 {
               }
               case case_3 {
               }
             }
           }
           leaf cable-length-compensation {
             description "Antenna cable length compensation in nanoseconds";
             type union {
               type uint32;
               type string {
                 pattern "<.*>|$.*";
               }
             }
           }
           leaf antenna-voltage {
             description "Configure antenna voltage";
             type enumeration {
               enum "3.3" {
                 description "3.3 units";
               }
               enum "5" {
                 description "5 units";
               }
             }
           }
           leaf constellation {
             description "Configure constellation of satellites to use";
             type enumeration {
               enum "gps" {
                 description "Global Positioning Satellite(GPS) for clock recovery";
               }
               enum "glonass" {
                 description "Global Navigation Satellite System(GLONASS) constellation";
               }
               enum "gps-and-glonass" {
                 description "All constellations";
               }
               enum "beidou" {
                 description "BEIDOU for clock recovery constellations";
               }
               enum "gps-beidou" {
                 description "GPS and BEIDOU for clock recovery";
               }
               enum "gps-beidou-qzss" {
                 description "GPS ,BEIDOU and qzss for clock recovery";
               }
               enum "galileo" {
                 description "GALILEO for clock recovery";
               }
               enum "gps-galileo" {
                 description "GPS and GALILEO for clock recovery";
               }
               enum "gps-qzss" {
                 description "GPS and QZSS for clock recovery";
               }
               enum "gps-glonass-qzss" {
                 description "GPS,GLONASS and QZSS for clock recovery";
               }
               enum "gps-galileo-qzss" {
                 description "GPS , GALILEO and QZSS for clock recovery";
               }
             }
           }
           leaf anti-jamming {
             description "Enable anti-jamming feature";
             type empty;
           }
         }
         container server {
           presence "enable server";
           description "The role of port is server which transmits signals out";
           uses apply-advanced;
           container time-of-day-format {
             description "RS-232 port time-of-day format";
             uses apply-advanced;
             choice format {
               case case_1 {
                 leaf ascii {
                   description "ASCII Time-of-day message format string";
                   type string {
                     length "1 .. 80";
                   }
                 }
               }
             }
           }
         }
       }
       list interfaces {
         key name;
         description "Interface(s) with upstream clock source";
         leaf name {
           type enumeration {
             enum "external" {
               description "External clock interface";
             }
             enum "external-0/0" {
               description "External clock interface on SCB-0";
             }
             enum "external-0/1" {
               description "External clock interface on SCB-0";
             }
             enum "external-1/0" {
               description "External clock interface on SCB-1";
             }
             enum "external-1/1" {
               description "External clock interface on SCB-1";
             }
             enum "external-a" {
               description "External-A clock interface";
             }
             enum "external-b" {
               description "External-B clock interface";
             }
             enum "external-0" {
               description "External-0 clock interface";
             }
             enum "external-1" {
               description "External-1 clock interface";
             }
             enum "external-2" {
               description "External-2 clock interface";
             }
             enum "bits" {
               description "External BITS interface configuration";
             }
             enum "bits-a" {
               description "External BITS interface A configuration";
             }
             enum "bits-b" {
               description "External BITS interface B configuration";
             }
             enum "gps-0" {
               description "External GPS interface A configuration";
             }
             enum "gps-1" {
               description "External GPS interface B configuration";
             }
           }
         }
         uses apply-advanced;
         leaf signal-type {
           description "Frequency for provided reference clocks";
           type enumeration {
             enum "1mhz" {
               description "1 MHz clock signal";
             }
             enum "5mhz" {
               description "5 MHz clock signal";
             }
             enum "10mhz" {
               description "10 MHz clock signal";
             }
             enum "2048khz" {
               description "E1 unframed 2048Khz G.703 signal";
             }
             enum "e1" {
               description "E1-coded 2048 KHz signal on 120 ohm balanced line";
             }
             enum "t1" {
               description "T1-coded 1.544 MHz signal on 100 ohm balanced line";
             }
             enum "cc-8k" {
               description "Composite Clock 64kHz+8kHz";
             }
             enum "cc-8k-400" {
               description "Composite Clock 64kHz+8kHz+400Hz";
             }
             enum "6312k" {
               description "Japanese Standard 6312kHz";
             }
           }
         }
         leaf pulse-per-second-enable {
           description "Enable pulse-per-second (PPS) receive on the interface";
           type empty;
         }
         container e1-options {
           description "E1 interface-specific options";
           uses apply-advanced;
           leaf line-encoding {
             description "Line encoding";
             default "hdb3";
             type enumeration {
               enum "ami" {
                 description "Automatic mark inversion";
               }
               enum "hdb3" {
                 description "High-density bipolar 3 code";
               }
             }
           }
           leaf framing {
             description "Framing mode";
             default "g704";
             type enumeration {
               enum "g704" {
                 description "G.704 framing format for E1 interfaces";
               }
               enum "g704-no-crc4" {
                 description "G.704 framing without CRC4 for E1 interfaces";
               }
             }
           }
           leaf sabit {
             description "The sabit used for exchanging SSM quality";
             default "4";
             type union {
               type string {
                 pattern "<.*>|$.*";
               }
               type uint32 {
                 range "4 .. 8";
               }
             }
           }
         }
         container t1-options {
           description "T1 interface-specific options";
           uses apply-advanced;
           leaf line-encoding {
             description "Line encoding";
             default "b8zs";
             type enumeration {
               enum "ami" {
                 description "Automatic mark inversion";
               }
               enum "b8zs" {
                 description "8-bit zero suppression";
               }
             }
           }
           leaf framing {
             description "Framing mode";
             default "esf";
             type enumeration {
               enum "esf" {
                 description "Extended Super Frame";
               }
               enum "sf" {
                 description "Super Frame";
               }
             }
           }
         }
       }
       container output {
         description "External clock interface related";
         uses apply-advanced;
         list interfaces {
           key name;
           description "Interface(s) to output source to";
           leaf name {
             type enumeration {
               enum "external" {
                 description "External clock interface";
               }
               enum "external-0/0" {
                 description "External clock interface on SCB-0";
               }
               enum "external-0/1" {
                 description "External clock interface on SCB-0";
               }
               enum "external-1/0" {
                 description "External clock interface on SCB-1";
               }
               enum "external-1/1" {
                 description "External clock interface on SCB-1";
               }
               enum "external-a" {
                 description "External-A clock interface";
               }
               enum "external-b" {
                 description "External-B clock interface";
               }
               enum "bits" {
                 description "External BITS interface configuration";
               }
               enum "external-0" {
                 description "External-0 clock interface";
               }
               enum "external-1" {
                 description "External-1 clock interface";
               }
               enum "external-2" {
                 description "External-2 clock interface";
               }
             }
           }
           uses apply-advanced;
           container ssm {
             description "SSM Message config";
             uses apply-advanced;
             leaf option-2 {
               description "Select generation";
               type enumeration {
                 enum "GEN-1" {
                   description "SSM Message type GEN-1";
                 }
                 enum "GEN-2" {
                   description "SSM Message type GEN-2";
                 }
               }
             }
           }
           leaf wander-filter-disable {
             description "Disables wander filtering";
             type empty;
           }
           leaf holdover-mode-disable {
             description "Disables holdover";
             type empty;
           }
           leaf source-mode {
             description "Source mode for selecting source to output";
             default "line";
             type enumeration {
               enum "chassis" {
                 description "The chassis clock is output";
               }
               enum "line" {
                 description "The best line clock source is output";
               }
               enum "equipment-clock" {
                 description "The chassis clock is output";
               }
               enum "ptp-clock" {
                 description "The best line clock source is output";
               }
             }
           }
           leaf tx-dnu-to-line-source-enable {
             description "Sets Tx QL to DNU/DUS on line source interface";
             type empty;
           }
           leaf minimum-quality {
             description "Minimum quality threshold";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
       }
       container source {
         description "ESMC source(s) related";
         uses apply-advanced;
         container external-a {
           presence "enable external-a";
           description "External Clock source A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container external-b {
           presence "enable external-b";
           description "External Clock source B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps {
           presence "enable gps";
           description "Global Positioning System 10MHz input";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf no-ssm-support {
             description "No SSM support available for this interface";
             type empty;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps-0 {
           presence "enable gps-0";
           description "Global Positioning System input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container gps-1 {
           presence "enable gps-1";
           description "Global Positioning System input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits {
           presence "enable bits";
           description "External Building Integrated Timing Supply input";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf no-ssm-support {
             description "No SSM support available for this interface";
             type empty;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-a {
           presence "enable bits-a";
           description "External Building Integrated Timing Supply input A";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         container bits-b {
           presence "enable bits-b";
           description "External Building Integrated Timing Supply input B";
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
         list interfaces {
           key name;
           description "Interface(s) with upstream clock source";
           leaf name {
             type string;
           }
           uses apply-advanced;
           leaf priority {
             description "User priority for this clock";
             type union {
               type string {
                 pattern "<.*>|$.*";
               }
               type uint32 {
                 range "1 .. 5";
               }
             }
           }
           leaf request {
             description "Clock selection request criterion";
             type enumeration {
               enum "lockout" {
                 description "Opt out of clock selection";
               }
               enum "force-switch" {
                 description "Switch to this interface as primary clock source";
               }
             }
           }
           leaf wait-to-restore {
             description "Port signal up state time before opening for ESMC";
             units "min";
             type union {
               type string {
                 pattern "<.*>|$.*";
               }
               type uint32 {
                 range "0 .. 12";
               }
             }
           }
           leaf no-ssm-support {
             description "No SSM support available for this interface";
             type empty;
           }
           leaf hold-off-time {
             description "Port signal down state time before closing for ESMC";
             units "milliseconds";
             type union {
               type string {
                 pattern "<.*>|$.*";
               }
               type uint32 {
                 range "300 .. 1800";
               }
             }
           }
           leaf aggregated-ether {
             description "Aggregated sources group name";
             type string;
           }
           leaf quality-level {
             description "ESMC Clock EEC level";
             type enumeration {
               enum "ePRTC" {
                 description "Time quality of enhanced primary reference time clock";
               }
               enum "PRTC" {
                 description "Time quality of primary reference time clock";
               }
               enum "ePRC" {
                 description "Time quality of enhanced primary reference clock";
               }
               enum "eEEC" {
                 description "Time quality of enhanced ethernet equipment clock";
               }
               enum "prc" {
                 description "Timing quality of a primary reference clock (option-1 only)";
               }
               enum "ssu-a" {
                 description "Timing quality of a type I or IV slave clock (option-1 only)";
               }
               enum "ssu-b" {
                 description "Timing quality of a type VI slave clock (option-1 only)";
               }
               enum "sec" {
                 description "Timing quality of SDH equipment clock (option-1 only)";
               }
               enum "prs" {
                 description "Clock traceable to primary reference source (option-2 only)";
               }
               enum "st2" {
                 description "Clock traceable to stratum 2 (option-2 only)";
               }
               enum "tnc" {
                 description "Clock traceable to transit node clock (option-2 only)";
               }
               enum "st3e" {
                 description "Clock traceable to stratum 3E (option-2 only)";
               }
               enum "st3" {
                 description "Clock traceable to stratum 3 (option-2 only)";
               }
               enum "st4" {
                 description "Clock traceable to stratum 4 free-run (option-2 only)";
               }
               enum "smc" {
                 description "Clock traceable to self-timed SONET (option-2 only)";
               }
               enum "stu" {
                 description "Clock traceable to unknown quality (option-2 only)";
               }
             }
           }
         }
       }
       container esmc-transmit {
         description "ESMC transmit parameters";
         uses apply-advanced;
         list interfaces {
           key name;
           ordered-by user;
           description "Interface(s) on which to permit ESMC transmit messages";
           leaf name {
             type string;
           }
           uses apply-advanced;
         }
       }
       container hold-interval {
         description "Hold interval";
         uses apply-advanced;
         leaf switchover {
           description "Switchover wait time after clock recovery";
           default "30";
           units "sec";
           type union {
             type string {
               pattern "<.*>|$.*";
             }
             type uint32 {
               range "30 .. 60";
             }
           }
         }
         leaf configuration-change {
           description "Clock select wait time after change in config";
           default "15";
           units "sec";
           type union {
             type string {
               pattern "<.*>|$.*";
             }
             type uint32 {
               range "15 .. 60";
             }
           }
         }
         leaf restart {
           description "Clock select wait time after reboot";
           default "120";
           units "sec";
           type union {
             type string {
               pattern "<.*>|$.*";
             }
             type uint32 {
               range "60 .. 180";
             }
           }
         }
       }
       leaf validation-interval {
         description "Time between frequency measurements";
         default "90";
         units "seconds";
         type union {
           type string {
             pattern "<.*>|$.*";
           }
           type uint32 {
             range "90 .. 86400";
           }
         }
       }
       leaf slave-free-run {
         description "Slave Clock running mode";
         type empty;
       }
       leaf y-cable-line-termination {
         description "A single signal is wired to both CBs via Y-cable";
         type empty;
       }
       leaf transmitter-enable {
         description "Control whether diagnostic timing signal is transmitted";
         type empty;
       }
       leaf signal-type {
         description "Frequency for provided reference clocks";
         default "t1";
         type enumeration {
           enum "e1" {
             description "E1-coded 2048 Khz signal on 120 ohm balanced line";
           }
           enum "t1" {
             description "T1-coded 1.544 Mhz signal on 100 ohm balanced line";
           }
           enum "cc-8k" {
             description "Composite Clock 64kHz+8kHz";
           }
           enum "cc-8k-400" {
             description "Composite Clock 64kHz+8kHz+400Hz";
           }
           enum "6312k" {
             description "Japanese Standard 6312kHz";
           }
         }
       }
       leaf primary {
         description "Best choice synchronization reference source list";
         type enumeration {
           enum "external-a" {
             description "Use external-a as a primary source";
           }
           enum "external-b" {
             description "Use external-b as a primary source";
           }
           enum "bits-a" {
             description "Use bits-a as a primary source";
           }
           enum "bits-b" {
             description "Use bits-b as a primary source";
           }
           enum "gps-0" {
             description "Use gps-0 as a primary source";
           }
           enum "gps-1" {
             description "Use gps-1 as a primary source";
           }
           enum "fpc-0" {
             description "Use fpc-0 as a primary source";
           }
           enum "fpc-1" {
             description "Use fpc-1 as a primary source";
           }
           enum "fpc-2" {
             description "Use fpc-2 as a primary source";
           }
           enum "fpc-3" {
             description "Use fpc-3 as a primary source";
           }
           enum "fpc-4" {
             description "Use fpc-4 as a primary source";
           }
           enum "fpc-5" {
             description "Use fpc-5 as a primary source";
           }
           enum "fpc-6" {
             description "Use fpc-6 as a primary source";
           }
           enum "fpc-7" {
             description "Use fpc-7 as a primary source";
           }
           enum "fpc-8" {
             description "Use fpc-8 as a primary source";
           }
           enum "fpc-9" {
             description "Use fpc-9 as a primary source";
           }
           enum "fpc-10" {
             description "Use fpc-10 as a primary source";
           }
           enum "fpc-11" {
             description "Use fpc-11 as a primary source";
           }
           enum "fpc-12" {
             description "Use fpc-12 as a primary source";
           }
           enum "fpc-13" {
             description "Use fpc-13 as a primary source";
           }
           enum "fpc-14" {
             description "Use fpc-14 as a primary source";
           }
           enum "fpc-15" {
             description "Use fpc-15 as a primary source";
           }
         }
       }
       leaf secondary {
         description "Alternative choice synchronization reference source list";
         type enumeration {
           enum "external-a" {
             description "Use external-a as a secondary source";
           }
           enum "external-b" {
             description "Use external-b as a secondary source";
           }
           enum "bits-a" {
             description "Use bits-a as a secondary source";
           }
           enum "bits-b" {
             description "Use bits-b as a secondary source";
           }
           enum "gps-0" {
             description "Use gps-0 as a secondary source";
           }
           enum "gps-1" {
             description "Use gps-1 as a secondary source";
           }
           enum "fpc-0" {
             description "Use fpc-0 as a secondary source";
           }
           enum "fpc-1" {
             description "Use fpc-1 as a secondary source";
           }
           enum "fpc-2" {
             description "Use fpc-2 as a secondary source";
           }
           enum "fpc-3" {
             description "Use fpc-3 as a secondary source";
           }
           enum "fpc-4" {
             description "Use fpc-4 as a secondary source";
           }
           enum "fpc-5" {
             description "Use fpc-5 as a secondary source";
           }
           enum "fpc-6" {
             description "Use fpc-6 as a secondary source";
           }
           enum "fpc-7" {
             description "Use fpc-7 as a secondary source";
           }
           enum "fpc-8" {
             description "Use fpc-8 as a secondary source";
           }
           enum "fpc-9" {
             description "Use fpc-9 as a secondary source";
           }
           enum "fpc-10" {
             description "Use fpc-10 as a secondary source";
           }
           enum "fpc-11" {
             description "Use fpc-11 as a secondary source";
           }
           enum "fpc-12" {
             description "Use fpc-12 as a secondary source";
           }
           enum "fpc-13" {
             description "Use fpc-13 as a secondary source";
           }
           enum "fpc-14" {
             description "Use fpc-14 as a secondary source";
           }
           enum "fpc-15" {
             description "Use fpc-15 as a secondary source";
           }
         }
       }
       list gnss-receiver {
         key name;
         description "Global Navigation Satellite System receiver configs";
         leaf name {
           description "GNSS port/slot number";
           type union {
             type string {
               pattern "<.*>|$.*";
             }
             type uint32;
           }
         }
         uses apply-advanced;
         leaf interface {
           description "Enable/Disable GNSS port/slot communication";
           type empty;
         }
         leaf disable-log {
           description "Enable/Disable logging of gnss-receiver messages";
           type empty;
         }
         leaf snr-threshold {
           description "Satellites with signal levels above this value are used in positioning- in dBHz";
           type union {
             type string {
               pattern "<.*>|$.*";
             }
             type uint32 {
               range "0 .. 99";
             }
           }
         }
         container receiver-type {
           description "GNSS receiver type";
           uses apply-advanced;
           leaf tb-1 {
             description "Receiver type is tb-1";
             type empty;
           }
         }
         container position-mode {
           description "GNSS Receiver's different positioning modes";
           uses apply-advanced;
           container survey-mode {
             description "Set survey mode and length of survey in minutes";
             uses apply-advanced;
             leaf survey-length {
               description "GNSS Receiver's number of position fixes, before switching to position-fix mode- in mins";
               type union {
                 type string {
                   pattern "<.*>|$.*";
                 }
                 type int32 {
                   range "0 .. 10080";
                 }
               }
             }
           }
           container position-fix-mode {
             description "Set gnss receiver to fixed position mode";
             uses apply-advanced;
             leaf latitude {
               description "GNSS Receiver's latitude in decimal degrees, range -90.000000 to 90.000000";
               type decimal64 {
                 fraction-digits 9;
                 range "-90 .. 90";
               }
             }
             leaf longitude {
               description "GNSS Receiver's longitude in decimal degrees, range -180.000000 to 180.000000";
               type decimal64 {
                 fraction-digits 9;
                 range "-180 .. 180";
               }
             }
             leaf altitude {
               description "GNSS Receiver's altitude in meters, range -1000.000000 to 18000.000000";
               type decimal64 {
                 fraction-digits 9;
                 range "-1000 .. 18000";
               }
             }
           }
         }
         leaf cable-delay-compensation {
           description "GNSS Receiver Unit to Router RF cable delay compensation in nanoseconds";
           type union {
             type string {
               pattern "<.*>|$.*";
             }
             type int32 {
               range "-100000 .. 100000";
             }
           }
         }
         container constellation {
           description "GNSS Receiver's different constellation and bands";
           uses apply-advanced;
           container gps {
             description "GPS constellation";
             uses apply-advanced;
             leaf l1ca {
               description "GPS L1 band";
               type empty;
             }
           }
           container glonass {
             description "GLONASS constellation";
             uses apply-advanced;
             leaf l1of {
               description "GLONASS L1 band";
               type empty;
             }
           }
           container galileo {
             description "GALILEO constellation";
             uses apply-advanced;
             leaf e1 {
               description "GALILEO E1 band";
               type empty;
             }
           }
           container qzss {
             description "QZSS constellation";
             uses apply-advanced;
             leaf l1ca {
               description "QZSS L1 band";
               type empty;
             }
           }
         }
       }
     }
     container lcd {
       description "Chassis LCD";
       status deprecated;
       uses apply-advanced;
       list fpc {
         key name;
         ordered-by user;
         leaf name {
           description "FPC slot number";
           type union {
             type string {
               pattern "<.*>|$.*";
             }
             type uint32;
           }
         }
         choice menu-item {
           case case_1 {
             leaf maintenance-menu {
               description "LCD maintenance menu";
               type empty;
             }
           }
         }
         choice enable-disable {
           case case_1 {
             leaf disable {
               description "Disable maintenance-menu";
               type empty;
             }
           }
         }
       }
       choice menu-item {
         case case_1 {
           leaf maintenance-menu {
             description "LCD maintenance menu";
             type empty;
           }
         }
       }
       choice enable-disable {
         case case_1 {
           leaf disable {
             description "Disable maintenance-menu";
             type empty;
           }
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     leaf loopback-firewallv6-optimization {
       description "Increase ACL scale for loopback IPv6 filters; restarts PFE";
       type empty;
     }
     leaf input-firewall-optimized-profile {
       description "Optimal default filter usage when IFA/FCoe/FIPsnooping is not used; restarts PFE";
       type empty;
     }
     leaf ivacl-firewall-no-portrange-profile {
       description "L4 Src/Dst Port range optimize is not needed; restarts PFE";
       type empty;
     }
     leaf iracl-firewall-ipv4-profile {
       description "IPv6 address match is not needed for IRACL filters; restarts PFE";
       type empty;
     }
     leaf ipvacl-firewall-l2-profile {
       description "Only Src/Dst MAC,VLAN,EtherType match is needed for IPACL/IVACL filters; restarts PFE";
       type empty;
     }
     leaf loopback-firewall-optimization {
       description "Optimal TCAM use,restarts PFE(for IP rsrved multicast dest & IP ttl=0/1,config explicitly)";
       type empty;
     }
     leaf epacl-firewall-optimization {
       description "Maximizes Egress Port ACLs TCAM use and restarts PFE";
       type empty;
     }
     leaf per-logical-interface-firewall {
       description "Ingress port firewall can be supported per logical interface, restarts PFE";
       type empty;
     }
     container lcd-menu {
       description "Chassis LCD menu";
       uses apply-advanced;
       list fpc {
         key name;
         ordered-by user;
         leaf name {
           description "FPC slot number";
           type union {
             type string {
               pattern "<.*>|$.*";
             }
             type uint32;
           }
         }
         uses apply-advanced;
         list menu-item {
           key name;
           ordered-by user;
           description "LCD menu item";
           leaf name {
             description "LCD menu name";
             type string;
           }
           leaf disable {
             description "Disable LCD menu";
             type empty;
           }
         }
       }
     }
     leaf fru-poweron-sequence {
       description "FRUs power on sequence like 0 1 2 3 ... within double quotes";
       type string {
       }
     }
     leaf fru-local-storage-disable {
       description "Disable and erase local storage on FPC.(FPC reboot required)";
       type empty;
     }
     leaf fpc-empolicy-profile {
       description "FPC EM Policy Profile";
       type enumeration {
         enum "low-power-mode" {
           description "Set low power mode";
         }
       }
     }
     container psm {
       description "Power supply module";
       uses apply-advanced;
       container redundancy {
         description "PSM Source/Feed Redundancy configuration";
         uses apply-advanced;
         leaf source-redundancy {
           description "Toggle source redundancy for PSM";
           type empty;
         }
         container feed-redundancy {
           description "Toggle feed redundancy for a PSM slot";
           uses apply-advanced;
           list slot {
             key name;
             description "PSM slot number";
             leaf name {
               description "Select PSM slot";
               type union {
                 type string {
                   pattern "<.*>|$.*";
                 }
                 type uint32;
               }
             }
             uses apply-advanced;
           }
         }
       }
       leaf min-voltage {
         description "Set minimum input voltage(V)";
         type union {
           type uint32;
           type string {
             pattern "<.*>|$.*";
           }
         }
       }
       leaf max-power {
         description "Configure power capacity for the PSM (W)";
         type union {
           type uint32;
           type string {
             pattern "<.*>|$.*";
           }
         }
       }
     }
     leaf auto-image-upgrade {
       description "Auto image upgrade using DHCP";
       type empty;
     }
     container route-localization {
       description "Route-Localization settings";
       uses apply-advanced;
       leaf inet {
         description "Route-Localization inet";
         type empty;
       }
       leaf inet6 {
         description "Route-Localization inet6";
         type empty;
       }
     }
     container state {
       description "Set SFB upgrade state.";
       uses apply-advanced;
       leaf cb-upgrade {
         description "Set CB upgrade state on/off.";
         default "off";
         type enumeration {
           enum "off" {
             description "Set after CB upgrade is complete";
           }
           enum "on" {
             description "Set before the start of CB upgrade.";
           }
         }
       }
       leaf sfb-upgrade {
         description "Set SFB upgrade state on/off.";
         default "off";
         type enumeration {
           enum "off" {
             description "Set after SFB upgrade is complete";
           }
           enum "on" {
             description "Set before the start of SFB upgrade.";
           }
         }
       }
     }
     leaf extended-statistics {
       description "Enable extended system statistics";
       type empty;
     }
     container error {
       description "Error level configuration for all FPC";
       presence "enable error";
       uses chassis_fpc_error_type;
     }
     container oss-map {
       description "Translate Operation Supported System's requirements";
       uses apply-advanced;
       leaf model-name {
         description "Override chassis model name for specific show/snmp output";
         type enumeration {
           enum "t640" {
             description "Set to T640's model";
           }
           enum "t1600" {
             description "Set to T1600's model";
           }
         }
       }
     }
     container jnu-management {
       description "JNU Management configuration";
       uses apply-advanced;
       leaf mode {
         description "JNU Mode";
         type enumeration {
           enum "feature-rich" {
             description "Feature Rich Mode";
           }
           enum "bng-control-plane" {
             description "BNG control-plane mode";
           }
         }
       }
       leaf satellite-name {
         description "Satellite name";
         type string;
       }
       leaf device-group {
         description "Satellite device group";
         type string;
       }
       list device-group-map {
         key name;
         ordered-by user;
         description "Common groups mapping to device groups";
         leaf name {
           description "Satellite Device Group";
           type string;
         }
         uses apply-advanced;
         leaf-list include-groups {
           ordered-by user;
           description "Common groups list";
           type string;
         }
       }
       list satellite {
         key name;
         ordered-by user;
         description "List of satellites";
         leaf name {
           description "Satellite name";
           type string;
         }
         uses apply-advanced;
         leaf device-group {
           description "Satellite Device Group";
           type string;
         }
         leaf model {
           description "Satellite model";
           type string;
         }
         leaf version {
           description "Satellite version";
           type string {
           }
         }
       }
       leaf user {
         description "Satellite User Name";
         type string;
       }
       leaf controller {
         description "Controller Name";
         type string;
       }
       leaf authentication {
         description "Authentication string";
         type jt:unreadable;
       }
     }
     list satellite {
       key name;
       ordered-by user;
       description "List of available satellite configurations";
       leaf name {
         description "Satellite name";
         type string;
       }
       uses apply-advanced;
     }
     leaf preserve-fpc-poweron-sequence {
       description "Preserve MPC poweron sequence for consistency across reboot";
       type empty;
     }
     leaf auto-satellite-conversion {
       description "Enable remote conversion to satellite device-mode";
       type empty;
     }
     container satellite-management {
       presence "enable satellite-management";
       description "Satellite management configuration";
       uses apply-advanced;
       container designated-event-forwarding {
         presence "enable designated-event-forwarding";
         description "Designated event forwarding";
       }
       container traceoptions {
         description "Global satelite discovery and provisioning trace options";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Tracing parameters";
           leaf name {
             type enumeration {
               enum "parse" {
                 description "Trace configuration parsing";
               }
               enum "config-internal" {
                 description "Trace configuration internals";
               }
               enum "normal" {
                 description "Trace normal events";
               }
               enum "general" {
                 description "Trace general events";
               }
               enum "state" {
                 description "Trace state transitions";
               }
               enum "task" {
                 description "Trace SDPD task processing";
               }
               enum "timer" {
                 description "Trace SDPD task timer processing";
               }
               enum "krt" {
                 description "Trace communication over routing socket";
               }
               enum "lldp" {
                 description "Trace LLDP events";
               }
               enum "provision" {
                 description "Trace provisioning events";
               }
               enum "extended-port" {
                 description "Trace extended-port events";
               }
               enum "multi-chassis" {
                 description "Trace multi-chassis events";
               }
               enum "upgrade-group" {
                 description "Trace sw-update events";
               }
               enum "device" {
                 description "Trace device FSM events";
               }
               enum "tcp" {
                 description "Trace TCP events";
               }
               enum "interface" {
                 description "Trace interface events";
               }
               enum "cluster" {
                 description "Trace cluster events";
               }
               enum "all" {
                 description "Trace everything";
               }
             }
           }
           leaf disable {
             description "Disable this trace flag";
             type empty;
           }
         }
       }
       leaf cluster-policy {
         description "Cluster policy";
         type string;
       }
       list cluster {
         key name;
         description "Configure a satellite device cluster";
         leaf name {
           description "Satellite cluster name";
           type string {
             length "1 .. 16";
           }
         }
         uses apply-advanced;
         leaf cluster-id {
           description "Satellite cluster identifier";
           type union {
             type string {
               pattern "<.*>|$.*";
             }
             type uint32 {
               range "1 .. 32";
             }
           }
         }
         leaf-list cascade-ports {
           description "Cascade ports";
           type union {
             type jt:interface-device;
             type string {
               pattern "<.*>|$.*";
             }
           }
         }
         leaf cluster-policy {
           description "Candidate uplink policy";
           type string;
         }
         list fpc {
           key name;
           leaf name {
             description "Satellite slot identifier";
             type union {
               type string {
                 pattern "<.*>|$.*";
               }
               type uint32 {
                 range "65 .. 254";
               }
             }
           }
           uses apply-advanced;
           leaf alias {
             description "Satellite alias";
             type string {
               length "1 .. 16";
             }
           }
           leaf description {
             description "Satellite description";
             type string {
               length "1 .. 64";
             }
           }
           leaf member-id {
             description "Satellite member id";
             type union {
               type string {
                 pattern "<.*>|$.*";
               }
               type uint32 {
                 range "0 .. 62";
               }
             }
           }
           leaf system-id {
             description "Satellite system id";
             type jt:mac-addr;
           }
           leaf cluster-policy {
             description "Candidate uplink policy";
             type string;
           }
         }
       }
       list fpc {
         key name;
         description "FPC identifier for a satellite device";
         leaf name {
           description "Satellite slot identifier";
           type union {
             type string {
               pattern "<.*>|$.*";
             }
             type uint32 {
               range "65 .. 254";
             }
           }
         }
         uses apply-advanced;
         leaf serial-number {
           description "Satellite serial number";
           type string {
             length "1 .. 16";
           }
         }
         leaf system-id {
           description "Satellite system id";
           type jt:mac-addr;
         }
         leaf target-mode {
           description "Enable target mode forwarding for extended-ports";
           type empty;
         }
         leaf alias {
           description "Satellite alias";
           type string {
             length "1 .. 16";
           }
         }
         leaf description {
           description "Satellite description";
           type string {
             length "1 .. 64";
           }
         }
         container management-address {
           presence "enable management-address";
           description "Satellite Management Interface IP";
           uses apply-advanced;
           leaf address {
             description "Satellite Management Interface IP address";
             type jt:ipv4prefix;
           }
           leaf gateway {
             description "Satellite Management Interface Gateway IP address";
             type jt:ipv4addr;
           }
         }
         leaf-list cascade-ports {
           description "Cascade ports";
           type union {
             type jt:interface-device;
             type string {
               pattern "<.*>|$.*";
             }
           }
         }
         leaf extended-ports-template {
           description "Extended ports template";
           type string;
         }
         choice ufd_type {
           case case_1 {
             container uplink-failure-detection {
               presence "enable uplink-failure-detection";
               description "Enable uplink-failure-detection";
               uses apply-advanced;
               leaf candidate-uplink-policy {
                 description "Candidate uplink policy";
                 type string;
               }
             }
           }
         }
         leaf environment-monitoring-policy {
           description "Environment monitoring policy";
           type string;
         }
         choice forwarding-policy-type {
           case case_1 {
             container forwarding-policy {
               presence "enable forwarding-policy";
               description "Enable a forwarding policy";
               uses apply-advanced;
               leaf forwarding-policy-alias {
                 description "Define forwarding policy alias";
                 type string;
               }
             }
           }
         }
       }
       leaf extended-ports-policy {
         description "Extended ports policy";
         type string;
       }
       choice ufd_type {
         case case_1 {
           container uplink-failure-detection {
             presence "enable uplink-failure-detection";
             description "Enable uplink-failure-detection";
             uses apply-advanced;
             leaf candidate-uplink-policy {
               description "Candidate uplink policy";
               type string;
             }
           }
         }
       }
       container psu {
         description "Power Supply Unit redundancy configuration";
         uses apply-advanced;
         container redundancy {
           description "PSU Redundancy settings";
           uses apply-advanced;
           leaf n-plus-n {
             description "PSU redundancy: N+N configuration";
             type empty;
           }
         }
       }
       container environment-monitoring-policy {
         presence "enable environment-monitoring-policy";
         description "Environment monitoring policy";
         uses apply-advanced;
         leaf policy-name {
           description "Default environment monitoring policy";
           type string;
         }
       }
       choice forwarding-policy-type {
         case case_1 {
           container forwarding-policy {
             presence "enable forwarding-policy";
             description "Enable a forwarding policy";
             uses apply-advanced;
             leaf forwarding-policy-alias {
               description "Define forwarding policy alias";
               type string;
             }
           }
         }
       }
       container redundancy-groups {
         description "Redundancy groups configuration";
         uses apply-advanced;
         leaf chassis-id {
           description "Chassis identifier";
           type union {
             type string {
               pattern "<.*>|$.*";
             }
             type uint32 {
               range "1 .. 4";
             }
           }
         }
         list rg-group {
           key name;
           ordered-by user;
           description "Redundancy groups";
           uses redundancy-group-type;
         }
       }
       container upgrade-groups {
         description "Upgrade group configuration";
         uses apply-advanced;
         list upgrade-group {
           key name;
           description "Upgrade group";
           uses upgrade-group-type;
         }
       }
       container auto-satellite-conversion {
         description "Enable automatic satellite conversion";
         uses apply-advanced;
         leaf-list satellite {
           ordered-by user;
           description "Satellite slot-id or range or all";
           type string {
             length "1 .. 100";
           }
         }
       }
       container single-home {
         description "Devices are connected to local aggregation device only";
         uses apply-advanced;
         leaf-list satellite {
           ordered-by user;
           description "Satellite slot-id or range or all";
           type string {
             length "1 .. 100";
           }
         }
       }
       leaf aging-timer {
         description "Aging-timer";
         units "minutes";
         type union {
           type string {
             pattern "<.*>|$.*";
           }
           type uint32 {
             range "2 .. 60000";
           }
         }
       }
       leaf block-console-access {
         description "Block console access";
         type empty;
       }
       container firewall {
         description "Define a firewall configuration";
         uses apply-advanced;
         container family {
           description "Protocol family";
           container bridge {
             description "Protocol family BRIDGE for firewall filter";
             uses apply-advanced;
             list filter {
               key name;
               ordered-by user;
               uses satellite-bridge-filter;
             }
           }
         }
       }
     }
     container periodic {
       description "Chassisd periodic options";
       uses apply-advanced;
       leaf yield-cpu {
         description "Yield cpu in FRU periodic";
         type empty;
       }
       leaf one-sib-per-check {
         description "Check one SIB per periodic";
         type empty;
       }
       leaf no-sib-asic-stats {
         description "Disable asic statis for all SIBs in periodic";
         type empty;
       }
       leaf slow-fpc-check {
         description "Slow FPC check in periodic";
         type empty;
       }
       leaf ch-power-check-interval {
         description "Chassis power check interval, 0=default";
         default "0";
         units "seconds";
         type union {
           type string {
             pattern "<.*>|$.*";
           }
           type uint32 {
             range "0 .. 60";
           }
         }
       }
       leaf re-check-interval {
         description "Chassis RE check interval, 0=default";
         default "0";
         units "seconds";
         type union {
           type string {
             pattern "<.*>|$.*";
           }
           type uint32 {
             range "0 .. 60";
           }
         }
       }
     }
     leaf turbotx-disable {
       description "Disable turbotx processing";
       type empty;
     }
     container thermal-health-check {
       presence "enable thermal-health-check";
       description "Enable Thermal Health check of the chassis";
       uses apply-advanced;
       container fet-failure-check {
         presence "enable fet-failure-check";
         uses apply-advanced;
         leaf action-onfail {
           description "Set the action when Oring FET detected";
           default "none";
           type enumeration {
             enum "none" {
               description "No action when Oring FET detected";
             }
             enum "auto-shutdown" {
               description "Shutdown when Oring FET detected";
             }
           }
         }
       }
     }
     container fpc-down-on-repeated-conn-drops {
       description "Bring FPC down if connection drops repeatedly";
       uses apply-advanced;
       leaf max-drop-count {
         description "Number of connection drops to shutdown FPC";
         default "0";
         type union {
           type uint32;
           type string {
             pattern "<.*>|$.*";
           }
         }
       }
       leaf time-interval {
         description "Interval in minutes over which connection drops are counted";
         default "0";
         units "minutes";
         type union {
           type uint32;
           type string {
             pattern "<.*>|$.*";
           }
         }
       }
     }
     container mode {
       description "Set FRU mode";
       uses apply-advanced;
       container standalone {
         presence "enable standalone";
         description "Bringup FRU in standalone mode1";
         uses apply-advanced;
         list fpc {
           key name;
           leaf name {
             description "FPC slot number";
             type string {
               length "1 .. 4";
             }
           }
           uses apply-advanced;
           container loopback {
             description "Loopback Configuration for Mode & Type";
             uses apply-advanced;
             leaf wan {
               default "serdes";
               type enumeration {
                 enum "serdes" {
                   description "Serdes type loopback";
                 }
                 enum "retimer" {
                   description "Retimer type loopback";
                 }
               }
             }
             leaf fabric {
               default "serdes";
               type enumeration {
                 enum "serdes" {
                   description "Serdes type loopback";
                 }
                 enum "retimer" {
                   description "Retimer type loopback";
                 }
               }
             }
           }
         }
         list fabric-card {
           key name;
           ordered-by user;
           description "Fabric Card Loopback setting";
           uses chassis_fabric_card_type;
         }
       }
       choice power-mode {
         case case_1 {
           leaf power-optimized {
             description "Set power mode to power-optimized";
             type empty;
           }
         }
       }
     }
     leaf local-station-mac {
       description "Local station mac address configuration";
       type jt:mac-unicast;
     }
     container system-domains {
       presence "enable system-domains";
       description "Root and protected system domain configuration";
       uses apply-advanced;
       leaf root-domain-id {
         description "Root domain identifier";
         type union {
           type string {
             pattern "<.*>|$.*";
           }
           type uint32 {
             range "1 .. 3";
           }
         }
       }
       list protected-system-domains {
         key name;
         description "Protected system domain configuration";
         uses juniper-protected-system-domain;
       }
       container traceoptions {
         description "Protected system domain traceoptions";
         uses juniper-protected-system-domain-traceoptions;
       }
     }
     container network-slices {
       presence "enable network-slices";
       description "Network slices configuration";
       uses apply-advanced;
       container guest-network-functions {
         presence "enable guest-network-functions";
         description "Guest network function configuration";
         uses apply-advanced;
         list gnf {
           key name;
           description "Guest network function";
           uses juniper-gnf;
         }
       }
       leaf vlan-isolation {
         description "Enable VLAN isolation for Control Plane";
         type empty;
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping chassis-pw-type {
     uses apply-advanced;
     leaf device-count {
       description "Number of pseudo-wire ps devices";
       type union {
         type string {
           pattern "<.*>|$.*";
         }
         type uint32 {
           range "1 .. 18000";
         }
       }
     }
   }
   grouping chassis_agg_dev_type {
     uses apply-advanced;
     leaf ae-20 {
       description "Run AE over Container nexthops Infrastructure";
       status deprecated;
       type empty;
     }
     container ethernet {
       description "Aggregated device options for Ethernet";
       uses chassisd_agg_enet_type;
     }
     container sonet {
       description "Aggregated device options for SONET";
       uses chassisd_agg_pos_type;
     }
     leaf maximum-links {
       description "Maximum links limit for aggregated devices (16, 32, or 64)";
       type union {
         type int32;
         type string {
           pattern "<.*>|$.*";
         }
       }
     }
   }
   grouping chassis_alarm_type {
     uses apply-advanced;
     container management-ethernet {
       description "Management Ethernet alarms";
       uses chassis_alarm_ethernet_type;
     }
     container otn-odu {
       description "OTN ODU alarms";
       uses chassis_alarm_otn_odu_type;
     }
     container otn-otu {
       description "OTN OTU alarms";
       uses chassis_alarm_otn_otu_type;
     }
     container sonet {
       description "SONET alarms";
       uses chassis_alarm_sonet_type;
     }
     container t3 {
       description "DS3 alarms";
       uses chassis_alarm_ds3_type;
     }
     container ds1 {
       description "DS1 alarms";
       uses chassis_alarm_ds1_type;
     }
     container ethernet {
       description "Ethernet alarms";
       uses chassis_alarm_ethernet_type;
     }
     container integrated-services {
       description "Integrated services alarms";
       uses chassis_alarm_integrated_services_type;
     }
     container services {
       description "Services PIC alarms";
       uses chassis_alarm_services_type;
     }
     container serial {
       description "Serial alarms";
       uses chassis_alarm_serial_type;
     }
     container fibre-channel {
       description "Fibre Channel alarms";
       uses chassis_alarm_fibre-channel_type;
     }
     container relay {
       description "Alarm relays";
       uses chassis_alarm_relay_type;
     }
     list psm {
       key name;
       description "Alarm for psm input feed";
       leaf name {
         description "PSM slot number";
         type union {
           type string {
             pattern "<.*>|$.*";
           }
           type uint32;
         }
       }
       uses apply-advanced;
       container input1 {
         uses apply-advanced;
         leaf ignore {
           description "Ignore input1 alarm of Power Supply Module";
           type empty;
         }
       }
       container input2 {
         uses apply-advanced;
         leaf ignore {
           description "Ignore input2 alarm of Power Supply Module";
           type empty;
         }
       }
     }
     container fru-absence {
       description "FRU module absence";
       uses apply-advanced;
       container ignore {
         description "Ignore the power supply module absence alarm";
         uses apply-advanced;
         list fpc {
           key name;
           ordered-by user;
           description "FPC Slot Number";
           uses chassis_fpc_type_slot;
         }
       }
     }
   }
   grouping chassis_alarm_ds1_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ds3_type {
     uses apply-advanced;
     leaf ais {
       description "Alarm indicator signal";
       type enumeration {
         enum "red" {
           description "Assert red system alarm";
         }
         enum "yellow" {
           description "Assert yellow system alarm";
         }
         enum "ignore" {
           description "Do not assert any alarm signals";
         }
       }
     }
     leaf exz {
       description "Excessive zeros";
       type enumeration {
         enum "red" {
           description "Assert red system alarm";
         }
         enum "yellow" {
           description "Assert yellow system alarm";
         }
         enum "ignore" {
           description "Do not assert any alarm signals";
         }
       }
     }
     leaf ferf {
       description "Far-end failure";
       type enumeration {
         enum "red" {
           description "Assert red system alarm";
         }
         enum "yellow" {
           description "Assert yellow system alarm";
         }
         enum "ignore" {
           description "Do not assert any alarm signals";
         }
       }
     }
     leaf idle {
       description "Idle alarm";
       type enumeration {
         enum "red" {
           description "Assert red system alarm";
         }
         enum "yellow" {
           description "Assert yellow system alarm";
         }
         enum "ignore" {
           description "Do not assert any alarm signals";
         }
       }
     }
     leaf lcv {
       description "Line code violation";
       type enumeration {
         enum "red" {
           description "Assert red system alarm";
         }
         enum "yellow" {
           description "Assert yellow system alarm";
         }
         enum "ignore" {
           description "Do not assert any alarm signals";
         }
       }
     }
     leaf lof {
       description "Loss of frame";
       type enumeration {
         enum "red" {
           description "Assert red system alarm";
         }
         enum "yellow" {
           description "Assert yellow system alarm";
         }
         enum "ignore" {
           description "Do not assert any alarm signals";
         }
       }
     }
     leaf los {
       description "Loss of signal";
       type enumeration {
         enum "red" {
           description "Assert red system alarm";
         }
         enum "yellow" {
           description "Assert yellow system alarm";
         }
         enum "ignore" {
           description "Do not assert any alarm signals";
         }
       }
     }
     leaf pll {
       description "Phase-locked loop out of lock";
       type enumeration {
         enum "red" {
           description "Assert red system alarm";
         }
         enum "yellow" {
           description "Assert yellow system alarm";
         }
         enum "ignore" {
           description "Do not assert any alarm signals";
         }
       }
     }
     leaf ylw {
       description "Yellow alarm";
       type enumeration {
         enum "red" {
           description "Assert red system alarm";
         }
         enum "yellow" {
           description "Assert yellow system alarm";
         }
         enum "ignore" {
           description "Do not assert any alarm signals";
         }
       }
     }
   }
   grouping chassis_alarm_ethernet_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_fibre-channel_type {
     uses apply-advanced;
     leaf link-down {
       description "Link has gone down";
       type enumeration {
         enum "red" {
           description "Assert red system alarm";
         }
         enum "yellow" {
           description "Assert yellow system alarm";
         }
         enum "ignore" {
           description "Do not assert any alarm signals";
         }
       }
     }
   }
   grouping chassis_alarm_integrated_services_type {
     uses apply-advanced;
     leaf failure {
       description "Integrated Services failure";
       type enumeration {
         enum "red" {
           description "Assert red system alarm";
         }
         enum "yellow" {
           description "Assert yellow system alarm";
         }
         enum "ignore" {
           description "Do not assert any alarm signals";
         }
       }
     }
   }
   grouping chassis_alarm_otn_odu_type {
     uses apply-advanced;
     leaf odu-bdi {
       description "ODU backward-defect-indicator, ODU-BDI failure";
       type enumeration {
         enum "red" {
           description "Assert red system alarm";
         }
         enum "yellow" {
           description "Assert yellow system alarm";
         }
         enum "ignore" {
           description "Do not assert any alarm signals";
         }
       }
     }
     leaf odu-ttim {
       description "ODU trail-trace-identifier-mismatch, ODU-TTIM failure";
       type enumeration {
         enum "red" {
           description "Assert red system alarm";
         }
         enum "yellow" {
           description "Assert yellow system alarm";
         }
         enum "ignore" {
           description "Do not assert any alarm signals";
         }
       }
     }
     leaf odu-ptim {
       description "ODU payload-type-mismatch, ODU-PTIM failure";
       type enumeration {
         enum "red" {
           description "Assert red system alarm";
         }
         enum "yellow" {
           description "Assert yellow system alarm";
         }
         enum "ignore" {
           description "Do not assert any alarm signals";
         }
       }
     }
   }
   grouping chassis_alarm_otn_otu_type {
     uses apply-advanced;
     leaf oc-los {
       description "Loss of signal, LOS failure";
       type enumeration {
         enum "red" {
           description "Assert red system alarm";
         }
         enum "yellow" {
           description "Assert yellow system alarm";
         }
         enum "ignore" {
           description "Do not assert any alarm signals";
         }
       }
     }
     leaf oc-lof {
       description "Loss of framing, LOF failure";
       type enumeration {
         enum "red" {
           description "Assert red system alarm";
         }
         enum "yellow" {
           description "Assert yellow system alarm";
         }
         enum "ignore" {
           description "Do not assert any alarm signals";
         }
       }
     }
     leaf oc-lom {
       description "Loss of multiframe, LOM failure";
       type enumeration {
         enum "red" {
           description "Assert red system alarm";
         }
         enum "yellow" {
           description "Assert yellow system alarm";
         }
         enum "ignore" {
           description "Do not assert any alarm signals";
         }
       }
     }
     leaf wavelength-lock {
       description "Wavelength lock alarm";
       type enumeration {
         enum "red" {
           description "Assert red system alarm";
         }
         enum "yellow" {
           description "Assert yellow system alarm";
         }
         enum "ignore" {
           description "Do not assert any alarm signals";
         }
       }
     }
     leaf otu-bdi {
       description "OTU backward-defect-indicator, OTU-BDI failure";
       type enumeration {
         enum "red" {
           description "Assert red system alarm";
         }
         enum "yellow" {
           description "Assert yellow system alarm";
         }
         enum "ignore" {
           description "Do not assert any alarm signals";
         }
       }
     }
     leaf otu-iae {
       description "OTU incoming-alignment-error, OTU-IAE failure";
       type enumeration {
         enum "red" {
           description "Assert red system alarm";
         }
         enum "yellow" {
           description "Assert yellow system alarm";
         }
         enum "ignore" {
           description "Do not assert any alarm signals";
         }
       }
     }
     leaf otu-ttim {
       description "OTU trail-trace-identifier-mismatch, OTU-TTIM failure";
       type enumeration {
         enum "red" {
           description "Assert red system alarm";
         }
         enum "yellow" {
           description "Assert yellow system alarm";
         }
         enum "ignore" {
           description "Do not assert any alarm signals";
         }
       }
     }
     leaf otu-fec-excessive-errs {
       description "OTU fec-excessive-errors, OTU-FEC_EXE failure";
       type enumeration {
         enum "red" {
           description "Assert red system alarm";
         }
         enum "yellow" {
           description "Assert yellow system alarm";
         }
         enum "ignore" {
           description "Do not assert any alarm signals";
         }
       }
     }
   }
   grouping chassis_alarm_relay_type {
     uses apply-advanced;
     container input {
       description "Input relays";
       uses apply-advanced;
       list port {
         key name;
         ordered-by user;
         leaf name {
           description "Relay port number";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf trigger {
           description "Relay triggered";
           type enumeration {
             enum "red" {
               description "Assert red system alarm";
             }
             enum "yellow" {
               description "Assert yellow system alarm";
             }
             enum "ignore" {
               description "Do not assert any alarm signals";
             }
           }
         }
       }
     }
     container output {
       description "Output relays";
       uses apply-advanced;
       list port {
         key name;
         ordered-by user;
         leaf name {
           description "Relay port number";
           type union {
             type string {
               pattern "<.*>|$.*";
             }
             type uint32 {
               range "0 .. 3";
             }
           }
         }
         uses apply-advanced;
         leaf mode {
           description "Relay mode in de-active state";
           type enumeration {
             enum "open" {
               description "Normally open";
             }
             enum "close" {
               description "Normally closed";
             }
           }
         }
         leaf temperature {
           description "Trigger on temperature alarm red";
           type empty;
         }
         leaf input-relay {
           description "Trigger on input relay trigger";
           type union {
             type string {
               pattern "<.*>|$.*";
             }
             type uint32 {
               range "0 .. 3";
             }
           }
         }
       }
     }
   }
   grouping chassis_alarm_serial_type {
     uses apply-advanced;
     leaf loss-of-rx-clock {
       description "RX clock absent";
       type enumeration {
         enum "red" {
           description "Assert red system alarm";
         }
         enum "yellow" {
           description "Assert yellow system alarm";
         }
         enum "ignore" {
           description "Do not assert any alarm signals";
         }
       }
     }
     leaf loss-of-tx-clock {
       description "TX clock absent";
       type enumeration {
         enum "red" {
           description "Assert red system alarm";
         }
         enum "yellow" {
           description "Assert yellow system alarm";
         }
         enum "ignore" {
           description "Do not assert any alarm signals";
         }
       }
     }
     leaf dcd-absent {
       description "DCD signal absent";
       type enumeration {
         enum "red" {
           description "Assert red system alarm";
         }
         enum "yellow" {
           description "Assert yellow system alarm";
         }
         enum "ignore" {
           description "Do not assert any alarm signals";
         }
       }
     }
     leaf cts-absent {
       description "CTS signal absent";
       type enumeration {
         enum "red" {
           description "Assert red system alarm";
         }
         enum "yellow" {
           description "Assert yellow system alarm";
         }
         enum "ignore" {
           description "Do not assert any alarm signals";
         }
       }
     }
     leaf dsr-absent {
       description "DSR signal absent";
       type enumeration {
         enum "red" {
           description "Assert red system alarm";
         }
         enum "yellow" {
           description "Assert yellow system alarm";
         }
         enum "ignore" {
           description "Do not assert any alarm signals";
         }
       }
     }
     leaf tm-absent {
       description "TM signal absent";
       type enumeration {
         enum "red" {
           description "Assert red system alarm";
         }
         enum "yellow" {
           description "Assert yellow system alarm";
         }
         enum "ignore" {
           description "Do not assert any alarm signals";
         }
       }
     }
   }
   grouping chassis_alarm_services_type {
     uses apply-advanced;
     leaf pic-reset {
       description "Services PIC reset";
       type enumeration {
         enum "red" {
           description "Assert red system alarm";
         }
         enum "yellow" {
           description "Assert yellow system alarm";
         }
         enum "ignore" {
           description "Do not assert any alarm signals";
         }
       }
     }
     leaf pic-hold-reset {
       description "Services PIC held in reset";
       type enumeration {
         enum "red" {
           description "Assert red system alarm";
         }
         enum "yellow" {
           description "Assert yellow system alarm";
         }
         enum "ignore" {
           description "Do not assert any alarm signals";
         }
       }
     }
     leaf linkdown {
       description "Services PIC linkdown";
       type enumeration {
         enum "red" {
           description "Assert red system alarm";
         }
         enum "yellow" {
           description "Assert yellow system alarm";
         }
         enum "ignore" {
           description "Do not assert any alarm signals";
         }
       }
     }
     leaf rx-errors {
       description "Services PIC excessive rx errors";
       type enumeration {
         enum "red" {
           description "Assert red system alarm";
         }
         enum "yellow" {
           description "Assert yellow system alarm";
         }
         enum "ignore" {
           description "Do not assert any alarm signals";
         }
       }
     }
     leaf tx-errors {
       description "Services PIC excessive tx errors";
       type enumeration {
         enum "red" {
           description "Assert red system alarm";
         }
         enum "yellow" {
           description "Assert yellow system alarm";
         }
         enum "ignore" {
           description "Do not assert any alarm signals";
         }
       }
     }
     leaf sw-down {
       description "Services PIC software problem";
       type enumeration {
         enum "red" {
           description "Assert red system alarm";
         }
         enum "yellow" {
           description "Assert yellow system alarm";
         }
         enum "ignore" {
           description "Do not assert any alarm signals";
         }
       }
     }
     leaf hw-down {
       description "Services PIC hardware problem";
       type enumeration {
         enum "red" {
           description "Assert red system alarm";
         }
         enum "yellow" {
           description "Assert yellow system alarm";
         }
         enum "ignore" {
           description "Do not assert any alarm signals";
         }
       }
     }
   }
   grouping chassis_alarm_sonet_type {
     uses apply-advanced;
     leaf lol {
       description "Loss of light";
       type enumeration {
         enum "red" {
           description "Assert red system alarm";
         }
         enum "yellow" {
           description "Assert yellow system alarm";
         }
         enum "ignore" {
           description "Do not assert any alarm signals";
         }
       }
     }
     leaf pll {
       description "Phase locked loop out of lock";
       type enumeration {
         enum "red" {
           description "Assert red system alarm";
         }
         enum "yellow" {
           description "Assert yellow system alarm";
         }
         enum "ignore" {
           description "Do not assert any alarm signals";
         }
       }
     }
     leaf lof {
       description "Loss of framing, LOF failure";
       type enumeration {
         enum "red" {
           description "Assert red system alarm";
         }
         enum "yellow" {
           description "Assert yellow system alarm";
         }
         enum "ignore" {
           description "Do not assert any alarm signals";
         }
       }
     }
     leaf los {
       description "Loss of signal, LOS failure";
       type enumeration {
         enum "red" {
           description "Assert red system alarm";
         }
         enum "yellow" {
           description "Assert yellow system alarm";
         }
         enum "ignore" {
           description "Do not assert any alarm signals";
         }
       }
     }
     leaf ais-l {
       description "Line alarm indication signal, AIS-L failure";
       type enumeration {
         enum "red" {
           description "Assert red system alarm";
         }
         enum "yellow" {
           description "Assert yellow system alarm";
         }
         enum "ignore" {
           description "Do not assert any alarm signals";
         }
       }
     }
     leaf ais-p {
       description "Path alarm indication signal, AIS-P failure";
       type enumeration {
         enum "red" {
           description "Assert red system alarm";
         }
         enum "yellow" {
           description "Assert yellow system alarm";
         }
         enum "ignore" {
           description "Do not assert any alarm signals";
         }
       }
     }
     leaf lop-p {
       description "Loss of pointer, LOP-P failure";
       type enumeration {
         enum "red" {
           description "Assert red system alarm";
         }
         enum "yellow" {
           description "Assert yellow system alarm";
         }
         enum "ignore" {
           description "Do not assert any alarm signals";
         }
       }
     }
     leaf ber-sd {
       description "Signal Degrade (SD), bit error rate > 1E-6";
       type enumeration {
         enum "red" {
           description "Assert red system alarm";
         }
         enum "yellow" {
           description "Assert yellow system alarm";
         }
         enum "ignore" {
           description "Do not assert any alarm signals";
         }
       }
     }
     leaf ber-sf {
       description "Signal Fail (SF), bit error rate > 1E-3";
       type enumeration {
         enum "red" {
           description "Assert red system alarm";
         }
         enum "yellow" {
           description "Assert yellow system alarm";
         }
         enum "ignore" {
           description "Do not assert any alarm signals";
         }
       }
     }
     leaf rfi-l {
       description "Line remote failure indication, RFI-L, line FERF";
       type enumeration {
         enum "red" {
           description "Assert red system alarm";
         }
         enum "yellow" {
           description "Assert yellow system alarm";
         }
         enum "ignore" {
           description "Do not assert any alarm signals";
         }
       }
     }
     leaf rfi-p {
       description "Path remote failure indication, RFI-P, STS path yellow";
       type enumeration {
         enum "red" {
           description "Assert red system alarm";
         }
         enum "yellow" {
           description "Assert yellow system alarm";
         }
         enum "ignore" {
           description "Do not assert any alarm signals";
         }
       }
     }
     leaf uneq-p {
       description "STS Path (C2) unequipped, UNEQ-P failure";
       type enumeration {
         enum "red" {
           description "Assert red system alarm";
         }
         enum "yellow" {
           description "Assert yellow system alarm";
         }
         enum "ignore" {
           description "Do not assert any alarm signals";
         }
       }
     }
     leaf locd {
       description "Loss of cell delineation (ATM only)";
       type enumeration {
         enum "red" {
           description "Assert red system alarm";
         }
         enum "yellow" {
           description "Assert yellow system alarm";
         }
         enum "ignore" {
           description "Do not assert any alarm signals";
         }
       }
     }
     leaf plm-p {
       description "STS payload label (C2) mismatch, PLM-P failure";
       type enumeration {
         enum "red" {
           description "Assert red system alarm";
         }
         enum "yellow" {
           description "Assert yellow system alarm";
         }
         enum "ignore" {
           description "Do not assert any alarm signals";
         }
       }
     }
   }
   grouping chassis_cb_type {
     leaf name {
       description "CB slot number";
       type union {
         type string {
           pattern "<.*>|$.*";
         }
         type uint32;
       }
     }
     uses apply-advanced;
     container temperature-threshold {
       description "CB temperature thresholds";
       uses chassis-temperature-threshold-type;
     }
     list temperature-sensor {
       key name;
       description "CB temperature sensor";
       uses chassis-temperature-sensor-type;
     }
   }
   grouping chassis-temperature-sensor-type {
     leaf name {
       description "Temperature sensor name";
       type string;
     }
     uses apply-advanced;
     container temperature-threshold {
       description "Temperature thresholds";
       uses chassis-temperature-threshold-type;
     }
   }
   grouping chassis-temperature-threshold-type {
     description "Chassis temperature thresholds";
     uses apply-advanced;
     leaf fans-to-normal-speed {
       description "Threshold at which fans return to normal speed";
       units "degrees C";
       type union {
         type uint32;
         type string {
           pattern "<.*>|$.*";
         }
       }
     }
     leaf fans-on-intermediate-speed {
       description "Threshold at which fans run intermediate speed";
       units "degrees C";
       type union {
         type uint32;
         type string {
           pattern "<.*>|$.*";
         }
       }
     }
     leaf fans-on-full-speed {
       description "Threshold at which fans run full speed";
       units "degrees C";
       type union {
         type uint32;
         type string {
           pattern "<.*>|$.*";
         }
       }
     }
     leaf fans-on-full-speed-if-failed-fan {
       description "Threshold at which fans run full speed when bad fan present";
       units "degrees C";
       type union {
         type uint32;
         type string {
           pattern "<.*>|$.*";
         }
       }
     }
     leaf yellow-alarm {
       description "Threshold at which yellow alarm is set";
       units "degrees C";
       type union {
         type uint32;
         type string {
           pattern "<.*>|$.*";
         }
       }
     }
     leaf yellow-alarm-if-failed-fan {
       description "Threshold at which yellow alarm is set when bad fan present";
       units "degrees C";
       type union {
         type uint32;
         type string {
           pattern "<.*>|$.*";
         }
       }
     }
     leaf red-alarm {
       description "Threshold at which red alarm is set";
       units "degrees C";
       type union {
         type uint32;
         type string {
           pattern "<.*>|$.*";
         }
       }
     }
     leaf red-alarm-if-failed-fan {
       description "Threshold at which red alarm is set when bad fan present";
       units "degrees C";
       type union {
         type uint32;
         type string {
           pattern "<.*>|$.*";
         }
       }
     }
     leaf fire-shutdown {
       description "Threshold at which router will be shutdown within 10 seconds";
       units "degrees C";
       type union {
         type uint32;
         type string {
           pattern "<.*>|$.*";
         }
       }
     }
   }
   grouping chassis_fabric_card_type {
     leaf name {
       description "Fabric Card slot number";
       type string {
         length "1 .. 5";
       }
     }
     uses apply-advanced;
     container loopback {
       description "Loopback Configuration for Mode & Type";
       uses apply-advanced;
       leaf serdes {
         description "Fabric Card serdes setting";
         type empty;
       }
       leaf retimer {
         description "Fabric card retimer setting";
         type empty;
       }
     }
   }
   grouping chassis_fabric_type {
     uses apply-advanced;
     leaf upgrade-mode {
       description "Enable online switch fabric upgrade";
       type enumeration {
         enum "default" {
           description "Fabric upgrade";
         }
         enum "t4000" {
           description "T4000 Fabric upgrade";
         }
         enum "3d-fabric" {
           description "TXP-3D Fabric upgrade";
         }
       }
     }
     container event {
       description "Fabric events";
       uses apply-advanced;
       container link-failure {
         presence "enable link-failure";
         description "Fabric link failure";
         uses apply-advanced;
         container action {
           presence "enable action";
           description "Fabric action to be taken";
           uses apply-advanced;
         }
       }
       container reachability-fault {
         presence "enable reachability-fault";
         description "Fabric reachability fault detection";
         uses apply-advanced;
         container degraded {
           presence "enable degraded";
           description "Degraded fabric configuration";
           uses apply-advanced;
           container error-threshold {
             presence "enable error-threshold";
             description "Fabric error threshold for degraded case";
             uses apply-advanced;
             container degradation {
               presence "enable degradation";
               description "Degradation attributes";
               uses apply-advanced;
               leaf percentage {
                 description "The percentage degradation on which action is taken";
                 type union {
                   type string {
                     pattern "<.*>|$.*";
                   }
                   type uint32 {
                     range "1 .. 99";
                   }
                 }
               }
             }
           }
         }
         container actions {
           description "Reachability fault actions";
           uses apply-advanced;
           leaf fpc-restart-disable {
             description "Disable fpc restart action for FHP";
             type empty;
           }
           container recovery-failure {
             description "Recovery failure action to be taken for FHP";
             uses apply-advanced;
             leaf pfe-offline {
               description "Proceed with PFE offline action for FHP";
               type empty;
             }
           }
         }
       }
     }
     container oam {
       description "Fabric OAM configuration";
       uses apply-advanced;
       leaf detection-disable {
         description "Disable fabric OAM";
         type empty;
       }
       leaf runtime-disable {
         description "Disable runtime fabric OAM";
         type empty;
       }
     }
     container degraded {
       presence "enable degraded";
       description "Degraded fabric configuration";
       uses apply-advanced;
       leaf action-fpc-restart-disable {
         description "Limit degraded fabric actions to Plane restart only";
         type empty;
       }
       leaf degraded-fpc-bad-plane-threshold {
         description "No of bad planes to declare a FPC degraded";
         default "4";
         type union {
           type string {
             pattern "<.*>|$.*";
           }
           type uint32 {
             range "4 .. 18";
           }
         }
       }
       leaf degraded-fabric-detection-enable {
         description "Enable degraded FPC detection";
         type empty;
       }
       leaf fpc-restart {
         description "Restart fpc on zero planes";
         type empty;
       }
       leaf auto-recovery-disable {
         description "Disable fabric degraded auto recovery";
         type empty;
       }
       leaf fpc-offline-on-blackholing {
         description "Offline FPC on fabric blackholing";
         type empty;
       }
     }
     container redundancy-mode {
       description "Fabric redundancy mode";
       uses apply-advanced;
       choice mode {
         case case_1 {
           leaf redundant {
             description "Fabric is configured in redundant mode";
             type empty;
           }
         }
         case case_2 {
           leaf increased-bandwidth {
             description "Fabric is configured in increased bandwidth mode";
             type empty;
           }
         }
       }
     }
     leaf disable-grant-bypass {
       description "Disable fabric grant-bypass mode";
       type empty;
     }
   }
   grouping chassis_feb_type {
     uses apply-advanced;
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
     list slot {
       key name;
       ordered-by user;
       leaf name {
         description "FEB slot number";
         type union {
           type string {
             pattern "<.*>|$.*";
           }
           type uint32;
         }
       }
       uses apply-advanced;
       container sanity-poll {
         description "FPC register sanity poll";
         uses apply-advanced;
         leaf retry-count {
           description "Number of retries before reporting error";
           default "10";
           type union {
             type string {
               pattern "<.*>|$.*";
             }
             type uint32 {
               range "1 .. 30";
             }
           }
         }
         container on-error {
           description "Actions to be taken if inconsistencies are detected";
           uses apply-advanced;
           leaf raise-alarm {
             description "Raise emergency alarm";
             type empty;
           }
           leaf power {
             description "Power cycle or power off FPC";
             type enumeration {
               enum "cycle" {
                 description "Write coredump and reboot FPC";
               }
               enum "off" {
                 description "Power down FPC indefinitely";
               }
             }
           }
           leaf write-coredump {
             description "Write coredump and continue";
             type empty;
           }
         }
       }
       leaf power {
         description "Power FEBs on or off";
         type enumeration {
           enum "off" {
             description "Do not provide power to FEBs";
           }
           enum "on" {
             description "Provide power to FEBs";
           }
         }
       }
       choice mode {
       }
       leaf port-mirror-instance {
         description "Associate a port mirroring instance with the FEB";
         type string {
           length "1 .. 64";
         }
       }
       leaf sampling-instance {
         description "Associate a sampling instance with the FEB";
         type string {
           length "1 .. 64";
         }
       }
       leaf ucode-imem-remap {
         description "Remap the PIC microcode to IMEM on FEB";
         type empty;
       }
       container inline-services {
         uses apply-advanced;
         leaf report-zero-oif-gw-on-discard {
           description "Jflow reports value zero in OIF and GW when traffic is not forwarded";
           type empty;
         }
         leaf flex-flow-sizing {
           description "No fixed size allocation of flow tables for proto families";
           type empty;
         }
         leaf use-extended-flow-memory {
           description "Use extended memory for flow records";
           type empty;
         }
         container flow-table-size {
           uses apply-advanced;
           leaf ipv4-flow-table-size {
             description "IPv4 flow table size in units of 256k";
             type union {
               type string {
                 pattern "<.*>|$.*";
               }
               type uint32 {
                 range "1 .. 245";
               }
             }
           }
           leaf ipv6-flow-table-size {
             description "IPv6 flow table size in units of 256k";
             type union {
               type string {
                 pattern "<.*>|$.*";
               }
               type uint32 {
                 range "1 .. 245";
               }
             }
           }
           leaf vpls-flow-table-size {
             description "VPLS flow table size in units of 256k";
             type union {
               type string {
                 pattern "<.*>|$.*";
               }
               type uint32 {
                 range "1 .. 245";
               }
             }
           }
           leaf bridge-flow-table-size {
             description "BRIDGE flow table size in units of 256k";
             type union {
               type string {
                 pattern "<.*>|$.*";
               }
               type uint32 {
                 range "1 .. 245";
               }
             }
           }
           leaf ipv6-extended-attrib {
             description "Enable extended flow attribute";
             type empty;
           }
           leaf mpls-flow-table-size {
             description "MPLS flow table size in units of 256k";
             type union {
               type string {
                 pattern "<.*>|$.*";
               }
               type uint32 {
                 range "1 .. 245";
               }
             }
           }
         }
       }
       container inline-video-monitoring {
         uses apply-advanced;
         leaf maximum-flows-count {
           description "Maximum number of inline video monitoring flows per PFE instance";
           type union {
             type string {
               pattern "<.*>|$.*";
             }
             type uint32 {
               range "16 .. 8192";
             }
           }
         }
       }
       container error {
         description "Error level configuration for FEB";
         uses chassis_fpc_error_type;
       }
       list pfe {
         key name;
         description "Packet forwarding engine parameters";
         uses chassis_pfe_type;
       }
       container openflow {
         description "Openflow configuration";
         uses apply-advanced;
         leaf access-list-partition {
           description "Space reserved for openflow access-list rules";
           units "percents";
           type union {
             type string {
               pattern "<.*>|$.*";
             }
             type uint32 {
               range "0 .. 100";
             }
           }
         }
       }
     }
   }
   grouping chassis_fpc_error_type {
     description "Chassis Fpc Error level";
     uses apply-advanced;
     container fatal {
       description "FPC Fatal errors (default threshold = 1)";
       uses chassis_fpc_error_level_major_fatal;
     }
     container major {
       description "FPC Major Level errors (default threshold = 1)";
       uses chassis_fpc_error_level_major_fatal;
     }
     container minor {
       description "FPC Minor Level errors (default threshold = 10)";
       uses chassis_fpc_error_level_minor;
     }
     list override-cmerror {
       key name;
       ordered-by user;
       description "Error configuration override";
       max-elements 100;
       uses chassis_fru_cmerror_override_type;
     }
     container reset-pfe {
       description "FPC config reset-pfe options";
       presence "enable reset-pfe";
       uses chassis_fpc_error_config_reset_pfe_opt;
     }
     container scope {
       description "Error scope";
       uses chassis_fpc_scope_type;
     }
   }
   grouping chassis_fpc_error_config_reset_pfe_opt {
     uses apply-advanced;
     leaf retry-limit {
       description "Reset pfe retry limit";
       type union {
         type string {
           pattern "<.*>|$.*";
         }
         type uint32 {
           range "0 .. 3";
         }
       }
     }
     leaf pause-period {
       description "Reset pfe pause period in minutes";
       type union {
         type string {
           pattern "<.*>|$.*";
         }
         type uint32 {
           range "0 .. 10000000";
         }
       }
     }
     leaf pfe-disable-period {
       description "Reset pfe disable period in minutes";
       type union {
         type string {
           pattern "<.*>|$.*";
         }
         type uint32 {
           range "1 .. 10000000";
         }
       }
     }
   }
   grouping chassis_fpc_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise FPC trap";
           }
         }
       }
       uses apply-advanced;
     }
   }
   grouping chassis_fpc_scope_type {
     description "Chassis Fpc Error Scope";
     uses apply-advanced;
     container board {
       description "Board level scope";
       uses chassis_fpc_scope_category;
     }
     container pfe {
       description "Forwarding engine scope ";
       uses chassis_fpc_scope_category;
     }
   }
   grouping chassis_fpc_scope_category {
     description "Chassis Fpc Error Category";
     uses apply-advanced;
     container category {
       description "FPC error category";
       uses chassis_fpc_scope_category_type;
     }
   }
   grouping chassis_fpc_scope_category_type {
     description "Chassis Fpc Category level";
     uses apply-advanced;
     container functional {
       description "FPC functional category";
       uses chassis_fpc_scope_category_error_type;
     }
     container memory {
       description "FPC memory category";
       uses chassis_fpc_scope_category_error_type;
     }
     container io {
       description "FPC input-output category";
       uses chassis_fpc_scope_category_error_type;
     }
     container storage {
       description "FPC storage category";
       uses chassis_fpc_scope_category_error_type;
     }
     container switch {
       description "FPC switch category";
       uses chassis_fpc_scope_category_error_type;
     }
     container processing {
       description "FPC processing category";
       uses chassis_fpc_scope_category_error_type;
     }
   }
   grouping chassis_fpc_scope_category_error_type {
     description "Chassis Fpc Error level";
     uses apply-advanced;
     container fatal {
       description "FPC Fatal errors (default threshold = 1)";
       uses chassis_fpc_error_level_type;
     }
     container major {
       description "FPC Major Level errors (default threshold = 1)";
       uses chassis_fpc_error_level_type;
     }
     container minor {
       description "FPC Minor Level errors (default threshold = 10)";
       uses chassis_fpc_error_level_type;
     }
   }
   grouping chassis_fpc_error_level_type {
     uses apply-advanced;
     leaf threshold {
       description "Error count at which to take the action (0 - valid for minor only)";
       type union {
         type string {
           pattern "<.*>|$.*";
         }
         type uint32 {
           range "0 .. 4294967295";
         }
       }
     }
     list action {
       key name;
       ordered-by user;
       description "Configure the action for this level";
       leaf name {
         type enumeration {
           enum "reset" {
             description "Reset FPC";
           }
           enum "offline" {
             description "Offline FPC";
           }
           enum "alarm" {
             description "Raise FPC alarm";
           }
           enum "get-state" {
             description "Retreive FPC state for debugging";
           }
           enum "log" {
             description "Log occurence to system log file";
           }
           enum "disable-pfe" {
             description "Disable PFE interfaces on FPC";
           }
           enum "reset-pfe" {
             description "Reset PFE on FPC";
           }
           enum "offline-pic" {
             description "Offline PICs associated with PFE on FPC";
           }
           enum "trap" {
             description "Raise trap";
           }
         }
       }
       uses apply-advanced;
     }
   }
   grouping chassis_fpc_type {
     leaf name {
       description "FPC slot number";
       type union {
         type string {
           pattern "<.*>|$.*";
         }
         type uint32;
       }
     }
     uses apply-advanced;
     container auto-speed-detection {
       description "Disables auto-speed detection";
       uses apply-advanced;
       choice auto-speed-detections {
         case case_1 {
           leaf disable {
             description "Disables automatic speed detection";
             type empty;
           }
         }
       }
     }
     container linkscan-per-fpc {
       presence "enable linkscan-per-fpc";
       description "Configure linkscan per FPC";
       uses apply-advanced;
       leaf fpc-linkscan-interval {
         description " setting linkscan interval of FPC in microsecond";
         type union {
           type string {
             pattern "<.*>|$.*";
           }
           type uint32 {
             range "10000 .. 500000";
           }
         }
       }
     }
     container ukern-trace {
       description "Set ukern trace";
       uses apply-advanced;
       container log {
         description "Set ukern-trace log";
         uses apply-advanced;
         leaf app-type {
           description "Name of application with ukern-trace logs";
           type enumeration {
             enum "dfw" {
               description "All dfw ukern-trace logs";
             }
           }
         }
         leaf logging {
           description "Enable or Disable ukern-trace logging of an app-type";
           type enumeration {
             enum "off" {
               description "Disable logging";
             }
             enum "on" {
               description "Enable logging";
             }
           }
         }
       }
     }
     container sanity-poll {
       description "FPC register sanity poll";
       uses apply-advanced;
       leaf retry-count {
         description "Number of retries before reporting error";
         default "10";
         type union {
           type string {
             pattern "<.*>|$.*";
           }
           type uint32 {
             range "1 .. 30";
           }
         }
       }
       container on-error {
         description "Actions to be taken if inconsistencies are detected";
         uses apply-advanced;
         leaf raise-alarm {
           description "Raise emergency alarm";
           type empty;
         }
         leaf power {
           description "Power cycle or power off FPC";
           type enumeration {
             enum "cycle" {
               description "Write coredump and reboot FPC";
             }
             enum "off" {
               description "Power down FPC indefinitely";
             }
           }
         }
         leaf write-coredump {
           description "Write coredump and continue";
           type empty;
         }
       }
     }
     container forwarding-options {
       description "Configure options to control packet forwarding";
       uses apply-advanced;
       choice uft_object {
         case case_1 {
           container l2-profile-one {
             presence "enable l2-profile-one";
             description "MAC: 288K L3-host: 16K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_2 {
           container l2-profile-two {
             presence "enable l2-profile-two";
             description "MAC: 224K L3-host: 80K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_3 {
           container l2-profile-three {
             presence "enable l2-profile-three";
             description "(default) MAC: 160K L3-host: 144K LPM: 16K, needs reboot for VC;restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_4 {
           container l3-profile {
             presence "enable l3-profile";
             description "MAC: 96K L3-host: 208K LPM: 16K EM:0, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_5 {
           container lpm-profile {
             presence "enable lpm-profile";
             description "MAC: 32K L3-host: 16K LPM: 128K EM:0, needs reboot for VC; restarts PFE if standalone";
             uses apply-advanced;
             leaf prefix-65-127-disable {
               description "Disable IPV6 prefixes with length > 64";
               type empty;
             }
             leaf unicast-in-lpm {
               description "Install unicast host entries in LPM table";
               type empty;
             }
           }
         }
         case case_6 {
           container exact-match-profile {
             presence "enable exact-match-profile";
             description "MAC: 8K L3-host: 8K LPM: 16K EM: 64K, needs reboot for VC; restarts PFE if standalone";
             uses apply-advanced;
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
         case case_7 {
           container vxlan-gbp-profile {
             presence "enable vxlan-gbp-profile";
             description "MAC: 48K L3-host: 48K LPM: 16K EM:32K, needs reboot for VC; restarts PFE if standalone";
           }
         }
         case case_8 {
           container vxlan-gbp-l2-profile {
             presence "enable vxlan-gbp-l2-profile";
             description "MAC: 64K L3-host: 32K LPM: 16K EM:16K, needs reboot for VC; restarts PFE if standalone";
           }
         }
         case case_9 {
           container vxlan-gbp-l3-profile {
             presence "enable vxlan-gbp-l3-profile";
             description "MAC: 32K L3-host: 64K LPM: 16K EM:16K, needs reboot for VC; restarts PFE if standalone";
           }
         }
         case case_10 {
           container em-hw-profile {
             presence "enable em-hw-profile";
             description "MAC: 48K L3-host: 48K LPM: 16K EM:32K, needs reboot for VC; restarts PFE if standalone";
           }
         }
         case case_11 {
           container default-profile {
             presence "enable default-profile";
             description "MAC: 64K L3-host: 32K LPM: 24K IFP: 12K, needs reboot for VC; restarts PFE if standalone";
           }
         }
         case case_12 {
           container ifp-profile {
             presence "enable ifp-profile";
             description "MAC: 64K L3-host: 32K LPM: 12K IFP: 18K, needs reboot for VC; restarts PFE if standalone";
           }
         }
         case case_13 {
           container custom-profile {
             description "(Partition the shared banks, will automatically restart the PFE when configured)";
             uses apply-advanced;
             container l2-entries {
               description "Customize l2 entries needed";
               uses apply-advanced;
               leaf num-banks {
                 description "Number of banks needed for entries of this type";
                 default "0";
                 type union {
                   type string {
                     pattern "<.*>|$.*";
                   }
                   type int32 {
                     range "0 .. 4";
                   }
                 }
               }
             }
             container l3-entries {
               description "Customize l3 entries needed";
               uses apply-advanced;
               leaf num-banks {
                 description "Number of banks needed for entries of this type";
                 default "0";
                 type union {
                   type string {
                     pattern "<.*>|$.*";
                   }
                   type int32 {
                     range "0 .. 4";
                   }
                 }
               }
             }
             container exact-match-entries {
               description "Customize exact match entries needed";
               uses apply-advanced;
               leaf num-banks {
                 description "Number of banks needed for entries of this type";
                 default "0";
                 type union {
                   type string {
                     pattern "<.*>|$.*";
                   }
                   type int32 {
                     range "0 .. 4";
                   }
                 }
               }
             }
             container lpm-entries {
               description "Customize lpm banks needed";
               uses apply-advanced;
               leaf num-banks {
                 description "Number of banks needed for entries of this type";
                 default "0";
                 type enumeration {
                   enum "0" {
                   }
                   enum "2" {
                   }
                   enum "4" {
                   }
                 }
               }
               leaf prefix-65-127-disable {
                 description "Disable IPV6 prefixes with length > 64";
                 type empty;
               }
             }
             leaf num-65-127-prefix {
               description "IPV6 prefixes > 64, in multiples of 1K e.g 3 = 3x1K entries(default 1)";
               default "1";
               type union {
                 type string {
                   pattern "<.*>|$.*";
                 }
                 type int32 {
                   range "0 .. 4";
                 }
               }
             }
           }
         }
       }
     }
     list pic {
       key name;
       description "Physical Interface Card number";
       uses chassis_pic_type;
     }
     container optical-options {
       description "Integrated Photonic Line Card settings";
       uses apply-advanced;
       choice disable-edfa-choice {
         leaf disable-edfa {
           description "Disable both EDFA";
           type empty;
         }
         leaf no-disable-edfa {
           description "Don't disable both EDFA";
           type empty;
         }
       }
       choice disable-osc-choice {
         leaf disable-osc {
           description "Disable OSC";
           type empty;
         }
         leaf no-disable-osc {
           description "Don't disable OSC";
           type empty;
         }
       }
       list wavelength {
         key name;
         description "Wavelength Selective Switch";
         leaf name {
           description "Wavelength of the WSS channel for 50Ghz/100Ghz spacing";
           type enumeration {
             enum "1568.77" {
               description "1568.77 nm/191.1003 THz 50/100Ghz spacing";
             }
             enum "1568.36" {
               description "1568.36 nm/191.15000 THz 6.25/12.5/50GHz spacing";
             }
             enum "1568.31" {
               description "1568.31 nm/191.15625 THz 6.25GHz spacing";
             }
             enum "1568.26" {
               description "1568.26 nm/191.16250 THz 6.25/12.5GHz spacing";
             }
             enum "1568.21" {
               description "1568.21 nm/191.16875 THz 6.25GHz spacing";
             }
             enum "1568.16" {
               description "1568.16 nm/191.17500 THz 6.25/12.5GHz spacing";
             }
             enum "1568.11" {
               description "1568.11 nm/191.18125 THz 6.25GHz spacing";
             }
             enum "1568.05" {
               description "1568.05 nm/191.18750 THz 6.25/12.5GHz spacing";
             }
             enum "1568.00" {
               description "1568.00 nm/191.19375 THz 6.25GHz spacing";
             }
             enum "1567.95" {
               description "1567.95 nm/191.20000 THz 6.25/12.5/50/100GHz spacing";
             }
             enum "1567.90" {
               description "1567.90 nm/191.20625 THz 6.25GHz spacing";
             }
             enum "1567.85" {
               description "1567.85 nm/191.21250 THz 6.25/12.5GHz spacing";
             }
             enum "1567.80" {
               description "1567.80 nm/191.21875 THz 6.25GHz spacing";
             }
             enum "1567.75" {
               description "1567.75 nm/191.22500 THz 6.25/12.5GHz spacing";
             }
             enum "1567.70" {
               description "1567.70 nm/191.23125 THz 6.25GHz spacing";
             }
             enum "1567.64" {
               description "1567.64 nm/191.23750 THz 6.25/12.5GHz spacing";
             }
             enum "1567.59" {
               description "1567.59 nm/191.24375 THz 6.25GHz spacing";
             }
             enum "1567.54" {
               description "1567.54 nm/191.25000 THz 6.25/12.5/50GHz spacing";
             }
             enum "1567.49" {
               description "1567.49 nm/191.25625 THz 6.25GHz spacing";
             }
             enum "1567.44" {
               description "1567.44 nm/191.26250 THz 6.25/12.5GHz spacing";
             }
             enum "1567.39" {
               description "1567.39 nm/191.26875 THz 6.25GHz spacing";
             }
             enum "1567.34" {
               description "1567.34 nm/191.27500 THz 6.25/12.5GHz spacing";
             }
             enum "1567.29" {
               description "1567.29 nm/191.28125 THz 6.25GHz spacing";
             }
             enum "1567.23" {
               description "1567.23 nm/191.28750 THz 6.25/12.5GHz spacing";
             }
             enum "1567.18" {
               description "1567.18 nm/191.29375 THz 6.25GHz spacing";
             }
             enum "1567.13" {
               description "1567.13 nm/191.30000 THz 6.25/12.5/50/100GHz spacing";
             }
             enum "1567.08" {
               description "1567.08 nm/191.30625 THz 6.25GHz spacing";
             }
             enum "1567.03" {
               description "1567.03 nm/191.31250 THz 6.25/12.5GHz spacing";
             }
             enum "1566.98" {
               description "1566.98 nm/191.31875 THz 6.25GHz spacing";
             }
             enum "1566.93" {
               description "1566.93 nm/191.32500 THz 6.25/12.5GHz spacing";
             }
             enum "1566.88" {
               description "1566.88 nm/191.33125 THz 6.25GHz spacing";
             }
             enum "1566.83" {
               description "1566.83 nm/191.33750 THz 6.25/12.5GHz spacing";
             }
             enum "1566.77" {
               description "1566.77 nm/191.34375 THz 6.25GHz spacing";
             }
             enum "1566.72" {
               description "1566.72 nm/191.35000 THz 6.25/12.5/50GHz spacing";
             }
             enum "1566.67" {
               description "1566.67 nm/191.35625 THz 6.25GHz spacing";
             }
             enum "1566.62" {
               description "1566.62 nm/191.36250 THz 6.25/12.5GHz spacing";
             }
             enum "1566.57" {
               description "1566.57 nm/191.36875 THz 6.25GHz spacing";
             }
             enum "1566.52" {
               description "1566.52 nm/191.37500 THz 6.25/12.5/75GHz spacing";
             }
             enum "1566.47" {
               description "1566.47 nm/191.38125 THz 6.25GHz spacing";
             }
             enum "1566.42" {
               description "1566.42 nm/191.38750 THz 6.25/12.5GHz spacing";
             }
             enum "1566.36" {
               description "1566.36 nm/191.39375 THz 6.25GHz spacing";
             }
             enum "1566.31" {
               description "1566.31 nm/191.40000 THz 6.25/12.5/50/100GHz spacing";
             }
             enum "1566.26" {
               description "1566.26 nm/191.40625 THz 6.25GHz spacing";
             }
             enum "1566.21" {
               description "1566.21 nm/191.41250 THz 6.25/12.5GHz spacing";
             }
             enum "1566.16" {
               description "1566.16 nm/191.41875 THz 6.25GHz spacing";
             }
             enum "1566.11" {
               description "1566.11 nm/191.42500 THz 6.25/12.5GHz spacing";
             }
             enum "1566.06" {
               description "1566.06 nm/191.43125 THz 6.25GHz spacing";
             }
             enum "1566.01" {
               description "1566.01 nm/191.43750 THz 6.25/12.5GHz spacing";
             }
             enum "1565.96" {
               description "1565.96 nm/191.44375 THz 6.25GHz spacing";
             }
             enum "1565.90" {
               description "1565.90 nm/191.45000 THz 6.25/12.5/50/75GHz spacing";
             }
             enum "1565.85" {
               description "1565.85 nm/191.45625 THz 6.25GHz spacing";
             }
             enum "1565.80" {
               description "1565.80 nm/191.46250 THz 6.25/12.5GHz spacing";
             }
             enum "1565.75" {
               description "1565.75 nm/191.46875 THz 6.25GHz spacing";
             }
             enum "1565.70" {
               description "1565.70 nm/191.47500 THz 6.25/12.5GHz spacing";
             }
             enum "1565.65" {
               description "1565.65 nm/191.48125 THz 6.25GHz spacing";
             }
             enum "1565.60" {
               description "1565.60 nm/191.48750 THz 6.25/12.5GHz spacing";
             }
             enum "1565.55" {
               description "1565.55 nm/191.49375 THz 6.25GHz spacing";
             }
             enum "1565.50" {
               description "1565.50 nm/191.50000 THz 6.25/12.5/50/100GHz spacing";
             }
             enum "1565.44" {
               description "1565.44 nm/191.50625 THz 6.25GHz spacing";
             }
             enum "1565.39" {
               description "1565.39 nm/191.51250 THz 6.25/12.5GHz spacing";
             }
             enum "1565.34" {
               description "1565.34 nm/191.51875 THz 6.25GHz spacing";
             }
             enum "1565.29" {
               description "1565.29 nm/191.52500 THz 6.25/12.5/75GHz spacing";
             }
             enum "1565.24" {
               description "1565.24 nm/191.53125 THz 6.25GHz spacing";
             }
             enum "1565.19" {
               description "1565.19 nm/191.53750 THz 6.25/12.5GHz spacing";
             }
             enum "1565.14" {
               description "1565.14 nm/191.54375 THz 6.25GHz spacing";
             }
             enum "1565.09" {
               description "1565.09 nm/191.55000 THz 6.25/12.5/50GHz spacing";
             }
             enum "1565.04" {
               description "1565.04 nm/191.55625 THz 6.25GHz spacing";
             }
             enum "1564.99" {
               description "1564.99 nm/191.56250 THz 6.25/12.5GHz spacing";
             }
             enum "1564.93" {
               description "1564.93 nm/191.56875 THz 6.25GHz spacing";
             }
             enum "1564.88" {
               description "1564.88 nm/191.57500 THz 6.25/12.5GHz spacing";
             }
             enum "1564.83" {
               description "1564.83 nm/191.58125 THz 6.25GHz spacing";
             }
             enum "1564.78" {
               description "1564.78 nm/191.58750 THz 6.25/12.5GHz spacing";
             }
             enum "1564.73" {
               description "1564.73 nm/191.59375 THz 6.25GHz spacing";
             }
             enum "1564.68" {
               description "1564.68 nm/191.60000 THz 6.25/12.5/50/75/100GHz spacing";
             }
             enum "1564.63" {
               description "1564.63 nm/191.60625 THz 6.25GHz spacing";
             }
             enum "1564.58" {
               description "1564.58 nm/191.61250 THz 6.25/12.5GHz spacing";
             }
             enum "1564.53" {
               description "1564.53 nm/191.61875 THz 6.25GHz spacing";
             }
             enum "1564.47" {
               description "1564.47 nm/191.62500 THz 6.25/12.5GHz spacing";
             }
             enum "1564.42" {
               description "1564.42 nm/191.63125 THz 6.25GHz spacing";
             }
             enum "1564.37" {
               description "1564.37 nm/191.63750 THz 6.25/12.5GHz spacing";
             }
             enum "1564.32" {
               description "1564.32 nm/191.64375 THz 6.25GHz spacing";
             }
             enum "1564.27" {
               description "1564.27 nm/191.65000 THz 6.25/12.5/50GHz spacing";
             }
             enum "1564.22" {
               description "1564.22 nm/191.65625 THz 6.25GHz spacing";
             }
             enum "1564.17" {
               description "1564.17 nm/191.66250 THz 6.25/12.5GHz spacing";
             }
             enum "1564.12" {
               description "1564.12 nm/191.66875 THz 6.25GHz spacing";
             }
             enum "1564.07" {
               description "1564.07 nm/191.67500 THz 6.25/12.5/75GHz spacing";
             }
             enum "1564.02" {
               description "1564.02 nm/191.68125 THz 6.25GHz spacing";
             }
             enum "1563.96" {
               description "1563.96 nm/191.68750 THz 6.25/12.5GHz spacing";
             }
             enum "1563.91" {
               description "1563.91 nm/191.69375 THz 6.25GHz spacing";
             }
             enum "1563.86" {
               description "1563.86 nm/191.70000 THz 6.25/12.5/50/100GHz spacing";
             }
             enum "1563.81" {
               description "1563.81 nm/191.70625 THz 6.25GHz spacing";
             }
             enum "1563.76" {
               description "1563.76 nm/191.71250 THz 6.25/12.5GHz spacing";
             }
             enum "1563.71" {
               description "1563.71 nm/191.71875 THz 6.25GHz spacing";
             }
             enum "1563.66" {
               description "1563.66 nm/191.72500 THz 6.25/12.5GHz spacing";
             }
             enum "1563.61" {
               description "1563.61 nm/191.73125 THz 6.25GHz spacing";
             }
             enum "1563.56" {
               description "1563.56 nm/191.73750 THz 6.25/12.5GHz spacing";
             }
             enum "1563.51" {
               description "1563.51 nm/191.74375 THz 6.25GHz spacing";
             }
             enum "1563.45" {
               description "1563.45 nm/191.75000 THz 6.25/12.5/50/75GHz spacing";
             }
             enum "1563.40" {
               description "1563.40 nm/191.75625 THz 6.25GHz spacing";
             }
             enum "1563.35" {
               description "1563.35 nm/191.76250 THz 6.25/12.5GHz spacing";
             }
             enum "1563.30" {
               description "1563.30 nm/191.76875 THz 6.25GHz spacing";
             }
             enum "1563.25" {
               description "1563.25 nm/191.77500 THz 6.25/12.5GHz spacing";
             }
             enum "1563.20" {
               description "1563.20 nm/191.78125 THz 6.25GHz spacing";
             }
             enum "1563.15" {
               description "1563.15 nm/191.78750 THz 6.25/12.5GHz spacing";
             }
             enum "1563.10" {
               description "1563.10 nm/191.79375 THz 6.25GHz spacing";
             }
             enum "1563.05" {
               description "1563.05 nm/191.80000 THz 6.25/12.5/50/100GHz spacing";
             }
             enum "1563.00" {
               description "1563.00 nm/191.80625 THz 6.25GHz spacing";
             }
             enum "1562.95" {
               description "1562.95 nm/191.81250 THz 6.25/12.5GHz spacing";
             }
             enum "1562.89" {
               description "1562.89 nm/191.81875 THz 6.25GHz spacing";
             }
             enum "1562.84" {
               description "1562.84 nm/191.82500 THz 6.25/12.5/75GHz spacing";
             }
             enum "1562.79" {
               description "1562.79 nm/191.83125 THz 6.25GHz spacing";
             }
             enum "1562.74" {
               description "1562.74 nm/191.83750 THz 6.25/12.5GHz spacing";
             }
             enum "1562.69" {
               description "1562.69 nm/191.84375 THz 6.25GHz spacing";
             }
             enum "1562.64" {
               description "1562.64 nm/191.85000 THz 6.25/12.5/50GHz spacing";
             }
             enum "1562.59" {
               description "1562.59 nm/191.85625 THz 6.25GHz spacing";
             }
             enum "1562.54" {
               description "1562.54 nm/191.86250 THz 6.25/12.5GHz spacing";
             }
             enum "1562.49" {
               description "1562.49 nm/191.86875 THz 6.25GHz spacing";
             }
             enum "1562.44" {
               description "1562.44 nm/191.87500 THz 6.25/12.5GHz spacing";
             }
             enum "1562.39" {
               description "1562.39 nm/191.88125 THz 6.25GHz spacing";
             }
             enum "1562.33" {
               description "1562.33 nm/191.88750 THz 6.25/12.5GHz spacing";
             }
             enum "1562.28" {
               description "1562.28 nm/191.89375 THz 6.25GHz spacing";
             }
             enum "1562.23" {
               description "1562.23 nm/191.90000 THz 6.25/12.5/50/75/100GHz spacing";
             }
             enum "1562.18" {
               description "1562.18 nm/191.90625 THz 6.25GHz spacing";
             }
             enum "1562.13" {
               description "1562.13 nm/191.91250 THz 6.25/12.5GHz spacing";
             }
             enum "1562.08" {
               description "1562.08 nm/191.91875 THz 6.25GHz spacing";
             }
             enum "1562.03" {
               description "1562.03 nm/191.92500 THz 6.25/12.5GHz spacing";
             }
             enum "1561.98" {
               description "1561.98 nm/191.93125 THz 6.25GHz spacing";
             }
             enum "1561.93" {
               description "1561.93 nm/191.93750 THz 6.25/12.5GHz spacing";
             }
             enum "1561.88" {
               description "1561.88 nm/191.94375 THz 6.25GHz spacing";
             }
             enum "1561.83" {
               description "1561.83 nm/191.95000 THz 6.25/12.5/50GHz spacing";
             }
             enum "1561.77" {
               description "1561.77 nm/191.95625 THz 6.25GHz spacing";
             }
             enum "1561.72" {
               description "1561.72 nm/191.96250 THz 6.25/12.5GHz spacing";
             }
             enum "1561.67" {
               description "1561.67 nm/191.96875 THz 6.25GHz spacing";
             }
             enum "1561.62" {
               description "1561.62 nm/191.97500 THz 6.25/12.5/75GHz spacing";
             }
             enum "1561.57" {
               description "1561.57 nm/191.98125 THz 6.25GHz spacing";
             }
             enum "1561.52" {
               description "1561.52 nm/191.98750 THz 6.25/12.5GHz spacing";
             }
             enum "1561.47" {
               description "1561.47 nm/191.99375 THz 6.25GHz spacing";
             }
             enum "1561.42" {
               description "1561.42 nm/192.00000 THz 6.25/12.5/50/100GHz spacing";
             }
             enum "1561.37" {
               description "1561.37 nm/192.00625 THz 6.25GHz spacing";
             }
             enum "1561.32" {
               description "1561.32 nm/192.01250 THz 6.25/12.5GHz spacing";
             }
             enum "1561.27" {
               description "1561.27 nm/192.01875 THz 6.25GHz spacing";
             }
             enum "1561.22" {
               description "1561.22 nm/192.02500 THz 6.25/12.5GHz spacing";
             }
             enum "1561.16" {
               description "1561.16 nm/192.03125 THz 6.25GHz spacing";
             }
             enum "1561.11" {
               description "1561.11 nm/192.03750 THz 6.25/12.5GHz spacing";
             }
             enum "1561.06" {
               description "1561.06 nm/192.04375 THz 6.25GHz spacing";
             }
             enum "1561.01" {
               description "1561.01 nm/192.05000 THz 6.25/12.5/50G/75Hz spacing";
             }
             enum "1560.96" {
               description "1560.96 nm/192.05625 THz 6.25GHz spacing";
             }
             enum "1560.91" {
               description "1560.91 nm/192.06250 THz 6.25/12.5GHz spacing";
             }
             enum "1560.86" {
               description "1560.86 nm/192.06875 THz 6.25GHz spacing";
             }
             enum "1560.81" {
               description "1560.81 nm/192.07500 THz 6.25/12.5GHz spacing";
             }
             enum "1560.76" {
               description "1560.76 nm/192.08125 THz 6.25GHz spacing";
             }
             enum "1560.71" {
               description "1560.71 nm/192.08750 THz 6.25/12.5GHz spacing";
             }
             enum "1560.66" {
               description "1560.66 nm/192.09375 THz 6.25GHz spacing";
             }
             enum "1560.61" {
               description "1560.61 nm/192.10000 THz 6.25/12.5/50/100GHz spacing";
             }
             enum "1560.56" {
               description "1560.56 nm/192.10625 THz 6.25GHz spacing";
             }
             enum "1560.50" {
               description "1560.50 nm/192.11250 THz 6.25/12.5GHz spacing";
             }
             enum "1560.45" {
               description "1560.45 nm/192.11875 THz 6.25GHz spacing";
             }
             enum "1560.40" {
               description "1560.40 nm/192.12500 THz 6.25/12.5/75GHz spacing";
             }
             enum "1560.35" {
               description "1560.35 nm/192.13125 THz 6.25GHz spacing";
             }
             enum "1560.30" {
               description "1560.30 nm/192.13750 THz 6.25/12.5GHz spacing";
             }
             enum "1560.25" {
               description "1560.25 nm/192.14375 THz 6.25GHz spacing";
             }
             enum "1560.20" {
               description "1560.20 nm/192.15000 THz 6.25/12.5/50GHz spacing";
             }
             enum "1560.15" {
               description "1560.15 nm/192.15625 THz 6.25GHz spacing";
             }
             enum "1560.10" {
               description "1560.10 nm/192.16250 THz 6.25/12.5GHz spacing";
             }
             enum "1560.05" {
               description "1560.05 nm/192.16875 THz 6.25GHz spacing";
             }
             enum "1560.00" {
               description "1560.00 nm/192.17500 THz 6.25/12.5GHz spacing";
             }
             enum "1559.95" {
               description "1559.95 nm/192.18125 THz 6.25GHz spacing";
             }
             enum "1559.90" {
               description "1559.90 nm/192.18750 THz 6.25/12.5GHz spacing";
             }
             enum "1559.84" {
               description "1559.84 nm/192.19375 THz 6.25GHz spacing";
             }
             enum "1559.79" {
               description "1559.79 nm/192.20000 THz 6.25/12.5/50/75/100GHz spacing";
             }
             enum "1559.74" {
               description "1559.74 nm/192.20625 THz 6.25GHz spacing";
             }
             enum "1559.69" {
               description "1559.69 nm/192.21250 THz 6.25/12.5GHz spacing";
             }
             enum "1559.64" {
               description "1559.64 nm/192.21875 THz 6.25GHz spacing";
             }
             enum "1559.59" {
               description "1559.59 nm/192.22500 THz 6.25/12.5GHz spacing";
             }
             enum "1559.54" {
               description "1559.54 nm/192.23125 THz 6.25GHz spacing";
             }
             enum "1559.49" {
               description "1559.49 nm/192.23750 THz 6.25/12.5GHz spacing";
             }
             enum "1559.44" {
               description "1559.44 nm/192.24375 THz 6.25GHz spacing";
             }
             enum "1559.39" {
               description "1559.39 nm/192.25000 THz 6.25/12.5/50GHz spacing";
             }
             enum "1559.34" {
               description "1559.34 nm/192.25625 THz 6.25GHz spacing";
             }
             enum "1559.29" {
               description "1559.29 nm/192.26250 THz 6.25/12.5GHz spacing";
             }
             enum "1559.24" {
               description "1559.24 nm/192.26875 THz 6.25GHz spacing";
             }
             enum "1559.19" {
               description "1559.19 nm/192.27500 THz 6.25/12.5/75GHz spacing";
             }
             enum "1559.14" {
               description "1559.14 nm/192.28125 THz 6.25GHz spacing";
             }
             enum "1559.08" {
               description "1559.08 nm/192.28750 THz 6.25/12.5GHz spacing";
             }
             enum "1559.03" {
               description "1559.03 nm/192.29375 THz 6.25GHz spacing";
             }
             enum "1558.98" {
               description "1558.98 nm/192.30000 THz 6.25/12.5/50/100GHz spacing";
             }
             enum "1558.93" {
               description "1558.93 nm/192.30625 THz 6.25GHz spacing";
             }
             enum "1558.88" {
               description "1558.88 nm/192.31250 THz 6.25/12.5GHz spacing";
             }
             enum "1558.83" {
               description "1558.83 nm/192.31875 THz 6.25GHz spacing";
             }
             enum "1558.78" {
               description "1558.78 nm/192.32500 THz 6.25/12.5GHz spacing";
             }
             enum "1558.73" {
               description "1558.73 nm/192.33125 THz 6.25GHz spacing";
             }
             enum "1558.68" {
               description "1558.68 nm/192.33750 THz 6.25/12.5GHz spacing";
             }
             enum "1558.63" {
               description "1558.63 nm/192.34375 THz 6.25GHz spacing";
             }
             enum "1558.58" {
               description "1558.58 nm/192.35000 THz 6.25/12.5/50/75GHz spacing";
             }
             enum "1558.53" {
               description "1558.53 nm/192.35625 THz 6.25GHz spacing";
             }
             enum "1558.48" {
               description "1558.48 nm/192.36250 THz 6.25/12.5GHz spacing";
             }
             enum "1558.43" {
               description "1558.43 nm/192.36875 THz 6.25GHz spacing";
             }
             enum "1558.38" {
               description "1558.38 nm/192.37500 THz 6.25/12.5GHz spacing";
             }
             enum "1558.32" {
               description "1558.32 nm/192.38125 THz 6.25GHz spacing";
             }
             enum "1558.27" {
               description "1558.27 nm/192.38750 THz 6.25/12.5GHz spacing";
             }
             enum "1558.22" {
               description "1558.22 nm/192.39375 THz 6.25GHz spacing";
             }
             enum "1558.17" {
               description "1558.17 nm/192.40000 THz 6.25/12.5/50/100GHz spacing";
             }
             enum "1558.12" {
               description "1558.12 nm/192.40625 THz 6.25GHz spacing";
             }
             enum "1558.07" {
               description "1558.07 nm/192.41250 THz 6.25/12.5GHz spacing";
             }
             enum "1558.02" {
               description "1558.02 nm/192.41875 THz 6.25GHz spacing";
             }
             enum "1557.97" {
               description "1557.97 nm/192.42500 THz 6.25/12.5/75GHz spacing";
             }
             enum "1557.92" {
               description "1557.92 nm/192.43125 THz 6.25GHz spacing";
             }
             enum "1557.87" {
               description "1557.87 nm/192.43750 THz 6.25/12.5GHz spacing";
             }
             enum "1557.82" {
               description "1557.82 nm/192.44375 THz 6.25GHz spacing";
             }
             enum "1557.77" {
               description "1557.77 nm/192.45000 THz 6.25/12.5/50GHz spacing";
             }
             enum "1557.72" {
               description "1557.72 nm/192.45625 THz 6.25GHz spacing";
             }
             enum "1557.67" {
               description "1557.67 nm/192.46250 THz 6.25/12.5GHz spacing";
             }
             enum "1557.62" {
               description "1557.62 nm/192.46875 THz 6.25GHz spacing";
             }
             enum "1557.57" {
               description "1557.57 nm/192.47500 THz 6.25/12.5GHz spacing";
             }
             enum "1557.52" {
               description "1557.52 nm/192.48125 THz 6.25GHz spacing";
             }
             enum "1557.46" {
               description "1557.46 nm/192.48750 THz 6.25/12.5GHz spacing";
             }
             enum "1557.41" {
               description "1557.41 nm/192.49375 THz 6.25GHz spacing";
             }
             enum "1557.36" {
               description "1557.36 nm/192.50000 THz 6.25/12.5/50/75/100GHz spacing";
             }
             enum "1557.31" {
               description "1557.31 nm/192.50625 THz 6.25GHz spacing";
             }
             enum "1557.26" {
               description "1557.26 nm/192.51250 THz 6.25/12.5GHz spacing";
             }
             enum "1557.21" {
               description "1557.21 nm/192.51875 THz 6.25GHz spacing";
             }
             enum "1557.16" {
               description "1557.16 nm/192.52500 THz 6.25/12.5GHz spacing";
             }
             enum "1557.11" {
               description "1557.11 nm/192.53125 THz 6.25GHz spacing";
             }
             enum "1557.06" {
               description "1557.06 nm/192.53750 THz 6.25/12.5GHz spacing";
             }
             enum "1557.01" {
               description "1557.01 nm/192.54375 THz 6.25GHz spacing";
             }
             enum "1556.96" {
               description "1556.96 nm/192.55000 THz 6.25/12.5/50GHz spacing";
             }
             enum "1556.91" {
               description "1556.91 nm/192.55625 THz 6.25GHz spacing";
             }
             enum "1556.86" {
               description "1556.86 nm/192.56250 THz 6.25/12.5GHz spacing";
             }
             enum "1556.81" {
               description "1556.81 nm/192.56875 THz 6.25GHz spacing";
             }
             enum "1556.76" {
               description "1556.76 nm/192.57500 THz 6.25/12.5/75GHz spacing";
             }
             enum "1556.71" {
               description "1556.71 nm/192.58125 THz 6.25GHz spacing";
             }
             enum "1556.66" {
               description "1556.66 nm/192.58750 THz 6.25/12.5GHz spacing";
             }
             enum "1556.61" {
               description "1556.61 nm/192.59375 THz 6.25GHz spacing";
             }
             enum "1556.55" {
               description "1556.55 nm/192.60000 THz 6.25/12.5/50/100GHz spacing";
             }
             enum "1556.50" {
               description "1556.50 nm/192.60625 THz 6.25GHz spacing";
             }
             enum "1556.45" {
               description "1556.45 nm/192.61250 THz 6.25/12.5GHz spacing";
             }
             enum "1556.40" {
               description "1556.40 nm/192.61875 THz 6.25GHz spacing";
             }
             enum "1556.35" {
               description "1556.35 nm/192.62500 THz 6.25/12.5GHz spacing";
             }
             enum "1556.30" {
               description "1556.30 nm/192.63125 THz 6.25GHz spacing";
             }
             enum "1556.25" {
               description "1556.25 nm/192.63750 THz 6.25/12.5GHz spacing";
             }
             enum "1556.20" {
               description "1556.20 nm/192.64375 THz 6.25GHz spacing";
             }
             enum "1556.15" {
               description "1556.15 nm/192.65000 THz 6.25/12.5/50/75GHz spacing";
             }
             enum "1556.10" {
               description "1556.10 nm/192.65625 THz 6.25GHz spacing";
             }
             enum "1556.05" {
               description "1556.05 nm/192.66250 THz 6.25/12.5GHz spacing";
             }
             enum "1556.00" {
               description "1556.00 nm/192.66875 THz 6.25GHz spacing";
             }
             enum "1555.95" {
               description "1555.95 nm/192.67500 THz 6.25/12.5GHz spacing";
             }
             enum "1555.90" {
               description "1555.90 nm/192.68125 THz 6.25GHz spacing";
             }
             enum "1555.85" {
               description "1555.85 nm/192.68750 THz 6.25/12.5GHz spacing";
             }
             enum "1555.80" {
               description "1555.80 nm/192.69375 THz 6.25GHz spacing";
             }
             enum "1555.75" {
               description "1555.75 nm/192.70000 THz 6.25/12.5/50/100GHz spacing";
             }
             enum "1555.70" {
               description "1555.70 nm/192.70625 THz 6.25GHz spacing";
             }
             enum "1555.65" {
               description "1555.65 nm/192.71250 THz 6.25/12.5GHz spacing";
             }
             enum "1555.60" {
               description "1555.60 nm/192.71875 THz 6.25GHz spacing";
             }
             enum "1555.55" {
               description "1555.55 nm/192.72500 THz 6.25/12.5/75GHz spacing";
             }
             enum "1555.49" {
               description "1555.49 nm/192.73125 THz 6.25GHz spacing";
             }
             enum "1555.44" {
               description "1555.44 nm/192.73750 THz 6.25/12.5GHz spacing";
             }
             enum "1555.39" {
               description "1555.39 nm/192.74375 THz 6.25GHz spacing";
             }
             enum "1555.34" {
               description "1555.34 nm/192.75000 THz 6.25/12.5/50GHz spacing";
             }
             enum "1555.29" {
               description "1555.29 nm/192.75625 THz 6.25GHz spacing";
             }
             enum "1555.24" {
               description "1555.24 nm/192.76250 THz 6.25/12.5GHz spacing";
             }
             enum "1555.19" {
               description "1555.19 nm/192.76875 THz 6.25GHz spacing";
             }
             enum "1555.14" {
               description "1555.14 nm/192.77500 THz 6.25/12.5GHz spacing";
             }
             enum "1555.09" {
               description "1555.09 nm/192.78125 THz 6.25GHz spacing";
             }
             enum "1555.04" {
               description "1555.04 nm/192.78750 THz 6.25/12.5GHz spacing";
             }
             enum "1554.99" {
               description "1554.99 nm/192.79375 THz 6.25GHz spacing";
             }
             enum "1554.94" {
               description "1554.94 nm/192.80000 THz 6.25/12.5/50/75/100GHz spacing";
             }
             enum "1554.89" {
               description "1554.89 nm/192.80625 THz 6.25GHz spacing";
             }
             enum "1554.84" {
               description "1554.84 nm/192.81250 THz 6.25/12.5GHz spacing";
             }
             enum "1554.79" {
               description "1554.79 nm/192.81875 THz 6.25GHz spacing";
             }
             enum "1554.74" {
               description "1554.74 nm/192.82500 THz 6.25/12.5GHz spacing";
             }
             enum "1554.69" {
               description "1554.69 nm/192.83125 THz 6.25GHz spacing";
             }
             enum "1554.64" {
               description "1554.64 nm/192.83750 THz 6.25/12.5GHz spacing";
             }
             enum "1554.59" {
               description "1554.59 nm/192.84375 THz 6.25GHz spacing";
             }
             enum "1554.54" {
               description "1554.54 nm/192.85000 THz 6.25/12.5/50GHz spacing";
             }
             enum "1554.49" {
               description "1554.49 nm/192.85625 THz 6.25GHz spacing";
             }
             enum "1554.44" {
               description "1554.44 nm/192.86250 THz 6.25/12.5GHz spacing";
             }
             enum "1554.39" {
               description "1554.39 nm/192.86875 THz 6.25GHz spacing";
             }
             enum "1554.34" {
               description "1554.34 nm/192.87500 THz 6.25/12.5/75GHz spacing";
             }
             enum "1554.29" {
               description "1554.29 nm/192.88125 THz 6.25GHz spacing";
             }
             enum "1554.23" {
               description "1554.23 nm/192.88750 THz 6.25/12.5GHz spacing";
             }
             enum "1554.18" {
               description "1554.18 nm/192.89375 THz 6.25GHz spacing";
             }
             enum "1554.13" {
               description "1554.13 nm/192.90000 THz 6.25/12.5/50/100GHz spacing";
             }
             enum "1554.08" {
               description "1554.08 nm/192.90625 THz 6.25GHz spacing";
             }
             enum "1554.03" {
               description "1554.03 nm/192.91250 THz 6.25/12.5GHz spacing";
             }
             enum "1553.98" {
               description "1553.98 nm/192.91875 THz 6.25GHz spacing";
             }
             enum "1553.93" {
               description "1553.93 nm/192.92500 THz 6.25/12.5GHz spacing";
             }
             enum "1553.88" {
               description "1553.88 nm/192.93125 THz 6.25GHz spacing";
             }
             enum "1553.83" {
               description "1553.83 nm/192.93750 THz 6.25/12.5GHz spacing";
             }
             enum "1553.78" {
               description "1553.78 nm/192.94375 THz 6.25GHz spacing";
             }
             enum "1553.73" {
               description "1553.73 nm/192.95000 THz 6.25/12.5/50/75GHz spacing";
             }
             enum "1553.68" {
               description "1553.68 nm/192.95625 THz 6.25GHz spacing";
             }
             enum "1553.63" {
               description "1553.63 nm/192.96250 THz 6.25/12.5GHz spacing";
             }
             enum "1553.58" {
               description "1553.58 nm/192.96875 THz 6.25GHz spacing";
             }
             enum "1553.53" {
               description "1553.53 nm/192.97500 THz 6.25/12.5GHz spacing";
             }
             enum "1553.48" {
               description "1553.48 nm/192.98125 THz 6.25GHz spacing";
             }
             enum "1553.43" {
               description "1553.43 nm/192.98750 THz 6.25/12.5GHz spacing";
             }
             enum "1553.38" {
               description "1553.38 nm/192.99375 THz 6.25GHz spacing";
             }
             enum "1553.33" {
               description "1553.33 nm/193.00000 THz 6.25/12.5/50/100GHz spacing";
             }
             enum "1553.28" {
               description "1553.28 nm/193.00625 THz 6.25GHz spacing";
             }
             enum "1553.23" {
               description "1553.23 nm/193.01250 THz 6.25/12.5GHz spacing";
             }
             enum "1553.18" {
               description "1553.18 nm/193.01875 THz 6.25GHz spacing";
             }
             enum "1553.13" {
               description "1553.13 nm/193.02500 THz 6.25/12.5/75GHz spacing";
             }
             enum "1553.08" {
               description "1553.08 nm/193.03125 THz 6.25GHz spacing";
             }
             enum "1553.03" {
               description "1553.03 nm/193.03750 THz 6.25/12.5GHz spacing";
             }
             enum "1552.98" {
               description "1552.98 nm/193.04375 THz 6.25GHz spacing";
             }
             enum "1552.93" {
               description "1552.93 nm/193.05000 THz 6.25/12.5/50GHz spacing";
             }
             enum "1552.88" {
               description "1552.88 nm/193.05625 THz 6.25GHz spacing";
             }
             enum "1552.83" {
               description "1552.83 nm/193.06250 THz 6.25/12.5GHz spacing";
             }
             enum "1552.78" {
               description "1552.78 nm/193.06875 THz 6.25GHz spacing";
             }
             enum "1552.73" {
               description "1552.73 nm/193.07500 THz 6.25/12.5GHz spacing";
             }
             enum "1552.68" {
               description "1552.68 nm/193.08125 THz 6.25GHz spacing";
             }
             enum "1552.62" {
               description "1552.62 nm/193.08750 THz 6.25/12.5GHz spacing";
             }
             enum "1552.57" {
               description "1552.57 nm/193.09375 THz 6.25GHz spacing";
             }
             enum "1552.52" {
               description "1552.52 nm/193.10000 THz 6.25/12.5/50/75/100GHz spacing";
             }
             enum "1552.47" {
               description "1552.47 nm/193.10625 THz 6.25GHz spacing";
             }
             enum "1552.42" {
               description "1552.42 nm/193.11250 THz 6.25/12.5GHz spacing";
             }
             enum "1552.37" {
               description "1552.37 nm/193.11875 THz 6.25GHz spacing";
             }
             enum "1552.32" {
               description "1552.32 nm/193.12500 THz 6.25/12.5GHz spacing";
             }
             enum "1552.27" {
               description "1552.27 nm/193.13125 THz 6.25GHz spacing";
             }
             enum "1552.22" {
               description "1552.22 nm/193.13750 THz 6.25/12.5GHz spacing";
             }
             enum "1552.17" {
               description "1552.17 nm/193.14375 THz 6.25GHz spacing";
             }
             enum "1552.12" {
               description "1552.12 nm/193.15000 THz 6.25/12.5/50GHz spacing";
             }
             enum "1552.07" {
               description "1552.07 nm/193.15625 THz 6.25GHz spacing";
             }
             enum "1552.02" {
               description "1552.02 nm/193.16250 THz 6.25/12.5GHz spacing";
             }
             enum "1551.97" {
               description "1551.97 nm/193.16875 THz 6.25GHz spacing";
             }
             enum "1551.92" {
               description "1551.92 nm/193.17500 THz 6.25/12.5/75GHz spacing";
             }
             enum "1551.87" {
               description "1551.87 nm/193.18125 THz 6.25GHz spacing";
             }
             enum "1551.82" {
               description "1551.82 nm/193.18750 THz 6.25/12.5GHz spacing";
             }
             enum "1551.77" {
               description "1551.77 nm/193.19375 THz 6.25GHz spacing";
             }
             enum "1551.72" {
               description "1551.72 nm/193.20000 THz 6.25/12.5/50/100GHz spacing";
             }
             enum "1551.67" {
               description "1551.67 nm/193.20625 THz 6.25GHz spacing";
             }
             enum "1551.62" {
               description "1551.62 nm/193.21250 THz 6.25/12.5GHz spacing";
             }
             enum "1551.57" {
               description "1551.57 nm/193.21875 THz 6.25GHz spacing";
             }
             enum "1551.52" {
               description "1551.52 nm/193.22500 THz 6.25/12.5GHz spacing";
             }
             enum "1551.47" {
               description "1551.47 nm/193.23125 THz 6.25GHz spacing";
             }
             enum "1551.42" {
               description "1551.42 nm/193.23750 THz 6.25/12.5GHz spacing";
             }
             enum "1551.37" {
               description "1551.37 nm/193.24375 THz 6.25GHz spacing";
             }
             enum "1551.32" {
               description "1551.32 nm/193.25000 THz 6.25/12.5/50/75GHz spacing";
             }
             enum "1551.27" {
               description "1551.27 nm/193.25625 THz 6.25GHz spacing";
             }
             enum "1551.22" {
               description "1551.22 nm/193.26250 THz 6.25/12.5GHz spacing";
             }
             enum "1551.17" {
               description "1551.17 nm/193.26875 THz 6.25GHz spacing";
             }
             enum "1551.12" {
               description "1551.12 nm/193.27500 THz 6.25/12.5GHz spacing";
             }
             enum "1551.07" {
               description "1551.07 nm/193.28125 THz 6.25GHz spacing";
             }
             enum "1551.02" {
               description "1551.02 nm/193.28750 THz 6.25/12.5GHz spacing";
             }
             enum "1550.97" {
               description "1550.97 nm/193.29375 THz 6.25GHz spacing";
             }
             enum "1550.92" {
               description "1550.92 nm/193.30000 THz 6.25/12.5/50/100GHz spacing";
             }
             enum "1550.87" {
               description "1550.87 nm/193.30625 THz 6.25GHz spacing";
             }
             enum "1550.82" {
               description "1550.82 nm/193.31250 THz 6.25/12.5GHz spacing";
             }
             enum "1550.77" {
               description "1550.77 nm/193.31875 THz 6.25GHz spacing";
             }
             enum "1550.72" {
               description "1550.72 nm/193.32500 THz 6.25/12.5/75GHz spacing";
             }
             enum "1550.67" {
               description "1550.67 nm/193.33125 THz 6.25GHz spacing";
             }
             enum "1550.62" {
               description "1550.62 nm/193.33750 THz 6.25/12.5GHz spacing";
             }
             enum "1550.57" {
               description "1550.57 nm/193.34375 THz 6.25GHz spacing";
             }
             enum "1550.52" {
               description "1550.52 nm/193.35000 THz 6.25/12.5/50GHz spacing";
             }
             enum "1550.47" {
               description "1550.47 nm/193.35625 THz 6.25GHz spacing";
             }
             enum "1550.42" {
               description "1550.42 nm/193.36250 THz 6.25/12.5GHz spacing";
             }
             enum "1550.37" {
               description "1550.37 nm/193.36875 THz 6.25GHz spacing";
             }
             enum "1550.32" {
               description "1550.32 nm/193.37500 THz 6.25/12.5GHz spacing";
             }
             enum "1550.27" {
               description "1550.27 nm/193.38125 THz 6.25GHz spacing";
             }
             enum "1550.22" {
               description "1550.22 nm/193.38750 THz 6.25/12.5GHz spacing";
             }
             enum "1550.17" {
               description "1550.17 nm/193.39375 THz 6.25GHz spacing";
             }
             enum "1550.12" {
               description "1550.12 nm/193.40000 THz 6.25/12.5/50/75/100GHz spacing";
             }
             enum "1550.07" {
               description "1550.07 nm/193.40625 THz 6.25GHz spacing";
             }
             enum "1550.02" {
               description "1550.02 nm/193.41250 THz 6.25/12.5GHz spacing";
             }
             enum "1549.97" {
               description "1549.97 nm/193.41875 THz 6.25GHz spacing";
             }
             enum "1549.92" {
               description "1549.92 nm/193.42500 THz 6.25/12.5GHz spacing";
             }
             enum "1549.87" {
               description "1549.87 nm/193.43125 THz 6.25GHz spacing";
             }
             enum "1549.82" {
               description "1549.82 nm/193.43750 THz 6.25/12.5GHz spacing";
             }
             enum "1549.77" {
               description "1549.77 nm/193.44375 THz 6.25GHz spacing";
             }
             enum "1549.72" {
               description "1549.72 nm/193.45000 THz 6.25/12.5/50GHz spacing";
             }
             enum "1549.67" {
               description "1549.67 nm/193.45625 THz 6.25GHz spacing";
             }
             enum "1549.62" {
               description "1549.62 nm/193.46250 THz 6.25/12.5GHz spacing";
             }
             enum "1549.57" {
               description "1549.57 nm/193.46875 THz 6.25GHz spacing";
             }
             enum "1549.52" {
               description "1549.52 nm/193.47500 THz 6.25/12.5/75GHz spacing";
             }
             enum "1549.47" {
               description "1549.47 nm/193.48125 THz 6.25GHz spacing";
             }
             enum "1549.42" {
               description "1549.42 nm/193.48750 THz 6.25/12.5GHz spacing";
             }
             enum "1549.37" {
               description "1549.37 nm/193.49375 THz 6.25GHz spacing";
             }
             enum "1549.32" {
               description "1549.32 nm/193.50000 THz 6.25/12.5/50/100GHz spacing";
             }
             enum "1549.26" {
               description "1549.26 nm/193.50625 THz 6.25GHz spacing";
             }
             enum "1549.21" {
               description "1549.21 nm/193.51250 THz 6.25/12.5GHz spacing";
             }
             enum "1549.16" {
               description "1549.16 nm/193.51875 THz 6.25GHz spacing";
             }
             enum "1549.11" {
               description "1549.11 nm/193.52500 THz 6.25/12.5GHz spacing";
             }
             enum "1549.06" {
               description "1549.06 nm/193.53125 THz 6.25GHz spacing";
             }
             enum "1549.01" {
               description "1549.01 nm/193.53750 THz 6.25/12.5GHz spacing";
             }
             enum "1548.96" {
               description "1548.96 nm/193.54375 THz 6.25GHz spacing";
             }
             enum "1548.91" {
               description "1548.91 nm/193.55000 THz 6.25/12.5/50G/75Hz spacing";
             }
             enum "1548.86" {
               description "1548.86 nm/193.55625 THz 6.25GHz spacing";
             }
             enum "1548.81" {
               description "1548.81 nm/193.56250 THz 6.25/12.5GHz spacing";
             }
             enum "1548.76" {
               description "1548.76 nm/193.56875 THz 6.25GHz spacing";
             }
             enum "1548.71" {
               description "1548.71 nm/193.57500 THz 6.25/12.5GHz spacing";
             }
             enum "1548.66" {
               description "1548.66 nm/193.58125 THz 6.25GHz spacing";
             }
             enum "1548.61" {
               description "1548.61 nm/193.58750 THz 6.25/12.5GHz spacing";
             }
             enum "1548.56" {
               description "1548.56 nm/193.59375 THz 6.25GHz spacing";
             }
             enum "1548.51" {
               description "1548.51 nm/193.60000 THz 6.25/12.5/50/100GHz spacing";
             }
             enum "1548.46" {
               description "1548.46 nm/193.60625 THz 6.25GHz spacing";
             }
             enum "1548.41" {
               description "1548.41 nm/193.61250 THz 6.25/12.5GHz spacing";
             }
             enum "1548.36" {
               description "1548.36 nm/193.61875 THz 6.25GHz spacing";
             }
             enum "1548.31" {
               description "1548.31 nm/193.62500 THz 6.25/12.5/75GHz spacing";
             }
             enum "1548.26" {
               description "1548.26 nm/193.63125 THz 6.25GHz spacing";
             }
             enum "1548.21" {
               description "1548.21 nm/193.63750 THz 6.25/12.5GHz spacing";
             }
             enum "1548.16" {
               description "1548.16 nm/193.64375 THz 6.25GHz spacing";
             }
             enum "1548.11" {
               description "1548.11 nm/193.65000 THz 6.25/12.5/50GHz spacing";
             }
             enum "1548.06" {
               description "1548.06 nm/193.65625 THz 6.25GHz spacing";
             }
             enum "1548.02" {
               description "1548.02 nm/193.66250 THz 6.25/12.5GHz spacing";
             }
             enum "1547.97" {
               description "1547.97 nm/193.66875 THz 6.25GHz spacing";
             }
             enum "1547.92" {
               description "1547.92 nm/193.67500 THz 6.25/12.5GHz spacing";
             }
             enum "1547.87" {
               description "1547.87 nm/193.68125 THz 6.25GHz spacing";
             }
             enum "1547.82" {
               description "1547.82 nm/193.68750 THz 6.25/12.5GHz spacing";
             }
             enum "1547.77" {
               description "1547.77 nm/193.69375 THz 6.25GHz spacing";
             }
             enum "1547.72" {
               description "1547.72 nm/193.70000 THz 6.25/12.5/50/75/100GHz spacing";
             }
             enum "1547.67" {
               description "1547.67 nm/193.70625 THz 6.25GHz spacing";
             }
             enum "1547.62" {
               description "1547.62 nm/193.71250 THz 6.25/12.5GHz spacing";
             }
             enum "1547.57" {
               description "1547.57 nm/193.71875 THz 6.25GHz spacing";
             }
             enum "1547.52" {
               description "1547.52 nm/193.72500 THz 6.25/12.5GHz spacing";
             }
             enum "1547.47" {
               description "1547.47 nm/193.73125 THz 6.25GHz spacing";
             }
             enum "1547.42" {
               description "1547.42 nm/193.73750 THz 6.25/12.5GHz spacing";
             }
             enum "1547.37" {
               description "1547.37 nm/193.74375 THz 6.25GHz spacing";
             }
             enum "1547.32" {
               description "1547.32 nm/193.75000 THz 6.25/12.5/50GHz spacing";
             }
             enum "1547.27" {
               description "1547.27 nm/193.75625 THz 6.25GHz spacing";
             }
             enum "1547.22" {
               description "1547.22 nm/193.76250 THz 6.25/12.5GHz spacing";
             }
             enum "1547.17" {
               description "1547.17 nm/193.76875 THz 6.25GHz spacing";
             }
             enum "1547.12" {
               description "1547.12 nm/193.77500 THz 6.25/12.5/75GHz spacing";
             }
             enum "1547.07" {
               description "1547.07 nm/193.78125 THz 6.25GHz spacing";
             }
             enum "1547.02" {
               description "1547.02 nm/193.78750 THz 6.25/12.5GHz spacing";
             }
             enum "1546.97" {
               description "1546.97 nm/193.79375 THz 6.25GHz spacing";
             }
             enum "1546.92" {
               description "1546.92 nm/193.80000 THz 6.25/12.5/50/100GHz spacing";
             }
             enum "1546.87" {
               description "1546.87 nm/193.80625 THz 6.25GHz spacing";
             }
             enum "1546.82" {
               description "1546.82 nm/193.81250 THz 6.25/12.5GHz spacing";
             }
             enum "1546.77" {
               description "1546.77 nm/193.81875 THz 6.25GHz spacing";
             }
             enum "1546.72" {
               description "1546.72 nm/193.82500 THz 6.25/12.5GHz spacing";
             }
             enum "1546.67" {
               description "1546.67 nm/193.83125 THz 6.25GHz spacing";
             }
             enum "1546.62" {
               description "1546.62 nm/193.83750 THz 6.25/12.5GHz spacing";
             }
             enum "1546.57" {
               description "1546.57 nm/193.84375 THz 6.25GHz spacing";
             }
             enum "1546.52" {
               description "1546.52 nm/193.85000 THz 6.25/12.5/50/75GHz spacing";
             }
             enum "1546.47" {
               description "1546.47 nm/193.85625 THz 6.25GHz spacing";
             }
             enum "1546.42" {
               description "1546.42 nm/193.86250 THz 6.25/12.5GHz spacing";
             }
             enum "1546.37" {
               description "1546.37 nm/193.86875 THz 6.25GHz spacing";
             }
             enum "1546.32" {
               description "1546.32 nm/193.87500 THz 6.25/12.5GHz spacing";
             }
             enum "1546.27" {
               description "1546.27 nm/193.88125 THz 6.25GHz spacing";
             }
             enum "1546.22" {
               description "1546.22 nm/193.88750 THz 6.25/12.5GHz spacing";
             }
             enum "1546.17" {
               description "1546.17 nm/193.89375 THz 6.25GHz spacing";
             }
             enum "1546.12" {
               description "1546.12 nm/193.90000 THz 6.25/12.5/50/100GHz spacing";
             }
             enum "1546.07" {
               description "1546.07 nm/193.90625 THz 6.25GHz spacing";
             }
             enum "1546.02" {
               description "1546.02 nm/193.91250 THz 6.25/12.5GHz spacing";
             }
             enum "1545.97" {
               description "1545.97 nm/193.91875 THz 6.25GHz spacing";
             }
             enum "1545.92" {
               description "1545.92 nm/193.92500 THz 6.25/12.5/75GHz spacing";
             }
             enum "1545.87" {
               description "1545.87 nm/193.93125 THz 6.25GHz spacing";
             }
             enum "1545.82" {
               description "1545.82 nm/193.93750 THz 6.25/12.5GHz spacing";
             }
             enum "1545.77" {
               description "1545.77 nm/193.94375 THz 6.25GHz spacing";
             }
             enum "1545.72" {
               description "1545.72 nm/193.95000 THz 6.25/12.5/50GHz spacing";
             }
             enum "1545.67" {
               description "1545.67 nm/193.95625 THz 6.25GHz spacing";
             }
             enum "1545.62" {
               description "1545.62 nm/193.96250 THz 6.25/12.5GHz spacing";
             }
             enum "1545.57" {
               description "1545.57 nm/193.96875 THz 6.25GHz spacing";
             }
             enum "1545.52" {
               description "1545.52 nm/193.97500 THz 6.25/12.5GHz spacing";
             }
             enum "1545.47" {
               description "1545.47 nm/193.98125 THz 6.25GHz spacing";
             }
             enum "1545.42" {
               description "1545.42 nm/193.98750 THz 6.25/12.5GHz spacing";
             }
             enum "1545.37" {
               description "1545.37 nm/193.99375 THz 6.25GHz spacing";
             }
             enum "1545.32" {
               description "1545.32 nm/194.00000 THz 6.25/12.5/50/75/100GHz spacing";
             }
             enum "1545.27" {
               description "1545.27 nm/194.00625 THz 6.25GHz spacing";
             }
             enum "1545.22" {
               description "1545.22 nm/194.01250 THz 6.25/12.5GHz spacing";
             }
             enum "1545.17" {
               description "1545.17 nm/194.01875 THz 6.25GHz spacing";
             }
             enum "1545.12" {
               description "1545.12 nm/194.02500 THz 6.25/12.5GHz spacing";
             }
             enum "1545.07" {
               description "1545.07 nm/194.03125 THz 6.25GHz spacing";
             }
             enum "1545.02" {
               description "1545.02 nm/194.03750 THz 6.25/12.5GHz spacing";
             }
             enum "1544.97" {
               description "1544.97 nm/194.04375 THz 6.25GHz spacing";
             }
             enum "1544.92" {
               description "1544.92 nm/194.05000 THz 6.25/12.5/50GHz spacing";
             }
             enum "1544.87" {
               description "1544.87 nm/194.05625 THz 6.25GHz spacing";
             }
             enum "1544.82" {
               description "1544.82 nm/194.06250 THz 6.25/12.5GHz spacing";
             }
             enum "1544.77" {
               description "1544.77 nm/194.06875 THz 6.25GHz spacing";
             }
             enum "1544.72" {
               description "1544.72 nm/194.07500 THz 6.25/12.5/75GHz spacing";
             }
             enum "1544.68" {
               description "1544.68 nm/194.08125 THz 6.25GHz spacing";
             }
             enum "1544.63" {
               description "1544.63 nm/194.08750 THz 6.25/12.5GHz spacing";
             }
             enum "1544.58" {
               description "1544.58 nm/194.09375 THz 6.25GHz spacing";
             }
             enum "1544.53" {
               description "1544.53 nm/194.10000 THz 6.25/12.5/50/100GHz spacing";
             }
             enum "1544.48" {
               description "1544.48 nm/194.10625 THz 6.25GHz spacing";
             }
             enum "1544.43" {
               description "1544.43 nm/194.11250 THz 6.25/12.5GHz spacing";
             }
             enum "1544.38" {
               description "1544.38 nm/194.11875 THz 6.25GHz spacing";
             }
             enum "1544.33" {
               description "1544.33 nm/194.12500 THz 6.25/12.5GHz spacing";
             }
             enum "1544.28" {
               description "1544.28 nm/194.13125 THz 6.25GHz spacing";
             }
             enum "1544.23" {
               description "1544.23 nm/194.13750 THz 6.25/12.5GHz spacing";
             }
             enum "1544.18" {
               description "1544.18 nm/194.14375 THz 6.25GHz spacing";
             }
             enum "1544.13" {
               description "1544.13 nm/194.15000 THz 6.25/12.5/50/75GHz spacing";
             }
             enum "1544.08" {
               description "1544.08 nm/194.15625 THz 6.25GHz spacing";
             }
             enum "1544.03" {
               description "1544.03 nm/194.16250 THz 6.25/12.5GHz spacing";
             }
             enum "1543.98" {
               description "1543.98 nm/194.16875 THz 6.25GHz spacing";
             }
             enum "1543.93" {
               description "1543.93 nm/194.17500 THz 6.25/12.5GHz spacing";
             }
             enum "1543.88" {
               description "1543.88 nm/194.18125 THz 6.25GHz spacing";
             }
             enum "1543.83" {
               description "1543.83 nm/194.18750 THz 6.25/12.5GHz spacing";
             }
             enum "1543.78" {
               description "1543.78 nm/194.19375 THz 6.25GHz spacing";
             }
             enum "1543.73" {
               description "1543.73 nm/194.20000 THz 6.25/12.5/50/100GHz spacing";
             }
             enum "1543.68" {
               description "1543.68 nm/194.20625 THz 6.25GHz spacing";
             }
             enum "1543.63" {
               description "1543.63 nm/194.21250 THz 6.25/12.5GHz spacing";
             }
             enum "1543.58" {
               description "1543.58 nm/194.21875 THz 6.25GHz spacing";
             }
             enum "1543.53" {
               description "1543.53 nm/194.22500 THz 6.25/12.5/75GHz spacing";
             }
             enum "1543.48" {
               description "1543.48 nm/194.23125 THz 6.25GHz spacing";
             }
             enum "1543.43" {
               description "1543.43 nm/194.23750 THz 6.25/12.5GHz spacing";
             }
             enum "1543.38" {
               description "1543.38 nm/194.24375 THz 6.25GHz spacing";
             }
             enum "1543.33" {
               description "1543.33 nm/194.25000 THz 6.25/12.5/50GHz spacing";
             }
             enum "1543.28" {
               description "1543.28 nm/194.25625 THz 6.25GHz spacing";
             }
             enum "1543.23" {
               description "1543.23 nm/194.26250 THz 6.25/12.5GHz spacing";
             }
             enum "1543.18" {
               description "1543.18 nm/194.26875 THz 6.25GHz spacing";
             }
             enum "1543.13" {
               description "1543.13 nm/194.27500 THz 6.25/12.5GHz spacing";
             }
             enum "1543.08" {
               description "1543.08 nm/194.28125 THz 6.25GHz spacing";
             }
             enum "1543.04" {
               description "1543.04 nm/194.28750 THz 6.25/12.5GHz spacing";
             }
             enum "1542.99" {
               description "1542.99 nm/194.29375 THz 6.25GHz spacing";
             }
             enum "1542.94" {
               description "1542.94 nm/194.30000 THz 6.25/12.5/50/75/100GHz spacing";
             }
             enum "1542.89" {
               description "1542.89 nm/194.30625 THz 6.25GHz spacing";
             }
             enum "1542.84" {
               description "1542.84 nm/194.31250 THz 6.25/12.5GHz spacing";
             }
             enum "1542.79" {
               description "1542.79 nm/194.31875 THz 6.25GHz spacing";
             }
             enum "1542.74" {
               description "1542.74 nm/194.32500 THz 6.25/12.5GHz spacing";
             }
             enum "1542.69" {
               description "1542.69 nm/194.33125 THz 6.25GHz spacing";
             }
             enum "1542.64" {
               description "1542.64 nm/194.33750 THz 6.25/12.5GHz spacing";
             }
             enum "1542.59" {
               description "1542.59 nm/194.34375 THz 6.25GHz spacing";
             }
             enum "1542.54" {
               description "1542.54 nm/194.35000 THz 6.25/12.5/50GHz spacing";
             }
             enum "1542.49" {
               description "1542.49 nm/194.35625 THz 6.25GHz spacing";
             }
             enum "1542.44" {
               description "1542.44 nm/194.36250 THz 6.25/12.5GHz spacing";
             }
             enum "1542.39" {
               description "1542.39 nm/194.36875 THz 6.25GHz spacing";
             }
             enum "1542.34" {
               description "1542.34 nm/194.37500 THz 6.25/12.5/75GHz spacing";
             }
             enum "1542.29" {
               description "1542.29 nm/194.38125 THz 6.25GHz spacing";
             }
             enum "1542.24" {
               description "1542.24 nm/194.38750 THz 6.25/12.5GHz spacing";
             }
             enum "1542.19" {
               description "1542.19 nm/194.39375 THz 6.25GHz spacing";
             }
             enum "1542.14" {
               description "1542.14 nm/194.40000 THz 6.25/12.5/50/100GHz spacing";
             }
             enum "1542.09" {
               description "1542.09 nm/194.40625 THz 6.25GHz spacing";
             }
             enum "1542.04" {
               description "1542.04 nm/194.41250 THz 6.25/12.5GHz spacing";
             }
             enum "1541.99" {
               description "1541.99 nm/194.41875 THz 6.25GHz spacing";
             }
             enum "1541.94" {
               description "1541.94 nm/194.42500 THz 6.25/12.5GHz spacing";
             }
             enum "1541.89" {
               description "1541.89 nm/194.43125 THz 6.25GHz spacing";
             }
             enum "1541.84" {
               description "1541.84 nm/194.43750 THz 6.25/12.5GHz spacing";
             }
             enum "1541.80" {
               description "1541.80 nm/194.44375 THz 6.25GHz spacing";
             }
             enum "1541.75" {
               description "1541.75 nm/194.45000 THz 6.25/12.5/50/75GHz spacing";
             }
             enum "1541.70" {
               description "1541.70 nm/194.45625 THz 6.25GHz spacing";
             }
             enum "1541.65" {
               description "1541.65 nm/194.46250 THz 6.25/12.5GHz spacing";
             }
             enum "1541.60" {
               description "1541.60 nm/194.46875 THz 6.25GHz spacing";
             }
             enum "1541.55" {
               description "1541.55 nm/194.47500 THz 6.25/12.5GHz spacing";
             }
             enum "1541.50" {
               description "1541.50 nm/194.48125 THz 6.25GHz spacing";
             }
             enum "1541.45" {
               description "1541.45 nm/194.48750 THz 6.25/12.5GHz spacing";
             }
             enum "1541.40" {
               description "1541.40 nm/194.49375 THz 6.25GHz spacing";
             }
             enum "1541.35" {
               description "1541.35 nm/194.50000 THz 6.25/12.5/50/100GHz spacing";
             }
             enum "1541.30" {
               description "1541.30 nm/194.50625 THz 6.25GHz spacing";
             }
             enum "1541.25" {
               description "1541.25 nm/194.51250 THz 6.25/12.5GHz spacing";
             }
             enum "1541.20" {
               description "1541.20 nm/194.51875 THz 6.25GHz spacing";
             }
             enum "1541.15" {
               description "1541.15 nm/194.52500 THz 6.25/12.5/75GHz spacing";
             }
             enum "1541.10" {
               description "1541.10 nm/194.53125 THz 6.25GHz spacing";
             }
             enum "1541.05" {
               description "1541.05 nm/194.53750 THz 6.25/12.5GHz spacing";
             }
             enum "1541.00" {
               description "1541.00 nm/194.54375 THz 6.25GHz spacing";
             }
             enum "1540.95" {
               description "1540.95 nm/194.55000 THz 6.25/12.5/50GHz spacing";
             }
             enum "1540.90" {
               description "1540.90 nm/194.55625 THz 6.25GHz spacing";
             }
             enum "1540.85" {
               description "1540.85 nm/194.56250 THz 6.25/12.5GHz spacing";
             }
             enum "1540.80" {
               description "1540.80 nm/194.56875 THz 6.25GHz spacing";
             }
             enum "1540.76" {
               description "1540.76 nm/194.57500 THz 6.25/12.5GHz spacing";
             }
             enum "1540.71" {
               description "1540.71 nm/194.58125 THz 6.25GHz spacing";
             }
             enum "1540.66" {
               description "1540.66 nm/194.58750 THz 6.25/12.5GHz spacing";
             }
             enum "1540.61" {
               description "1540.61 nm/194.59375 THz 6.25GHz spacing";
             }
             enum "1540.56" {
               description "1540.56 nm/194.60000 THz 6.25/12.5/50/75/100GHz spacing";
             }
             enum "1540.51" {
               description "1540.51 nm/194.60625 THz 6.25GHz spacing";
             }
             enum "1540.46" {
               description "1540.46 nm/194.61250 THz 6.25/12.5GHz spacing";
             }
             enum "1540.41" {
               description "1540.41 nm/194.61875 THz 6.25GHz spacing";
             }
             enum "1540.36" {
               description "1540.36 nm/194.62500 THz 6.25/12.5GHz spacing";
             }
             enum "1540.31" {
               description "1540.31 nm/194.63125 THz 6.25GHz spacing";
             }
             enum "1540.26" {
               description "1540.26 nm/194.63750 THz 6.25/12.5GHz spacing";
             }
             enum "1540.21" {
               description "1540.21 nm/194.64375 THz 6.25GHz spacing";
             }
             enum "1540.16" {
               description "1540.16 nm/194.65000 THz 6.25/12.5/50GHz spacing";
             }
             enum "1540.11" {
               description "1540.11 nm/194.65625 THz 6.25GHz spacing";
             }
             enum "1540.06" {
               description "1540.06 nm/194.66250 THz 6.25/12.5GHz spacing";
             }
             enum "1540.01" {
               description "1540.01 nm/194.66875 THz 6.25GHz spacing";
             }
             enum "1539.96" {
               description "1539.96 nm/194.67500 THz 6.25/12.5/50/75GHz spacing";
             }
             enum "1539.91" {
               description "1539.91 nm/194.68125 THz 6.25GHz spacing";
             }
             enum "1539.86" {
               description "1539.86 nm/194.68750 THz 6.25/12.5GHz spacing";
             }
             enum "1539.82" {
               description "1539.82 nm/194.69375 THz 6.25GHz spacing";
             }
             enum "1539.77" {
               description "1539.77 nm/194.70000 THz 6.25/12.5/50/100GHz spacing";
             }
             enum "1539.72" {
               description "1539.72 nm/194.70625 THz 6.25GHz spacing";
             }
             enum "1539.67" {
               description "1539.67 nm/194.71250 THz 6.25/12.5GHz spacing";
             }
             enum "1539.62" {
               description "1539.62 nm/194.71875 THz 6.25GHz spacing";
             }
             enum "1539.57" {
               description "1539.57 nm/194.72500 THz 6.25/12.5GHz spacing";
             }
             enum "1539.52" {
               description "1539.52 nm/194.73125 THz 6.25GHz spacing";
             }
             enum "1539.47" {
               description "1539.47 nm/194.73750 THz 6.25/12.5GHz spacing";
             }
             enum "1539.42" {
               description "1539.42 nm/194.74375 THz 6.25GHz spacing";
             }
             enum "1539.37" {
               description "1539.37 nm/194.75000 THz 6.25/12.5/50/75GHz spacing";
             }
             enum "1539.32" {
               description "1539.32 nm/194.75625 THz 6.25GHz spacing";
             }
             enum "1539.27" {
               description "1539.27 nm/194.76250 THz 6.25/12.5GHz spacing";
             }
             enum "1539.22" {
               description "1539.22 nm/194.76875 THz 6.25GHz spacing";
             }
             enum "1539.17" {
               description "1539.17 nm/194.77500 THz 6.25/12.5GHz spacing";
             }
             enum "1539.12" {
               description "1539.12 nm/194.78125 THz 6.25GHz spacing";
             }
             enum "1539.07" {
               description "1539.07 nm/194.78750 THz 6.25/12.5GHz spacing";
             }
             enum "1539.03" {
               description "1539.03 nm/194.79375 THz 6.25GHz spacing";
             }
             enum "1538.98" {
               description "1538.98 nm/194.80000 THz 6.25/12.5/50/100GHz spacing";
             }
             enum "1538.93" {
               description "1538.93 nm/194.80625 THz 6.25GHz spacing";
             }
             enum "1538.88" {
               description "1538.88 nm/194.81250 THz 6.25/12.5GHz spacing";
             }
             enum "1538.83" {
               description "1538.83 nm/194.81875 THz 6.25GHz spacing";
             }
             enum "1538.78" {
               description "1538.78 nm/194.82500 THz 6.25/12.5/75GHz spacing";
             }
             enum "1538.73" {
               description "1538.73 nm/194.83125 THz 6.25GHz spacing";
             }
             enum "1538.68" {
               description "1538.68 nm/194.83750 THz 6.25/12.5GHz spacing";
             }
             enum "1538.63" {
               description "1538.63 nm/194.84375 THz 6.25GHz spacing";
             }
             enum "1538.58" {
               description "1538.58 nm/194.85000 THz 6.25/12.5/50GHz spacing";
             }
             enum "1538.53" {
               description "1538.53 nm/194.85625 THz 6.25GHz spacing";
             }
             enum "1538.48" {
               description "1538.48 nm/194.86250 THz 6.25/12.5GHz spacing";
             }
             enum "1538.43" {
               description "1538.43 nm/194.86875 THz 6.25GHz spacing";
             }
             enum "1538.38" {
               description "1538.38 nm/194.87500 THz 6.25/12.5/75GHz spacing";
             }
             enum "1538.33" {
               description "1538.33 nm/194.88125 THz 6.25GHz spacing";
             }
             enum "1538.28" {
               description "1538.28 nm/194.88750 THz 6.25/12.5GHz spacing";
             }
             enum "1538.24" {
               description "1538.24 nm/194.89375 THz 6.25GHz spacing";
             }
             enum "1538.19" {
               description "1538.19 nm/194.90000 THz 6.25/12.5/50/75/100GHz spacing";
             }
             enum "1538.14" {
               description "1538.14 nm/194.90625 THz 6.25GHz spacing";
             }
             enum "1538.09" {
               description "1538.09 nm/194.91250 THz 6.25/12.5GHz spacing";
             }
             enum "1538.04" {
               description "1538.04 nm/194.91875 THz 6.25GHz spacing";
             }
             enum "1537.99" {
               description "1537.99 nm/194.92500 THz 6.25/12.5GHz spacing";
             }
             enum "1537.94" {
               description "1537.94 nm/194.93125 THz 6.25GHz spacing";
             }
             enum "1537.89" {
               description "1537.89 nm/194.93750 THz 6.25/12.5GHz spacing";
             }
             enum "1537.84" {
               description "1537.84 nm/194.94375 THz 6.25GHz spacing";
             }
             enum "1537.79" {
               description "1537.79 nm/194.95000 THz 6.25/12.5/50GHz spacing";
             }
             enum "1537.74" {
               description "1537.74 nm/194.95625 THz 6.25GHz spacing";
             }
             enum "1537.69" {
               description "1537.69 nm/194.96250 THz 6.25/12.5GHz spacing";
             }
             enum "1537.64" {
               description "1537.64 nm/194.96875 THz 6.25GHz spacing";
             }
             enum "1537.59" {
               description "1537.59 nm/194.97500 THz 6.25/12.5/75GHz spacing";
             }
             enum "1537.55" {
               description "1537.55 nm/194.98125 THz 6.25GHz spacing";
             }
             enum "1537.50" {
               description "1537.50 nm/194.98750 THz 6.25/12.5GHz spacing";
             }
             enum "1537.45" {
               description "1537.45 nm/194.99375 THz 6.25GHz spacing";
             }
             enum "1537.40" {
               description "1537.40 nm/195.00000 THz 6.25/12.5/50/100GHz spacing";
             }
             enum "1537.35" {
               description "1537.35 nm/195.00625 THz 6.25GHz spacing";
             }
             enum "1537.30" {
               description "1537.30 nm/195.01250 THz 6.25/12.5GHz spacing";
             }
             enum "1537.25" {
               description "1537.25 nm/195.01875 THz 6.25GHz spacing";
             }
             enum "1537.20" {
               description "1537.20 nm/195.02500 THz 6.25/12.5GHz spacing";
             }
             enum "1537.15" {
               description "1537.15 nm/195.03125 THz 6.25GHz spacing";
             }
             enum "1537.10" {
               description "1537.10 nm/195.03750 THz 6.25/12.5GHz spacing";
             }
             enum "1537.05" {
               description "1537.05 nm/195.04375 THz 6.25GHz spacing";
             }
             enum "1537.00" {
               description "1537.00 nm/195.05000 THz 6.25/12.5/50/75GHz spacing";
             }
             enum "1536.95" {
               description "1536.95 nm/195.05625 THz 6.25GHz spacing";
             }
             enum "1536.90" {
               description "1536.90 nm/195.06250 THz 6.25/12.5GHz spacing";
             }
             enum "1536.86" {
               description "1536.86 nm/195.06875 THz 6.25GHz spacing";
             }
             enum "1536.81" {
               description "1536.81 nm/195.07500 THz 6.25/12.5GHz spacing";
             }
             enum "1536.76" {
               description "1536.76 nm/195.08125 THz 6.25GHz spacing";
             }
             enum "1536.71" {
               description "1536.71 nm/195.08750 THz 6.25/12.5GHz spacing";
             }
             enum "1536.66" {
               description "1536.66 nm/195.09375 THz 6.25GHz spacing";
             }
             enum "1536.61" {
               description "1536.61 nm/195.10000 THz 6.25/12.5/50/100GHz spacing";
             }
             enum "1536.56" {
               description "1536.56 nm/195.10625 THz 6.25GHz spacing";
             }
             enum "1536.51" {
               description "1536.51 nm/195.11250 THz 6.25/12.5GHz spacing";
             }
             enum "1536.46" {
               description "1536.46 nm/195.11875 THz 6.25GHz spacing";
             }
             enum "1536.41" {
               description "1536.41 nm/195.12500 THz 6.25/12.5/75GHz spacing";
             }
             enum "1536.36" {
               description "1536.36 nm/195.13125 THz 6.25GHz spacing";
             }
             enum "1536.31" {
               description "1536.31 nm/195.13750 THz 6.25/12.5GHz spacing";
             }
             enum "1536.26" {
               description "1536.26 nm/195.14375 THz 6.25GHz spacing";
             }
             enum "1536.22" {
               description "1536.22 nm/195.15000 THz 6.25/12.5/50GHz spacing";
             }
             enum "1536.17" {
               description "1536.17 nm/195.15625 THz 6.25GHz spacing";
             }
             enum "1536.12" {
               description "1536.12 nm/195.16250 THz 6.25/12.5GHz spacing";
             }
             enum "1536.07" {
               description "1536.07 nm/195.16875 THz 6.25GHz spacing";
             }
             enum "1536.02" {
               description "1536.02 nm/195.17500 THz 6.25/12.5GHz spacing";
             }
             enum "1535.97" {
               description "1535.97 nm/195.18125 THz 6.25GHz spacing";
             }
             enum "1535.92" {
               description "1535.92 nm/195.18750 THz 6.25/12.5GHz spacing";
             }
             enum "1535.87" {
               description "1535.87 nm/195.19375 THz 6.25GHz spacing";
             }
             enum "1535.82" {
               description "1535.82 nm/195.20000 THz 6.25/12.5/50/75/100GHz spacing";
             }
             enum "1535.77" {
               description "1535.77 nm/195.20625 THz 6.25GHz spacing";
             }
             enum "1535.72" {
               description "1535.72 nm/195.21250 THz 6.25/12.5GHz spacing";
             }
             enum "1535.67" {
               description "1535.67 nm/195.21875 THz 6.25GHz spacing";
             }
             enum "1535.63" {
               description "1535.63 nm/195.22500 THz 6.25/12.5GHz spacing";
             }
             enum "1535.58" {
               description "1535.58 nm/195.23125 THz 6.25GHz spacing";
             }
             enum "1535.53" {
               description "1535.53 nm/195.23750 THz 6.25/12.5GHz spacing";
             }
             enum "1535.48" {
               description "1535.48 nm/195.24375 THz 6.25GHz spacing";
             }
             enum "1535.43" {
               description "1535.43 nm/195.25000 THz 6.25/12.5/50GHz spacing";
             }
             enum "1535.38" {
               description "1535.38 nm/195.25625 THz 6.25GHz spacing";
             }
             enum "1535.33" {
               description "1535.33 nm/195.26250 THz 6.25/12.5GHz spacing";
             }
             enum "1535.28" {
               description "1535.28 nm/195.26875 THz 6.25GHz spacing";
             }
             enum "1535.23" {
               description "1535.23 nm/195.27500 THz 6.25/12.5/75GHz spacing";
             }
             enum "1535.18" {
               description "1535.18 nm/195.28125 THz 6.25GHz spacing";
             }
             enum "1535.13" {
               description "1535.13 nm/195.28750 THz 6.25/12.5GHz spacing";
             }
             enum "1535.08" {
               description "1535.08 nm/195.29375 THz 6.25GHz spacing";
             }
             enum "1535.04" {
               description "1535.04 nm/195.30000 THz 6.25/12.5/50/100GHz spacing";
             }
             enum "1534.99" {
               description "1534.99 nm/195.30625 THz 6.25GHz spacing";
             }
             enum "1534.94" {
               description "1534.94 nm/195.31250 THz 6.25/12.5GHz spacing";
             }
             enum "1534.89" {
               description "1534.89 nm/195.31875 THz 6.25GHz spacing";
             }
             enum "1534.84" {
               description "1534.84 nm/195.32500 THz 6.25/12.5GHz spacing";
             }
             enum "1534.79" {
               description "1534.79 nm/195.33125 THz 6.25GHz spacing";
             }
             enum "1534.74" {
               description "1534.74 nm/195.33750 THz 6.25/12.5GHz spacing";
             }
             enum "1534.69" {
               description "1534.69 nm/195.34375 THz 6.25GHz spacing";
             }
             enum "1534.64" {
               description "1534.64 nm/195.35000 THz 6.25/12.5/50/75GHz spacing";
             }
             enum "1534.59" {
               description "1534.59 nm/195.35625 THz 6.25GHz spacing";
             }
             enum "1534.54" {
               description "1534.54 nm/195.36250 THz 6.25/12.5GHz spacing";
             }
             enum "1534.50" {
               description "1534.50 nm/195.36875 THz 6.25GHz spacing";
             }
             enum "1534.45" {
               description "1534.45 nm/195.37500 THz 6.25/12.5GHz spacing";
             }
             enum "1534.40" {
               description "1534.40 nm/195.38125 THz 6.25GHz spacing";
             }
             enum "1534.35" {
               description "1534.35 nm/195.38750 THz 6.25/12.5GHz spacing";
             }
             enum "1534.30" {
               description "1534.30 nm/195.39375 THz 6.25GHz spacing";
             }
             enum "1534.25" {
               description "1534.25 nm/195.40000 THz 6.25/12.5/50/100GHz spacing";
             }
             enum "1534.20" {
               description "1534.20 nm/195.40625 THz 6.25GHz spacing";
             }
             enum "1534.15" {
               description "1534.15 nm/195.41250 THz 6.25/12.5GHz spacing";
             }
             enum "1534.10" {
               description "1534.10 nm/195.41875 THz 6.25GHz spacing";
             }
             enum "1534.05" {
               description "1534.05 nm/195.42500 THz 6.25/12.5/75GHz spacing";
             }
             enum "1534.00" {
               description "1534.00 nm/195.43125 THz 6.25GHz spacing";
             }
             enum "1533.96" {
               description "1533.96 nm/195.43750 THz 6.25/12.5GHz spacing";
             }
             enum "1533.91" {
               description "1533.91 nm/195.44375 THz 6.25GHz spacing";
             }
             enum "1533.86" {
               description "1533.86 nm/195.45000 THz 6.25/12.5/50GHz spacing";
             }
             enum "1533.81" {
               description "1533.81 nm/195.45625 THz 6.25GHz spacing";
             }
             enum "1533.76" {
               description "1533.76 nm/195.46250 THz 6.25/12.5GHz spacing";
             }
             enum "1533.71" {
               description "1533.71 nm/195.46875 THz 6.25GHz spacing";
             }
             enum "1533.66" {
               description "1533.66 nm/195.47500 THz 6.25/12.5GHz spacing";
             }
             enum "1533.61" {
               description "1533.61 nm/195.48125 THz 6.25GHz spacing";
             }
             enum "1533.56" {
               description "1533.56 nm/195.48750 THz 6.25/12.5GHz spacing";
             }
             enum "1533.51" {
               description "1533.51 nm/195.49375 THz 6.25GHz spacing";
             }
             enum "1533.47" {
               description "1533.47 nm/195.50000 THz 6.25/12.5/50/75/100GHz spacing";
             }
             enum "1533.42" {
               description "1533.42 nm/195.50625 THz 6.25GHz spacing";
             }
             enum "1533.37" {
               description "1533.37 nm/195.51250 THz 6.25/12.5GHz spacing";
             }
             enum "1533.32" {
               description "1533.32 nm/195.51875 THz 6.25GHz spacing";
             }
             enum "1533.27" {
               description "1533.27 nm/195.52500 THz 6.25/12.5GHz spacing";
             }
             enum "1533.22" {
               description "1533.22 nm/195.53125 THz 6.25GHz spacing";
             }
             enum "1533.17" {
               description "1533.17 nm/195.53750 THz 6.25/12.5GHz spacing";
             }
             enum "1533.12" {
               description "1533.12 nm/195.54375 THz 6.25GHz spacing";
             }
             enum "1533.07" {
               description "1533.07 nm/195.55000 THz 6.25/12.5/50GHz spacing";
             }
             enum "1533.02" {
               description "1533.02 nm/195.55625 THz 6.25GHz spacing";
             }
             enum "1532.98" {
               description "1532.98 nm/195.56250 THz 6.25/12.5GHz spacing";
             }
             enum "1532.93" {
               description "1532.93 nm/195.56875 THz 6.25GHz spacing";
             }
             enum "1532.88" {
               description "1532.88 nm/195.57500 THz 6.25/12.5/75GHz spacing";
             }
             enum "1532.83" {
               description "1532.83 nm/195.58125 THz 6.25GHz spacing";
             }
             enum "1532.78" {
               description "1532.78 nm/195.58750 THz 6.25/12.5GHz spacing";
             }
             enum "1532.73" {
               description "1532.73 nm/195.59375 THz 6.25GHz spacing";
             }
             enum "1532.68" {
               description "1532.68 nm/195.60000 THz 6.25/12.5/50/100GHz spacing";
             }
             enum "1532.63" {
               description "1532.63 nm/195.60625 THz 6.25GHz spacing";
             }
             enum "1532.58" {
               description "1532.58 nm/195.61250 THz 6.25/12.5GHz spacing";
             }
             enum "1532.53" {
               description "1532.53 nm/195.61875 THz 6.25GHz spacing";
             }
             enum "1532.49" {
               description "1532.49 nm/195.62500 THz 6.25/12.5GHz spacing";
             }
             enum "1532.44" {
               description "1532.44 nm/195.63125 THz 6.25GHz spacing";
             }
             enum "1532.39" {
               description "1532.39 nm/195.63750 THz 6.25/12.5GHz spacing";
             }
             enum "1532.34" {
               description "1532.34 nm/195.64375 THz 6.25GHz spacing";
             }
             enum "1532.29" {
               description "1532.29 nm/195.65000 THz 6.25/12.5/50/75GHz spacing";
             }
             enum "1532.24" {
               description "1532.24 nm/195.65625 THz 6.25GHz spacing";
             }
             enum "1532.19" {
               description "1532.19 nm/195.66250 THz 6.25/12.5GHz spacing";
             }
             enum "1532.14" {
               description "1532.14 nm/195.66875 THz 6.25GHz spacing";
             }
             enum "1532.09" {
               description "1532.09 nm/195.67500 THz 6.25/12.5GHz spacing";
             }
             enum "1532.04" {
               description "1532.04 nm/195.68125 THz 6.25GHz spacing";
             }
             enum "1532.00" {
               description "1532.00 nm/195.68750 THz 6.25/12.5GHz spacing";
             }
             enum "1531.95" {
               description "1531.95 nm/195.69375 THz 6.25GHz spacing";
             }
             enum "1531.90" {
               description "1531.90 nm/195.70000 THz 6.25/12.5/50/100GHz spacing";
             }
             enum "1531.85" {
               description "1531.85 nm/195.70625 THz 6.25GHz spacing";
             }
             enum "1531.80" {
               description "1531.80 nm/195.71250 THz 6.25/12.5GHz spacing";
             }
             enum "1531.75" {
               description "1531.75 nm/195.71875 THz 6.25GHz spacing";
             }
             enum "1531.70" {
               description "1531.70 nm/195.72500 THz 6.25/12.5/75GHz spacing";
             }
             enum "1531.65" {
               description "1531.65 nm/195.73125 THz 6.25GHz spacing";
             }
             enum "1531.60" {
               description "1531.60 nm/195.73750 THz 6.25/12.5GHz spacing";
             }
             enum "1531.56" {
               description "1531.56 nm/195.74375 THz 6.25GHz spacing";
             }
             enum "1531.51" {
               description "1531.51 nm/195.75000 THz 6.25/12.5/50GHz spacing";
             }
             enum "1531.46" {
               description "1531.46 nm/195.75625 THz 6.25GHz spacing";
             }
             enum "1531.41" {
               description "1531.41 nm/195.76250 THz 6.25/12.5GHz spacing";
             }
             enum "1531.36" {
               description "1531.36 nm/195.76875 THz 6.25GHz spacing";
             }
             enum "1531.31" {
               description "1531.31 nm/195.77500 THz 6.25/12.5GHz spacing";
             }
             enum "1531.26" {
               description "1531.26 nm/195.78125 THz 6.25GHz spacing";
             }
             enum "1531.21" {
               description "1531.21 nm/195.78750 THz 6.25/12.5GHz spacing";
             }
             enum "1531.16" {
               description "1531.16 nm/195.79375 THz 6.25GHz spacing";
             }
             enum "1531.12" {
               description "1531.12 nm/195.80000 THz 6.25/12.5/50/75/100GHz spacing";
             }
             enum "1531.07" {
               description "1531.07 nm/195.80625 THz 6.25GHz spacing";
             }
             enum "1531.02" {
               description "1531.02 nm/195.81250 THz 6.25/12.5GHz spacing";
             }
             enum "1530.97" {
               description "1530.97 nm/195.81875 THz 6.25GHz spacing";
             }
             enum "1530.92" {
               description "1530.92 nm/195.82500 THz 6.25/12.5GHz spacing";
             }
             enum "1530.87" {
               description "1530.87 nm/195.83125 THz 6.25GHz spacing";
             }
             enum "1530.82" {
               description "1530.82 nm/195.83750 THz 6.25/12.5GHz spacing";
             }
             enum "1530.77" {
               description "1530.77 nm/195.84375 THz 6.25GHz spacing";
             }
             enum "1530.72" {
               description "1530.72 nm/195.85000 THz 6.25/12.5/50GHz spacing";
             }
             enum "1530.68" {
               description "1530.68 nm/195.85625 THz 6.25GHz spacing";
             }
             enum "1530.63" {
               description "1530.63 nm/195.86250 THz 6.25/12.5GHz spacing";
             }
             enum "1530.58" {
               description "1530.58 nm/195.86875 THz 6.25GHz spacing";
             }
             enum "1530.53" {
               description "1530.53 nm/195.87500 THz 6.25/12.5/75GHz spacing";
             }
             enum "1530.48" {
               description "1530.48 nm/195.88125 THz 6.25GHz spacing";
             }
             enum "1530.43" {
               description "1530.43 nm/195.88750 THz 6.25/12.5GHz spacing";
             }
             enum "1530.38" {
               description "1530.38 nm/195.89375 THz 6.25GHz spacing";
             }
             enum "1530.33" {
               description "1530.33 nm/195.90000 THz 6.25/12.5/50/100GHz spacing";
             }
             enum "1530.29" {
               description "1530.29 nm/195.90625 THz 6.25GHz spacing";
             }
             enum "1530.24" {
               description "1530.24 nm/195.91250 THz 6.25/12.5GHz spacing";
             }
             enum "1530.19" {
               description "1530.19 nm/195.91875 THz 6.25GHz spacing";
             }
             enum "1530.14" {
               description "1530.14 nm/195.92500 THz 6.25/12.5GHz spacing";
             }
             enum "1530.09" {
               description "1530.09 nm/195.93125 THz 6.25GHz spacing";
             }
             enum "1530.04" {
               description "1530.04 nm/195.93750 THz 6.25/12.5GHz spacing";
             }
             enum "1529.99" {
               description "1529.99 nm/195.94375 THz 6.25GHz spacing";
             }
             enum "1529.94" {
               description "1529.94 nm/195.95000 THz 6.25/12.5/50/75GHz spacing";
             }
             enum "1529.89" {
               description "1529.89 nm/195.95625 THz 6.25GHz spacing";
             }
             enum "1529.85" {
               description "1529.85 nm/195.96250 THz 6.25/12.5GHz spacing";
             }
             enum "1529.80" {
               description "1529.80 nm/195.96875 THz 6.25GHz spacing";
             }
             enum "1529.75" {
               description "1529.75 nm/195.97500 THz 6.25/12.5GHz spacing";
             }
             enum "1529.70" {
               description "1529.70 nm/195.98125 THz 6.25GHz spacing";
             }
             enum "1529.65" {
               description "1529.65 nm/195.98750 THz 6.25/12.5GHz spacing";
             }
             enum "1529.60" {
               description "1529.60 nm/195.99375 THz 6.25GHz spacing";
             }
             enum "1529.55" {
               description "1529.55 nm/196.00000 THz 6.25/12.5/50/100GHz spacing";
             }
             enum "1529.50" {
               description "1529.50 nm/196.00625 THz 6.25GHz spacing";
             }
             enum "1529.46" {
               description "1529.46 nm/196.01250 THz 6.25/12.5GHz spacing";
             }
             enum "1529.41" {
               description "1529.41 nm/196.01875 THz 6.25GHz spacing";
             }
             enum "1529.36" {
               description "1529.36 nm/196.02500 THz 6.25/12.5/75GHz spacing";
             }
             enum "1529.31" {
               description "1529.31 nm/196.03125 THz 6.25GHz spacing";
             }
             enum "1529.26" {
               description "1529.26 nm/196.03750 THz 6.25/12.5GHz spacing";
             }
             enum "1529.21" {
               description "1529.21 nm/196.04375 THz 6.25GHz spacing";
             }
             enum "1529.16" {
               description "1529.16 nm/196.05000 THz 6.25/12.5/50GHz spacing";
             }
             enum "1529.11" {
               description "1529.11 nm/196.05625 THz 6.25GHz spacing";
             }
             enum "1529.07" {
               description "1529.07 nm/196.06250 THz 6.25/12.5GHz spacing";
             }
             enum "1529.02" {
               description "1529.02 nm/196.06875 THz 6.25GHz spacing";
             }
             enum "1528.97" {
               description "1528.97 nm/196.07500 THz 6.25/12.5GHz spacing";
             }
             enum "1528.92" {
               description "1528.92 nm/196.08125 THz 6.25GHz spacing";
             }
             enum "1528.87" {
               description "1528.87 nm/196.08750 THz 6.25/12.5GHz spacing";
             }
             enum "1528.82" {
               description "1528.82 nm/196.09375 THz 6.25GHz spacing";
             }
             enum "1528.77" {
               description "1528.77 nm/196.10000 THz 6.25/12.5/50/75/100GHz spacing";
             }
             enum "1528.38" {
               description "1528.38 nm/196.15040 THz 50Ghz spacing";
             }
           }
         }
         uses apply-advanced;
         choice wss {
           case case_1 {
             container switch {
               presence "enable switch";
               description "Switch the wavelength to an optical interface";
               uses apply-advanced;
               leaf interface-name {
                 description "Name of physical interface";
                 type string;
               }
             }
           }
           case case_2 {
             leaf wss-express-in {
               description "Express-in this wavelength to another optical card";
               type empty;
             }
           }
         }
       }
       container tca {
         description "Set tca for optical properties";
         uses apply-advanced;
         container osc-tx-power-high-tca {
           description "OSC TX power high TCA";
           uses apply-advanced;
           choice enable-tca-choice {
             leaf enable-tca {
               description "Enable tca";
               type empty;
             }
             leaf no-enable-tca {
               description "Don't enable tca";
               type empty;
             }
           }
           leaf threshold {
             description "Threshold for 15 minute osc tx power high TCA in dBm";
             type string;
           }
           leaf threshold-24hrs {
             description "Threshold for 24 hour osc tx power high TCA in dBm";
             type string;
           }
         }
         container osc-tx-power-low-tca {
           description "OSC TX power low TCA";
           uses apply-advanced;
           choice enable-tca-choice {
             leaf enable-tca {
               description "Enable tca";
               type empty;
             }
             leaf no-enable-tca {
               description "Don't enable tca";
               type empty;
             }
           }
           leaf threshold {
             description "Threshold for 15 minute osc tx power low TCA in dBm";
             type string;
           }
           leaf threshold-24hrs {
             description "Threshold for 24 hour osc tx power low TCA in dBm";
             type string;
           }
         }
         container osc-rx-power-high-tca {
           description "OSC RX power high TCA";
           uses apply-advanced;
           choice enable-tca-choice {
             leaf enable-tca {
               description "Enable tca";
               type empty;
             }
             leaf no-enable-tca {
               description "Don't enable tca";
               type empty;
             }
           }
           leaf threshold {
             description "Threshold for 15 minute osc rx power high TCA in dBm";
             type string;
           }
           leaf threshold-24hrs {
             description "Threshold for 24 hour osc rx power high TCA in dBm";
             type string;
           }
         }
         container osc-rx-power-low-tca {
           description "OSC RX power low TCA";
           uses apply-advanced;
           choice enable-tca-choice {
             leaf enable-tca {
               description "Enable tca";
               type empty;
             }
             leaf no-enable-tca {
               description "Don't enable tca";
               type empty;
             }
           }
           leaf threshold {
             description "Threshold for 15 minute osc rx power low TCA in dBm";
             type string;
           }
           leaf threshold-24hrs {
             description "Threshold for 24 hour osc rx power low TCA in dBm";
             type string;
           }
         }
         container osc-fiber-loss-high-tca {
           description "OSC fiber loss high TCA";
           uses apply-advanced;
           choice enable-tca-choice {
             leaf enable-tca {
               description "Enable tca";
               type empty;
             }
             leaf no-enable-tca {
               description "Don't enable tca";
               type empty;
             }
           }
           leaf threshold {
             description "Threshold for 15 minute osc fiber loss high TCA in dB";
             type string;
           }
           leaf threshold-24hrs {
             description "Threshold for 24 hour osc fiber loss high TCA in dB";
             type string;
           }
         }
         container osc-fiber-loss-low-tca {
           description "OSC fiber loss low TCA";
           uses apply-advanced;
           choice enable-tca-choice {
             leaf enable-tca {
               description "Enable tca";
               type empty;
             }
             leaf no-enable-tca {
               description "Don't enable tca";
               type empty;
             }
           }
           leaf threshold {
             description "Threshold for 15 minute osc fiber loss low TCA in dB";
             type string;
           }
           leaf threshold-24hrs {
             description "Threshold for 24 hour osc fiber loss low TCA in dB";
             type string;
           }
         }
         container lout-voa-high-tca {
           description "LOUT VOA high TCA";
           uses apply-advanced;
           choice enable-tca-choice {
             leaf enable-tca {
               description "Enable tca";
               type empty;
             }
             leaf no-enable-tca {
               description "Don't enable tca";
               type empty;
             }
           }
           leaf threshold {
             description "Threshold for 15 minute LOUT VOA high TCA in dB";
             type string;
           }
           leaf threshold-24hrs {
             description "Threshold for 24 hour LOUT VOA high TCA in dB";
             type string;
           }
         }
         container lout-voa-low-tca {
           description "LOUT VOA low TCA";
           uses apply-advanced;
           choice enable-tca-choice {
             leaf enable-tca {
               description "Enable tca";
               type empty;
             }
             leaf no-enable-tca {
               description "Don't enable tca";
               type empty;
             }
           }
           leaf threshold {
             description "Threshold for 15 minute LOUT VOA low TCA in dB";
             type string;
           }
           leaf threshold-24hrs {
             description "Threshold for 24 hour LOUT VOA low TCA in dB";
             type string;
           }
         }
         container edfa1-in-power-high-tca {
           description "Ingress EDFA input power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA input power high TCA in dBm";
             type string;
           }
           leaf threshold-24hrs {
             description "Threshold for 24 hour Ingress EDFA input power high TCA in dBm";
             type string;
           }
         }
         container edfa1-in-power-low-tca {
           description "Ingress EDFA input power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA input power low TCA in dBm";
             type string;
           }
           leaf threshold-24hrs {
             description "Threshold for 24 hour Ingress EDFA input power low TCA in dBm";
             type string;
           }
         }
         container edfa1-out-power-high-tca {
           description "Ingress EDFA output power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA output power high TCA in dBm";
             type string;
           }
           leaf threshold-24hrs {
             description "Threshold for 24 hour Ingress EDFA output power high TCA in dBm";
             type string;
           }
         }
         container edfa1-out-power-low-tca {
           description "Ingress EDFA output power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA output power low TCA in dBm";
             type string;
           }
           leaf threshold-24hrs {
             description "Threshold for 24 hour Ingress EDFA output power low TCA in dBm";
             type string;
           }
         }
         container edfa1-sig-power-high-tca {
           description "Ingress EDFA signal power high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA signal power high TCA in dBm";
             type string;
           }
           leaf threshold-24hrs {
             description "Threshold for 24 hour Ingress EDFA signal power high TCA in dBm";
             type string;
           }
         }
         container edfa1-sig-power-low-tca {
           description "Ingress EDFA signal power low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA signal power low TCA in dBm";
             type string;
           }
           leaf threshold-24hrs {
             description "Threshold for 24 hour Ingress EDFA signal power low TCA in dBm";
             type string;
           }
         }
         container edfa1-awg-high-tca {
           description "Ingress EDFA pump AWG high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump AWG high TCA in mW";
             type string;
           }
           leaf threshold-24hrs {
             description "Threshold for 24 hour Ingress EDFA pump AWG high TCA in mW";
             type string;
           }
         }
         container edfa1-awg-low-tca {
           description "Ingress EDFA pump AWG low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump AWG low TCA in mW";
             type string;
           }
           leaf threshold-24hrs {
             description "Threshold for 24 hour Ingress EDFA pump AWG low TCA in mW";
             type string;
           }
         }
         container edfa1-express-high-tca {
           description "Ingress EDFA pump express high TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump express high TCA in mW";
             type string;
           }
           leaf threshold-24hrs {
             description "Threshold for 24 hour Ingress EDFA pump express high TCA in mW";
             type string;
           }
         }
         container edfa1-express-low-tca {
           description "Ingress EDFA pump express low TCA";
           uses apply-advanced;
           choice enable-tca-choice {
             leaf enable-tca {
               description "Enable tca";
               type empty;
             }
             leaf no-enable-tca {
               description "Don't enable tca";
               type empty;
             }
           }
           leaf threshold {
             description "Threshold for 15 minute Ingress EDFA pump express low TCA in mW";
             type string;
           }
           leaf threshold-24hrs {
             description "Threshold for 24 hour Ingress EDFA pump express low TCA in mW";
             type string;
           }
         }
         container edfa2-in-power-high-tca {
           description "Egress EDFA input power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA input power high TCA in dBm";
             type string;
           }
           leaf threshold-24hrs {
             description "Threshold for 24 hour Egress EDFA input power high TCA in dBm";
             type string;
           }
         }
         container edfa2-in-power-low-tca {
           description "Egress EDFA input power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA input power low TCA in dBm";
             type string;
           }
           leaf threshold-24hrs {
             description "Threshold for 24 hour Egress EDFA input power low TCA in dBm";
             type string;
           }
         }
         container edfa2-out-power-high-tca {
           description "Egress EDFA output power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA output power high TCA in dBm";
             type string;
           }
           leaf threshold-24hrs {
             description "Threshold for 24 hour Egress EDFA output power high TCA in dBm";
             type string;
           }
         }
         container edfa2-out-power-low-tca {
           description "Egress EDFA output power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA output power low TCA in dBm";
             type string;
           }
           leaf threshold-24hrs {
             description "Threshold for 24 hour Egress EDFA output power low TCA in dBm";
             type string;
           }
         }
         container edfa2-sig-power-high-tca {
           description "Egress EDFA signal power high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA signal power high TCA in dBm";
             type string;
           }
           leaf threshold-24hrs {
             description "Threshold for 24 hour Egress EDFA signal power high TCA in dBm";
             type string;
           }
         }
         container edfa2-sig-power-low-tca {
           description "Egress EDFA signal power low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA signal power low TCA in dBm";
             type string;
           }
           leaf threshold-24hrs {
             description "Threshold for 24 hour Egress EDFA signal power low TCA in dBm";
             type string;
           }
         }
         container edfa2-awg-high-tca {
           description "Egress EDFA pump AWG high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump AWG high TCA in mW";
             type string;
           }
           leaf threshold-24hrs {
             description "Threshold for 24 hour Egress EDFA pump AWG high TCA in mW";
             type string;
           }
         }
         container edfa2-awg-low-tca {
           description "Egress EDFA pump AWG low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump AWG low TCA in mW";
             type string;
           }
           leaf threshold-24hrs {
             description "Threshold for 24 hour Egress EDFA pump AWG low TCA in mW";
             type string;
           }
         }
         container edfa2-express-high-tca {
           description "Egress EDFA pump express high TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump express high TCA in mW";
             type string;
           }
           leaf threshold-24hrs {
             description "Threshold for 24 hour Egress EDFA pump express high TCA in mW";
             type string;
           }
         }
         container edfa2-express-low-tca {
           description "Egress EDFA pump express low TCA";
           uses apply-advanced;
           choice enable-tca-choice {
             leaf enable-tca {
               description "Enable tca";
               type empty;
             }
             leaf no-enable-tca {
               description "Don't enable tca";
               type empty;
             }
           }
           leaf threshold {
             description "Threshold for 15 minute Egress EDFA pump express low TCA in mW";
             type string;
           }
           leaf threshold-24hrs {
             description "Threshold for 24 hour Egress EDFA pump express low TCA in mW";
             type string;
           }
         }
         container ocm-power-high-line-out-tca {
           description "OCM Power Line Out high TCA";
           uses apply-advanced;
           choice enable-tca-choice {
             leaf enable-tca {
               description "Enable tca";
               type empty;
             }
             leaf no-enable-tca {
               description "Don't enable tca";
               type empty;
             }
           }
           leaf threshold {
             description "Threshold for 15 minute OCM Power high TCA in dBm";
             type string;
           }
           leaf threshold-24hrs {
             description "Threshold for 24 hour OCM Power high TCA in dBm";
             type string;
           }
         }
         container ocm-power-low-line-out-tca {
           description "OCM Power Line Out low TCA";
           uses apply-advanced;
           choice enable-tca-choice {
             leaf enable-tca {
               description "Enable tca";
               type empty;
             }
             leaf no-enable-tca {
               description "Don't enable tca";
               type empty;
             }
           }
           leaf threshold {
             description "Threshold for 15 minute OCM Power low TCA in dBm";
             type string;
           }
           leaf threshold-24hrs {
             description "Threshold for 24 hour OCM Power low TCA in dBm";
             type string;
           }
         }
       }
       container expansion-card {
         description "Associate an expansion card with the IPLC card";
         uses apply-advanced;
         container fpc {
           presence "enable fpc";
           uses apply-advanced;
           leaf fpc-slot {
             type union {
               type string {
                 pattern "<.*>|$.*";
               }
               type uint32;
             }
           }
         }
       }
       container express-in {
         description "Associate an express-in card with the IPLC card";
         uses apply-advanced;
         container fpc {
           presence "enable fpc";
           uses apply-advanced;
           leaf fpc-slot {
             type union {
               type string {
                 pattern "<.*>|$.*";
               }
               type uint32;
             }
           }
         }
       }
       container amplifier-chain {
         description "In-line amplifier options";
         uses apply-advanced;
         choice anchor-iplc-choice {
           leaf anchor-iplc {
             description "Mark IPLC as anchor for In-line amplifier chain";
             type empty;
           }
           leaf no-anchor-iplc {
             description "Don't mark IPLC as anchor for In-line amplifier chain";
             type empty;
           }
         }
         leaf osc-ip {
           description "IPLC OSC path IPv4 address format w.x.y.z/a";
           type string;
         }
         leaf osc-mac {
           description "IPLC OSC path MAC address format a:b:c:d:e:f";
           type string;
         }
         list ila {
           key name;
           description "Configure In-line amplifier number";
           leaf name {
             description "In-line amplifier Chain position number";
             type union {
               type string {
                 pattern "<.*>|$.*";
               }
               type uint32 {
                 range "0 .. 14";
               }
             }
           }
           uses apply-advanced;
           container ila-options {
             description "In-line amplifier settings";
             uses apply-advanced;
             leaf ila-ipv4-address {
               description "In-line amplifier IPV4 address format w.x.y.z/a";
               type string;
             }
             leaf ila-user {
               description "ILA User Name";
               type string;
             }
             leaf ila-password {
               description "ILA password string";
               type jt:unreadable;
             }
             container edfa-a-b {
               description "Configure edfa-a-b";
               uses apply-advanced;
               container tca-input-power-low {
                 description "Input power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power low TCA in dBm";
                   type string;
                 }
                 leaf threshold-24hrs {
                   description "Threshold for 24 hour input power low TCA in dBm";
                   type string;
                 }
               }
               container tca-input-power-high {
                 description "Input power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power high TCA in dBm";
                   type string;
                 }
                 leaf threshold-24hrs {
                   description "Threshold for 24 hour input power high TCA in dBm";
                   type string;
                 }
               }
               container tca-output-power-low {
                 description "Output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power low TCA in dBm";
                   type string;
                 }
                 leaf threshold-24hrs {
                   description "Threshold for 24 hour output power low TCA in dBm";
                   type string;
                 }
               }
               container tca-output-power-high {
                 description "Output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power high TCA in dBm";
                   type string;
                 }
                 leaf threshold-24hrs {
                   description "Threshold for 24 hour output power high TCA in dBm";
                   type string;
                 }
               }
               container tca-signal-output-power-low {
                 description "Signal output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power low TCA in dBm";
                   type string;
                 }
                 leaf threshold-24hrs {
                   description "Threshold for 24 hour signal output power low TCA in dBm";
                   type string;
                 }
               }
               container tca-signal-output-power-high {
                 description "Signal output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power high TCA in dBm";
                   type string;
                 }
                 leaf threshold-24hrs {
                   description "Threshold for 24 hour signal output power high TCA in dBm";
                   type string;
                 }
               }
               container tca-pump0-current-low {
                 description "Pump0 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current low TCA in mA";
                   type string;
                 }
                 leaf threshold-24hrs {
                   description "Threshold for 24 hour pump0 current low TCA in mA";
                   type string;
                 }
               }
               container tca-pump0-current-high {
                 description "Pump0 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current high TCA in mA";
                   type string;
                 }
                 leaf threshold-24hrs {
                   description "Threshold for 24 hour pump0 current high TCA in mA";
                   type string;
                 }
               }
               container tca-pump1-current-low {
                 description "Pump1 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current low TCA in mA";
                   type string;
                 }
                 leaf threshold-24hrs {
                   description "Threshold for 24 hour pump1 current low TCA in mA";
                   type string;
                 }
               }
               container tca-pump1-current-high {
                 description "Pump1 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current high TCA in mA";
                   type string;
                 }
                 leaf threshold-24hrs {
                   description "Threshold for 24 hour pump1 current high TCA in mA";
                   type string;
                 }
               }
               container tca-pump0-temperature-low {
                 description "Pump0 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature low TCA in C";
                   type string;
                 }
                 leaf threshold-24hrs {
                   description "Threshold for 24 hour pump0 temperature low TCA in C";
                   type string;
                 }
               }
               container tca-pump0-temperature-high {
                 description "Pump0 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature high TCA in C";
                   type string;
                 }
                 leaf threshold-24hrs {
                   description "Threshold for 24 hour pump0 temperature high TCA in C";
                   type string;
                 }
               }
               container tca-pump1-temperature-low {
                 description "Pump1 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature low TCA in C";
                   type string;
                 }
                 leaf threshold-24hrs {
                   description "Threshold for 24 hour pump1 temperature low TCA in C";
                   type string;
                 }
               }
               container tca-pump1-temperature-high {
                 description "Pump1 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature high TCA in C";
                   type string;
                 }
                 leaf threshold-24hrs {
                   description "Threshold for 24 hour pump1 temperature high TCA in C";
                   type string;
                 }
               }
             }
             container voa-a {
               description "Configure voa-a";
               uses apply-advanced;
               container tca-attenuation-low {
                 description "Attenuation low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation low TCA in dBm";
                   type string;
                 }
                 leaf threshold-24hrs {
                   description "Threshold for 24 hour attenuation low TCA in dBm";
                   type string;
                 }
               }
               container tca-attenuation-high {
                 description "Attenuation high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation high TCA in dBm";
                   type string;
                 }
                 leaf threshold-24hrs {
                   description "Threshold for 24 hour attenuation high TCA in dBm";
                   type string;
                 }
               }
             }
             container osc-a {
               description "Configure osc-a";
               uses apply-advanced;
               container osc-tx-power-high-tca {
                 description "OSC TX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power high TCA in dBm";
                   type string;
                 }
                 leaf threshold-24hrs {
                   description "Threshold for 24 hour osc tx power high TCA in dBm";
                   type string;
                 }
               }
               container osc-tx-power-low-tca {
                 description "OSC TX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power low TCA in dBm";
                   type string;
                 }
                 leaf threshold-24hrs {
                   description "Threshold for 24 hour osc tx power low TCA in dBm";
                   type string;
                 }
               }
               container osc-rx-power-high-tca {
                 description "OSC RX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power high TCA in dBm";
                   type string;
                 }
                 leaf threshold-24hrs {
                   description "Threshold for 24 hour osc rx power high TCA in dBm";
                   type string;
                 }
               }
               container osc-rx-power-low-tca {
                 description "OSC RX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power low TCA in dBm";
                   type string;
                 }
                 leaf threshold-24hrs {
                   description "Threshold for 24 hour osc rx power low TCA in dBm";
                   type string;
                 }
               }
               container osc-fiber-loss-high-tca {
                 description "OSC fiber loss high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss high TCA in dBm";
                   type string;
                 }
                 leaf threshold-24hrs {
                   description "Threshold for 24 hour osc fiber loss high TCA in dBm";
                   type string;
                 }
               }
               container osc-fiber-loss-low-tca {
                 description "OSC fiber loss low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss low TCA in dBm";
                   type string;
                 }
                 leaf threshold-24hrs {
                   description "Threshold for 24 hour osc fiber loss low TCA in dBm";
                   type string;
                 }
               }
             }
             container edfa-b-a {
               description "Configure edfa-b-a";
               uses apply-advanced;
               container tca-input-power-low {
                 description "Input power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power low TCA in dBm";
                   type string;
                 }
                 leaf threshold-24hrs {
                   description "Threshold for 24 hour input power low TCA in dBm";
                   type string;
                 }
               }
               container tca-input-power-high {
                 description "Input power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute input power high TCA in dBm";
                   type string;
                 }
                 leaf threshold-24hrs {
                   description "Threshold for 24 hour input power high TCA in dBm";
                   type string;
                 }
               }
               container tca-output-power-low {
                 description "Output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power low TCA in dBm";
                   type string;
                 }
                 leaf threshold-24hrs {
                   description "Threshold for 24 hour output power low TCA in dBm";
                   type string;
                 }
               }
               container tca-output-power-high {
                 description "Output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute output power high TCA in dBm";
                   type string;
                 }
                 leaf threshold-24hrs {
                   description "Threshold for 24 hour output power high TCA in dBm";
                   type string;
                 }
               }
               container tca-signal-output-power-low {
                 description "Signal output power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power low TCA in dBm";
                   type string;
                 }
                 leaf threshold-24hrs {
                   description "Threshold for 24 hour signal output power low TCA in dBm";
                   type string;
                 }
               }
               container tca-signal-output-power-high {
                 description "Signal output power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute signal output power high TCA in dBm";
                   type string;
                 }
                 leaf threshold-24hrs {
                   description "Threshold for 24 hour signal output power high TCA in dBm";
                   type string;
                 }
               }
               container tca-pump0-current-low {
                 description "Pump0 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current low TCA in dBm";
                   type string;
                 }
                 leaf threshold-24hrs {
                   description "Threshold for 24 hour pump0 current low TCA in dBm";
                   type string;
                 }
               }
               container tca-pump0-current-high {
                 description "Pump0 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 current high TCA in dBm";
                   type string;
                 }
                 leaf threshold-24hrs {
                   description "Threshold for 24 hour pump0 current high TCA in dBm";
                   type string;
                 }
               }
               container tca-pump1-current-low {
                 description "Pump1 current low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current low TCA in dBm";
                   type string;
                 }
                 leaf threshold-24hrs {
                   description "Threshold for 24 hour pump1 current low TCA in dBm";
                   type string;
                 }
               }
               container tca-pump1-current-high {
                 description "Pump1 current high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 current high TCA in dBm";
                   type string;
                 }
                 leaf threshold-24hrs {
                   description "Threshold for 24 hour pump1 current high TCA in dBm";
                   type string;
                 }
               }
               container tca-pump0-temperature-low {
                 description "Pump0 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature low TCA in C";
                   type string;
                 }
                 leaf threshold-24hrs {
                   description "Threshold for 24 hour pump0 temperature low TCA in C";
                   type string;
                 }
               }
               container tca-pump0-temperature-high {
                 description "Pump0 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump0 temperature high TCA in C";
                   type string;
                 }
                 leaf threshold-24hrs {
                   description "Threshold for 24 hour pump0 temperature high TCA in C";
                   type string;
                 }
               }
               container tca-pump1-temperature-low {
                 description "Pump1 temperature low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature low TCA in C";
                   type string;
                 }
                 leaf threshold-24hrs {
                   description "Threshold for 24 hour pump1 temperature low TCA in C";
                   type string;
                 }
               }
               container tca-pump1-temperature-high {
                 description "Pump1 temperature high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute pump1 temperature high TCA in C";
                   type string;
                 }
                 leaf threshold-24hrs {
                   description "Threshold for 24 hour pump1 temperature high TCA in C";
                   type string;
                 }
               }
             }
             container voa-b {
               description "Configure voa-b";
               uses apply-advanced;
               container tca-attenuation-low {
                 description "Attenuation low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation low TCA in dBm";
                   type string;
                 }
                 leaf threshold-24hrs {
                   description "Threshold for 24 hour attenuation low TCA in dBm";
                   type string;
                 }
               }
               container tca-attenuation-high {
                 description "Attenuation high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute attenuation high TCA in dBm";
                   type string;
                 }
                 leaf threshold-24hrs {
                   description "Threshold for 24 hour attenuation high TCA in dBm";
                   type string;
                 }
               }
             }
             container osc-b {
               description "Configure osc-b";
               uses apply-advanced;
               container osc-tx-power-high-tca {
                 description "OSC TX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power high TCA in dBm";
                   type string;
                 }
                 leaf threshold-24hrs {
                   description "Threshold for 24 hour osc tx power high TCA in dBm";
                   type string;
                 }
               }
               container osc-tx-power-low-tca {
                 description "OSC TX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc tx power low TCA in dBm";
                   type string;
                 }
                 leaf threshold-24hrs {
                   description "Threshold for 24 hour osc tx power low TCA in dBm";
                   type string;
                 }
               }
               container osc-rx-power-high-tca {
                 description "OSC RX power high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power high TCA in dBm";
                   type string;
                 }
                 leaf threshold-24hrs {
                   description "Threshold for 24 hour osc rx power high TCA in dBm";
                   type string;
                 }
               }
               container osc-rx-power-low-tca {
                 description "OSC RX power low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc rx power low TCA in dBm";
                   type string;
                 }
                 leaf threshold-24hrs {
                   description "Threshold for 24 hour osc rx power low TCA in dBm";
                   type string;
                 }
               }
               container osc-fiber-loss-high-tca {
                 description "OSC fiber loss high TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss high TCA in dBm";
                   type string;
                 }
                 leaf threshold-24hrs {
                   description "Threshold for 24 hour osc fiber loss high TCA in dBm";
                   type string;
                 }
               }
               container osc-fiber-loss-low-tca {
                 description "OSC fiber loss low TCA";
                 uses apply-advanced;
                 choice enable-tca-choice {
                   leaf enable-tca {
                     description "Enable tca";
                     type empty;
                   }
                   leaf no-enable-tca {
                     description "Don't enable tca";
                     type empty;
                   }
                 }
                 leaf threshold {
                   description "Threshold for 15 minute osc fiber loss low TCA in dBm";
                   type string;
                 }
                 leaf threshold-24hrs {
                   description "Threshold for 24 hour osc fiber loss low TCA in dBm";
                   type string;
                 }
               }
             }
           }
         }
       }
     }
     leaf power {
       description "Power FPCs on or off";
       type enumeration {
         enum "off" {
           description "Do not provide power to FPCs";
         }
         enum "on" {
           description "Provide power to FPCs";
         }
       }
     }
     leaf no-vlan-tagging {
       description "Disable vlan support on FPC with default tpid 0x8100";
       type empty;
     }
     container traffic-manager {
       description "Configure traffic-manager attributes";
       uses apply-advanced;
       container queue-threshold {
         description "Set queue thresholds";
         uses apply-advanced;
         container fabric-queue {
           description "Set fabric queue thresholds";
           uses apply-advanced;
           list priority {
             key name;
             ordered-by user;
             description "Queue priority";
             leaf name {
               description "Priority level";
               type enumeration {
                 enum "low" {
                   description "Low fabric priority";
                 }
                 enum "high" {
                   description "High fabric priority";
                 }
               }
             }
             uses apply-advanced;
             leaf threshold {
               description "Threshold percentage to be set";
               type union {
                 type string {
                   pattern "<.*>|$.*";
                 }
                 type uint32 {
                   range "1 .. 100";
                 }
               }
             }
           }
         }
         container wan-queue {
           description "Set wan queue thresholds";
           uses apply-advanced;
           list priority {
             key name;
             ordered-by user;
             description "Queue Priority";
             leaf name {
               description "Priority level";
               type enumeration {
                 enum "low" {
                   description "Low wan priority";
                 }
                 enum "medium-low" {
                   description "Medium low wan priority";
                 }
                 enum "medium-high" {
                   description "Medium high wan priority";
                 }
                 enum "high" {
                   description "High wan priority";
                 }
               }
             }
             uses apply-advanced;
             leaf threshold {
               description "Threshold percentage to be set";
               type union {
                 type string {
                   pattern "<.*>|$.*";
                 }
                 type uint32 {
                   range "1 .. 100";
                 }
               }
             }
           }
         }
       }
       choice enhanced-priority-mode-choice {
         leaf enhanced-priority-mode {
           description "Enable enhanced priority mode";
           type empty;
         }
         leaf no-enhanced-priority-mode {
           description "Don't enable enhanced priority mode";
           type empty;
         }
       }
       leaf packet-timestamp {
         description "Configure collecting CoS last packet enqueued timestamp";
         default "disable";
         type enumeration {
           enum "enable" {
             description "Enables collecting CoS last packet enqueued timestamp";
           }
           enum "disable" {
             description "Disables collecting CoS last packet enqueued timestamp";
           }
         }
       }
     }
     leaf max-power {
       description "Max power to be consumed by MPC";
       type union {
         type uint32;
         type string {
           pattern "<.*>|$.*";
         }
       }
     }
     leaf route-localization {
       description "Route-Localization fib-remote or fib-local";
       type enumeration {
         enum "fib-remote" {
           description "Route-Localization fib-remote";
         }
         enum "fib-local" {
           description "Route-Localization fib-local";
         }
       }
     }
     leaf vpn-localization {
       description "VPN-localization core-facing-only  or core-facing-default";
       type enumeration {
         enum "vpn-core-facing-only" {
           description "VPN core-facing-fpc which has no vpn-label state";
         }
         enum "vpn-core-facing-default" {
           description "VPN core-facing-fpc which has all the state";
         }
       }
     }
     leaf power-budget-priority {
       description "FPC priority number";
       type union {
         type string {
           pattern "<.*>|$.*";
         }
         type uint32;
       }
     }
     choice mode {
       case case_1 {
         leaf disable-power {
           description "Do not provide power to the card";
           status deprecated;
           type empty;
         }
       }
       case case_2 {
         leaf allow-sram-parity-errors {
           description "Do not power cycle FPC when SRAM parity errors occur";
           type empty;
         }
       }
     }
     choice riot-mode {
       case case_1 {
         container performance-mode {
           presence "enable performance-mode";
           description "Enable performance mode, FPC will restart if mode changes from lite mode to performance mode";
           uses apply-advanced;
           leaf number-of-ucode-workers {
             description "Configure number of ucode worker cores, FPC will restart if there is a change in number of ucode worker cores";
             default "0";
             type union {
               type string {
                 pattern "<.*>|$.*";
               }
               type uint32 {
                 range "0 .. 100";
               }
             }
           }
         }
       }
       case case_2 {
         leaf lite-mode {
           description "Enable lite mode, FPC will restart if mode changes from performance mode to lite mode";
           type empty;
         }
       }
     }
     leaf cfp-to-et {
       description "Enable ET interface and remove CFP client";
       type empty;
     }
     container lossless-flow-control {
       presence "enable lossless-flow-control";
       description "Lossless buffer config for Ethernet Mac pause";
       uses apply-advanced;
       choice enable_choice {
         case case_1 {
           leaf lossless-flow-control-enable {
             description "Enable Lossless buffer config for Ethernet Mac pause";
             type empty;
           }
         }
         case case_2 {
           leaf no-lossless-flow-control-enable {
             description "Disable Lossless buffer config for Ethernet Mac pause";
             type empty;
           }
         }
       }
     }
     leaf offline {
       description "Keep FPC offline";
       type empty;
     }
     leaf offline-on-fabric-bandwidth-reduction {
       description "Bring FPC offline when running with reduced fabric bandwidth";
       type empty;
     }
     leaf ir-mode {
       description "Configure IR or R mode for MPC4 and above cards";
       type enumeration {
         enum "IR" {
           description "Set IR mode";
         }
         enum "R" {
           description "Set R mode";
         }
       }
     }
     container no-loss {
       description "PFC lossless buffer configuratios";
       uses apply-advanced;
       container buffer {
         description "PFC lossless buffer";
         uses apply-advanced;
         leaf percentage {
           description "Configure buffer space for lossless traffic handling";
           units "percent";
           type union {
             type string {
               pattern "<.*>|$.*";
             }
             type uint32 {
               range "1 .. 100";
             }
           }
         }
       }
     }
     leaf license-mode {
       description "Configure license mode for PTX FPC3 and later cards";
       type enumeration {
         enum "r" {
           description "Set card to R mode";
         }
         enum "ir" {
           description "Set card to IR mode";
         }
         enum "lsr" {
           description "Set card to LSR mode";
         }
         enum "ip" {
           description "Set card to full IP mode";
         }
       }
     }
     container fabric {
       presence "enable fabric";
       uses apply-advanced;
       container loopback {
         presence "enable loopback";
         description "Set fpc fabric loopback mode";
         uses apply-advanced;
         leaf wan {
           description "Enable/Disable fpc fabric  wan loopback";
           type enumeration {
             enum "off" {
               description "Disable fpc fabric wan loopback";
             }
             enum "on" {
               description "Enable fpc fabric wan loopback";
             }
           }
         }
       }
       leaf blackhole-action {
         description "Action taken upon fabric plane blackhole involving the FPC";
         type enumeration {
           enum "log-only" {
             description "Log the detected blackhole condition";
           }
           enum "offline" {
             description "Offline the FPC";
           }
           enum "restart" {
             description "Restart the FPC";
           }
           enum "restart-then-offline" {
             description "Restart the FPC and offline in subsequent action. ";
           }
         }
       }
       container bandwidth-degradation {
         description "Take FPC recovery action when FPC running with reduced fabric bandwidth";
         uses apply-advanced;
         leaf percentage {
           description "The percentage of PFE bandwidth degradation to trigger action";
           type union {
             type string {
               pattern "<.*>|$.*";
             }
             type uint32 {
               range "1 .. 99";
             }
           }
         }
         leaf no-fabric-switchover {
           description "Do not perform switchover to spare CB";
           type empty;
         }
         leaf action {
           description "Type of action to trigger";
           type enumeration {
             enum "log-only" {
               description "Log the bandwidth degradation only";
             }
             enum "offline" {
               description "Offline the FPC, default action";
             }
             enum "restart" {
               description "Restart the FPC";
             }
             enum "restart-then-offline" {
               description "Restart the FPC and offline in subsequent action";
             }
           }
         }
       }
     }
     list port-mirror-instance {
       key name;
       ordered-by user;
       max-elements 2;
       leaf name {
         description "Associate a port mirroring instance with the FPC";
         type string {
           length "1 .. 64";
         }
       }
       uses apply-advanced;
     }
     list sampling-instance {
       key name;
       ordered-by user;
       max-elements 1;
       leaf name {
         description "Associate a sampling instance with the FPC";
         type string {
           length "1 .. 64";
         }
       }
       uses apply-advanced;
     }
     container inline-services {
       uses apply-advanced;
       leaf report-zero-oif-gw-on-discard {
         description "Jflow reports value zero in OIF and GW when traffic is not forwarded";
         type empty;
       }
       leaf flex-flow-sizing {
         description "No fixed size allocation of flow tables for proto families";
         type empty;
       }
       leaf use-extended-flow-memory {
         description "Use extended memory for flow records";
         type empty;
       }
       container flow-table-size {
         uses apply-advanced;
         leaf ipv4-flow-table-size {
           description "IPv4 flow table size in units of 256k";
           type union {
             type string {
               pattern "<.*>|$.*";
             }
             type uint32 {
               range "1 .. 245";
             }
           }
         }
         leaf ipv6-flow-table-size {
           description "IPv6 flow table size in units of 256k";
           type union {
             type string {
               pattern "<.*>|$.*";
             }
             type uint32 {
               range "1 .. 245";
             }
           }
         }
         leaf vpls-flow-table-size {
           description "VPLS flow table size in units of 256k";
           status deprecated;
           type union {
             type string {
               pattern "<.*>|$.*";
             }
             type uint32 {
               range "1 .. 245";
             }
           }
         }
         leaf bridge-flow-table-size {
           description "BRIDGE flow table size in units of 256k";
           type union {
             type string {
               pattern "<.*>|$.*";
             }
             type uint32 {
               range "1 .. 245";
             }
           }
         }
         leaf ipv6-extended-attrib {
           description "Enable extended flow attribute";
           type empty;
         }
         leaf mpls-flow-table-size {
           description "MPLS flow table size in units of 256k";
           type union {
             type string {
               pattern "<.*>|$.*";
             }
             type uint32 {
               range "1 .. 245";
             }
           }
         }
       }
     }
     container inline-video-monitoring {
       uses apply-advanced;
       leaf maximum-flows-count {
         description "Maximum number of inline video monitoring flows per PFE instance.";
         status deprecated;
         type union {
           type string {
             pattern "<.*>|$.*";
           }
           type uint32 {
             range "16 .. 8192";
           }
         }
       }
       leaf flow-table-size {
         description "Size of flow table size per PFE instance";
         type union {
           type string {
             pattern "<.*>|$.*";
           }
           type uint32 {
             range "16 .. 8192";
           }
         }
       }
     }
     container application-services {
       description "Application services configuration";
       uses apply-advanced;
       leaf package {
         description "Package selection";
         type string;
       }
     }
     container slamon-services {
       description "SLA monitoring services";
       uses apply-advanced;
       leaf rfc2544 {
         description "Enable sla monitoring services";
         type empty;
       }
     }
     leaf flexible-queuing-mode {
       description "Enable flexible queuing mode";
       type empty;
     }
     leaf loopback-device-count {
       description "Number of loopbacks";
       default "0";
       type union {
         type string {
           pattern "<.*>|$.*";
         }
         type uint32 {
           range "0 .. 4";
         }
       }
     }
     leaf interasic-linkerror-recovery-enable {
       description "Enable inter-asic link error recovery";
       type empty;
     }
     leaf number-of-ports {
       description "Number of physical ports to enable on FPC";
       type enumeration {
         enum "8" {
           description "Enable 8 ports";
         }
         enum "12" {
           description "Enable 12 ports";
         }
       }
     }
     list pfe-instance {
       key name;
       description "Packet forwarding engine parameters";
       uses chassis_pfe_type;
     }
     list pfe {
       key name;
       description "Packet forwarding engine parameters";
       uses chassis_pfe_type;
     }
     leaf service-package {
       description "Service package to be loaded on FPC";
       default "bundle-rfc2544";
       type enumeration {
         enum "bundle-rfc2544" {
           description "Service Package for RFC2544";
         }
         enum "bundle-nat-ipsec" {
           description "Service Package for NAT and IPSEC";
         }
         enum "bundle-ptp-enterprise-profile" {
           description "Service Package for PTP Enterprise Profile";
         }
       }
     }
     leaf max-queues {
       description "Maximum number of queues configurable on FPC";
       type enumeration {
         enum "8k" {
           description "8K maximum queues";
         }
         enum "16k" {
           description "16K maximum queues";
         }
         enum "32k" {
           description "32K maximum queues";
         }
         enum "48k" {
           description "48K maximum queues";
         }
         enum "64k" {
           description "64K maximum queues ";
         }
         enum "96k" {
           description "96K maximum queues ";
         }
         enum "128k" {
           description "128K maximum queues";
         }
         enum "192k" {
           description "192K maximum queues";
         }
         enum "256k" {
           description "256K maximum queues";
         }
         enum "384k" {
           description "256K maximum queues";
         }
         enum "512k" {
           description "512K maximum queues";
         }
         enum "768k" {
           description "768K maximum queues";
         }
         enum "1M" {
           description "1M maximum queues";
         }
         enum "1536k" {
           description "1536k maximum queues";
         }
         enum "2M" {
           description "2M maximum queues";
         }
       }
     }
     leaf bandwidth {
       description "Configure bandwidth of FPC";
       type enumeration {
         enum "1.6T" {
           description "Configure FPC bandwidth to 1.6T";
         }
       }
     }
     leaf pfe-bandwidth {
       description "Configure per PFE bandwidth";
       type enumeration {
         enum "240G" {
           description "Configure PFE bandwidth to 240G";
         }
         enum "300G" {
           description "Configure PFE bandwidth to 300G";
         }
         enum "400G" {
           description "Configure PFE bandwidth to 400G";
         }
       }
     }
     container error {
       description "Error level configuration for FPC";
       uses chassis_fpc_error_type;
     }
     list slc {
       key name;
       description "Sub-line card (SLC)";
       uses chassis_slc_type;
     }
     leaf low-power-mode {
       description "Configure FPC low power mode";
       type empty;
     }
     container openflow {
       description "Openflow configuration";
       uses apply-advanced;
       leaf access-list-partition {
         description "Space reserved for openflow access-list rules";
         units "percents";
         type union {
           type string {
             pattern "<.*>|$.*";
           }
           type uint32 {
             range "0 .. 100";
           }
         }
       }
     }
   }
   grouping chassis_fpc_type_slot {
     leaf name {
       description "FPC slot number";
       type string;
     }
     uses apply-advanced;
     list pem {
       key name;
       ordered-by user;
       description "Power Supply Module slot";
       uses chassis_pem_type_slot;
     }
   }
   grouping chassis_fru_cmerror_override_type {
     description "Chassis Fpc Error override";
     leaf name {
       description "Error identifier";
       type string {
         length "1 .. 255";
       }
     }
     uses apply-advanced;
     leaf state {
       description "State";
       type enumeration {
         enum "disable" {
           description "Disable error";
         }
       }
     }
     leaf severity {
       description "Severity";
       type enumeration {
         enum "minor" {
           description "Minor Severity";
         }
         enum "major" {
           description "Major Severity";
         }
         enum "fatal" {
           description "Fatal Severity";
         }
       }
     }
     container pfe {
       presence "enable pfe";
       description "Apply to these pfe";
       uses apply-advanced;
       leaf all {
         description "Apply to all pfe";
         type empty;
       }
     }
   }
   grouping chassis_pem_type {
     uses apply-advanced;
     leaf minimum {
       description "Minimum number of power supplies required for normal operation";
       type union {
         type string {
           pattern "<.*>|$.*";
         }
         type uint32;
       }
     }
     leaf feeds {
       description "Number of input feeds required";
       type union {
         type string {
           pattern "<.*>|$.*";
         }
         type uint32 {
           range "4 .. 6";
         }
       }
     }
     leaf input-current {
       description "Input current (Amps) in each feed ";
       default "60";
       type enumeration {
         enum "40" {
           description "40 Amps in each Feed";
         }
         enum "60" {
           description "60 Amps in each Feed";
         }
       }
     }
     container redundancy {
       description "PEM Source/Feed Redundancy configuration";
       uses apply-advanced;
       leaf source-redundancy {
         description "Toggle Source Redundancy for PEM";
         type empty;
       }
       container feed-redundancy {
         description "Toggle Feed Redundancy for a PEM slot";
         uses apply-advanced;
         list slot {
           key name;
           description "PEM Slot Number";
           leaf name {
             description "Select PEM slot";
             type union {
               type string {
                 pattern "<.*>|$.*";
               }
               type uint32;
             }
           }
           uses apply-advanced;
         }
       }
     }
   }
   grouping chassis_pem_type_slot {
     leaf name {
       description "PEM slot number";
       type string;
     }
     uses apply-advanced;
   }
   grouping chassis_pfe_type {
     description "PFE(Packet forwarding engine)";
     leaf name {
       description "PFE(Packet forwarding engine) identifier";
       type union {
         type string {
           pattern "<.*>|$.*";
         }
         type uint32;
       }
     }
     uses apply-advanced;
     container forwarding-packages {
       description "Associated forwarding package configuration";
       uses apply-advanced;
       container mobility {
         description "Mobility related PFE configuration";
         uses apply-advanced;
         choice package-type {
           case case_1 {
             leaf user-plane {
               description "User plane function";
               type empty;
             }
           }
         }
       }
     }
     container exception-reporting {
       description "Enable reporting of exceptions in the forwarding path";
       uses apply-advanced;
       list category {
         key name;
         ordered-by user;
         description "Exception category type";
         leaf name {
           type enumeration {
             enum "layer3" {
               description "Layer 3 exceptions";
             }
             enum "layer2" {
               description "Layer 2 exceptions";
             }
             enum "firewall" {
               description "Firewall exceptions";
             }
             enum "forwarding-state" {
               description "Forwarding state related exceptions";
             }
             enum "packet-errors" {
               description "Packet format error related exceptions";
             }
           }
         }
         uses apply-advanced;
         leaf inline-monitoring-instance {
           description "Inline monitoring to specified instance";
           type string {
             length "1 .. 64";
           }
         }
       }
     }
     leaf power {
       description "Power PFEs on or off";
       type enumeration {
         enum "off" {
           description "Power off PFE";
         }
         enum "on" {
           description "Power on PFE";
         }
       }
     }
     leaf temp-perf-throttle-disable {
       description "Disable temperature based PFE performance throttling";
       type empty;
     }
     leaf node {
       description "PFE(Packet forwarding engine) global identifier";
       type union {
         type string {
           pattern "<.*>|$.*";
         }
         type uint64 {
           range "1 .. 18446744073709551615";
         }
       }
     }
     leaf tunnel-services {
       description "Tunnel services configuration";
       type empty;
     }
     leaf temp-volt-reduction-disable {
       description "Disable temperature based PFE voltage reduction";
       type empty;
     }
     list core {
       key name;
       description "Core number";
       uses chassis_core_type;
     }
   }
   grouping chassis_core_type {
     leaf name {
       description "Core slot number";
       type union {
         type string {
           pattern "<.*>|$.*";
         }
         type uint32;
       }
     }
     uses apply-advanced;
     list channel {
       key name;
       description "Channel number";
       uses chassis_core_channel_type;
     }
   }
   grouping chassis_core_channel_type {
     leaf name {
       description "Channel number";
       type union {
         type string {
           pattern "<.*>|$.*";
         }
         type uint32;
       }
     }
     uses apply-advanced;
     container tunnel-services {
       description "Tunnel services";
       uses chassis_tunnel_services_type;
     }
   }
   grouping chassis_pic_type {
     leaf name {
       description "PIC slot number";
       type union {
         type string {
           pattern "<.*>|$.*";
         }
         type uint32;
       }
     }
     uses apply-advanced;
     leaf alternate-speed-set {
       description "PIC run time mode configuration";
       type enumeration {
         enum "6x100g-1x400g" {
           description "6x100G + 400G mode";
         }
       }
     }
     leaf pic-mode {
       description "PIC mode configuration";
       type enumeration {
         enum "1G" {
           description "1GE mode";
         }
         enum "10G" {
           description "10GE mode";
         }
         enum "25G" {
           description "25GE mode";
         }
         enum "40G" {
           description "40GE mode";
         }
         enum "50G" {
           description "50GE mode";
         }
         enum "100G" {
           description "100GE mode";
         }
         enum "400G" {
           description "400GE mode";
         }
         enum "1G10G" {
           description "1/10GE mode";
         }
       }
     }
     container tunnel-services {
       presence "enable tunnel-services";
       description "Tunnel services configuration";
       uses apply-advanced;
       leaf bandwidth {
         description "Amount of bandwidth reserved for tunnel service";
         type string;
       }
       leaf interface-type {
         description "Create specific tunnel interface";
         type enumeration {
           enum "gr" {
             description "Create gr tunnel interface";
           }
         }
       }
       leaf tunnel-only {
         description "Support only tunnel traffic";
         type empty;
       }
       leaf port {
         description "Front panel port number - ACX5048: [16-53], ACX5096: [64-95, 100-103]";
         type union {
           type uint32;
           type string {
             pattern "<.*>|$.*";
           }
         }
       }
       list tunnel-port {
         key name;
         ordered-by user;
         description "Tunnel port number";
         leaf name {
           description "Port number";
           type union {
             type string {
               pattern "<.*>|$.*";
             }
             type uint32;
           }
         }
         uses apply-advanced;
         leaf bandwidth {
           description "Amount of bandwidth reserved for tunnel service";
           type string;
         }
       }
     }
     leaf interface-type {
       description "Interface prefix";
       type enumeration {
         enum "ge" {
           description "Prefix interfaces as ge";
         }
         enum "xe" {
           description "Prefix interfaces as xe";
         }
         enum "et" {
           description "Prefix interfaces as et";
         }
       }
     }
     container inline-services {
       presence "enable inline-services";
       description "Inline services configuration";
       uses apply-advanced;
       list service-port {
         key name;
         ordered-by user;
         description "Service port number";
         leaf name {
           description "Port number";
           type union {
             type string {
               pattern "<.*>|$.*";
             }
             type uint32;
           }
         }
         uses apply-advanced;
         leaf bandwidth {
           description "Amount of bandwidth reserved for inline service";
           type string;
         }
       }
       leaf bandwidth {
         description "Amount of bandwidth reserved for inline service";
         type string;
       }
       leaf fragmentation-mtu {
         description "Set the fragmentation MTU size";
         default "1500";
         type union {
           type string {
             pattern "<.*>|$.*";
           }
           type uint32 {
             range "250 .. 9000";
           }
         }
       }
       leaf reassembly-context-age {
         description "Set the re-assembly context age millisecond timeout";
         default "25";
         type union {
           type string {
             pattern "<.*>|$.*";
           }
           type uint32 {
             range "5 .. 80";
           }
         }
       }
       container service-plane-recovery {
         description "Service plane recovery configuration";
         uses apply-advanced;
         leaf disable {
           type empty;
         }
         leaf downtime-gap-seconds {
           description "Gap between successive downtime events for recovery";
           default "180";
           type union {
             type string {
               pattern "<.*>|$.*";
             }
             type uint32 {
               range "30 .. 86400";
             }
           }
         }
         leaf downtime-events {
           description "Number of downtime events after which recovery is disabled";
           default "3";
           type union {
             type string {
               pattern "<.*>|$.*";
             }
             type uint32 {
               range "1 .. 100";
             }
           }
         }
       }
     }
     choice adaptive-or-monitoring {
       case case_1 {
         container adaptive-services {
           description "Adaptive services configuration";
           uses apply-advanced;
           container service-package {
             description "AS PIC service package";
             uses apply-advanced;
             choice service-package-choice {
               case case_1 {
                 leaf layer-3 {
                   description "Layer 3 service package";
                   type empty;
                 }
               }
               case case_2 {
                 leaf layer-2 {
                   description "Layer 2 service package";
                   type empty;
                 }
               }
               case case_3 {
                 leaf layer-2-3 {
                   description "Combined Layer 2 and Layer 3 service package";
                   type empty;
                 }
               }
               case case_4 {
                 container extension-provider {
                   description "Extension provider package configuration";
                   uses apply-advanced;
                   leaf data-pollers {
                     description "Number of cpus dedicated to poll data packets";
                     default "0";
                     type union {
                       type string {
                         pattern "<.*>|$.*";
                       }
                       type uint32 {
                         range "0 .. 7";
                       }
                     }
                   }
                   container data-flow-affinity {
                     presence "enable data-flow-affinity";
                     description "Enable flow affinity on data cores";
                     uses apply-advanced;
                     leaf hash-key {
                       type enumeration {
                         enum "layer-3" {
                           description "Set layer-3 as hash key";
                         }
                         enum "layer-4" {
                           description "Set layer-4 as hash key (default)";
                         }
                       }
                     }
                   }
                   leaf session-offload {
                     description "Enable session offload";
                     type empty;
                   }
                   leaf no-default-packages {
                     description "Do not load default packages";
                     type empty;
                   }
                   list package {
                     key name;
                     ordered-by user;
                     description "Extension provider package to run on the PIC";
                     max-elements 42;
                     leaf name {
                       description "Name of package";
                       type string;
                     }
                     uses apply-advanced;
                   }
                   list syslog {
                     key name;
                     ordered-by user;
                     description "System logging facility";
                     leaf name {
                       description "Facility type";
                       type enumeration {
                         enum "external" {
                           description "Local external applications";
                         }
                         enum "pfe" {
                           description "Packet Forwarding Engine";
                         }
                         enum "daemon" {
                           description "Various system processes";
                         }
                         enum "kernel" {
                           description "Kernel";
                         }
                       }
                     }
                     uses apply-advanced;
                     choice level {
                       case case_1 {
                         leaf any {
                           description "All levels";
                           type empty;
                         }
                       }
                       case case_2 {
                         leaf emergency {
                           description "Panic conditions";
                           type empty;
                         }
                       }
                       case case_3 {
                         leaf alert {
                           description "Conditions that should be corrected immediately";
                           type empty;
                         }
                       }
                       case case_4 {
                         leaf critical {
                           description "Critical conditions";
                           type empty;
                         }
                       }
                       case case_5 {
                         leaf error {
                           description "Error conditions";
                           type empty;
                         }
                       }
                       case case_6 {
                         leaf warning {
                           description "Warning messages";
                           type empty;
                         }
                       }
                       case case_7 {
                         leaf notice {
                           description "Conditions that should be handled specially";
                           type empty;
                         }
                       }
                       case case_8 {
                         leaf info {
                           description "Informational messages";
                           type empty;
                         }
                       }
                       case case_9 {
                         leaf none {
                           description "No messages";
                           type empty;
                         }
                       }
                     }
                     leaf destination {
                       description "Sylog destination";
                       type enumeration {
                         enum "routing-engine" {
                           description "Forward log messages to RE";
                         }
                         enum "pic-console" {
                           description "Forward to PIC console";
                         }
                       }
                     }
                   }
                 }
               }
             }
           }
         }
       }
       case case_2 {
         container monitoring-services {
           description "Monitoring services configuration";
           uses apply-advanced;
           leaf application {
             description "Application mode";
             type enumeration {
               enum "dynamic-flow-capture" {
                 description "Dynamic flow capture mode";
               }
               enum "flow-collector" {
                 description "Flow collector mode";
               }
               enum "monitor" {
                 description "Monitor mode";
               }
             }
           }
         }
       }
     }
     leaf no-mcast-replication {
       description "No mcast replication";
       type empty;
     }
     container ggsn-services {
       description "GGSN services configuration";
       status deprecated;
       uses apply-advanced;
       leaf application {
         description "Application mode";
         type enumeration {
           enum "ggsn-data" {
             description "GGSN-U mode";
           }
           enum "ggsn-inspection" {
             description "GGSN-I mode";
           }
           enum "ggsn-tunnel" {
             description "GGSN-T mode";
           }
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
         enum "lan" {
           description "LAN mode";
         }
       }
     }
     container synchronization {
       description "PIC synchronization source";
       uses apply-advanced;
       choice source {
         case case_1 {
           leaf port {
             description "Port Number";
             type union {
               type string {
                 pattern "<.*>|$.*";
               }
               type uint32 {
                 range "0 .. 11";
               }
             }
           }
         }
       }
     }
     container recovered-clock {
       description "Select recovered clock for this port";
       uses apply-advanced;
       leaf port {
         description "Port Number";
         type union {
           type string {
             pattern "<.*>|$.*";
           }
           type uint32 {
             range "0 .. 47";
           }
         }
       }
       leaf channel {
         description "Channel Number";
         type union {
           type string {
             pattern "<.*>|$.*";
           }
           type uint32 {
             range "0 .. 3";
           }
         }
       }
     }
     leaf vtmapping {
       description "Virtual tunnel mapping mode";
       type enumeration {
         enum "klm" {
           description "KLM mode";
         }
         enum "itu-t" {
           description "ITU-T mode";
         }
       }
     }
     leaf no-concatenate {
       description "Do not concatenate channels";
       type empty;
     }
     leaf no-multi-rate {
       description "Disable multi-rate mode";
       type empty;
     }
     leaf channelization {
       description "Enable Channelization";
       type empty;
     }
     leaf linerate-mode {
       description "Disable oversubscription. PIC operates in line rate mode";
       type empty;
     }
     leaf speed {
       description "Port speed";
       type enumeration {
         enum "1G" {
           description "1GE-Gigabit Ethernet";
         }
       }
     }
     leaf mixed-rate-mode {
       description "PIC operates in mixed-rate-mode. Speed and AE configurable for PIC Ports";
       type empty;
     }
     leaf no-pre-classifier {
       description "No pre-classification of packets";
       type empty;
     }
     leaf aggregate-ports {
       description "Aggregate multiple ports on a PIC as a single port";
       type empty;
     }
     leaf number-of-ports {
       description "Number of physical ports to enable on PIC";
       type union {
         type string {
           pattern "<.*>|$.*";
         }
         type uint32;
       }
     }
     leaf power {
       description "Power off PIC";
       type enumeration {
         enum "off" {
           description "Do not provide power to PIC";
         }
       }
     }
     leaf pic-type {
       description "OID of PIC type to be configured";
       type string {
       }
     }
     container aggregated-devices {
       description "Aggregated devices configuration";
       uses apply-advanced;
       container ima {
         description "Aggregated device options for Inverse Multiplexing for ATM";
         uses apply-advanced;
         leaf device-count {
           description "Number of IMA groups";
           type union {
             type string {
               pattern "<.*>|$.*";
             }
             type uint32 {
               range "1 .. 42";
             }
           }
         }
       }
     }
     leaf sparse-dlcis {
       description "Run in sparse data-link connection identifier mode";
       type empty;
     }
     leaf multi-link-layer-2-inline {
       description "Enable inline layer-2 services";
       type empty;
     }
     container q-pic-large-buffer {
       presence "enable q-pic-large-buffer";
       description "Run in large delay buffer mode";
       uses apply-advanced;
       choice buffer-type {
         case case_1 {
           leaf small-scale {
             description "Supports less number of interfaces";
             type empty;
           }
         }
         case case_2 {
           leaf large-scale {
             description "Supports large number of interfaces";
             type empty;
           }
         }
       }
     }
     container red-buffer-occupancy {
       description "Computation type for RED buffer occupancy";
       uses apply-advanced;
       container weighted-averaged {
         presence "enable weighted-averaged";
         description "Weighted-average computation";
         uses apply-advanced;
         leaf instant-usage-weight-exponent {
           description "Weight for instant buffer usage (negative exponent of 2)";
           type union {
             type uint8;
             type string {
               pattern "<.*>|$.*";
             }
           }
         }
       }
     }
     container traffic-manager {
       description "Configure traffic manager attributes";
       uses apply-advanced;
       leaf ingress-shaping-overhead {
         description "Number of CoS shaping overhead bytes in ingress";
         units "bytes";
         type union {
           type string {
             pattern "<.*>|$.*";
           }
           type int32 {
             range "-62 .. 192";
           }
         }
       }
       leaf egress-shaping-overhead {
         description "Number of CoS shaping overhead bytes in egress";
         units "bytes";
         type union {
           type string {
             pattern "<.*>|$.*";
           }
           type int32 {
             range "-62 .. 192";
           }
         }
       }
       leaf mode {
         description "Configure traffic manager mode";
         type enumeration {
           enum "egress-only" {
             description "Egress traffic manager enabled, ingress traffic manager disabled";
           }
           enum "session-shaping" {
             description "Enable egress session shaping";
           }
           enum "ingress-and-egress" {
             description "Enable the ingress and egress traffic managers";
           }
         }
       }
     }
     container idle-cell-format {
       description "ATM idle cell configuration";
       uses apply-advanced;
       leaf itu-t {
         description "ITU-T idle cell header format";
         type empty;
       }
       leaf payload-pattern {
         description "Payload pattern byte (0x00-0xff)";
         type string;
       }
     }
     container atm-l2circuit-mode {
       description "Enable ATM Layer 2 circuit transport mode";
       uses apply-advanced;
       choice mode_choice {
         case case_1 {
           leaf aal5 {
             description "ATM Layer 2 circuit AAL5 mode";
             type empty;
           }
         }
         case case_2 {
           leaf cell {
             description "ATM Layer 2 circuit cell mode";
             type empty;
           }
         }
         case case_3 {
           container trunk {
             presence "enable trunk";
             description "Set ATM Layer 2 circuit trunk mode";
             uses apply-advanced;
             choice trunk-mode {
               case case_1 {
                 container uni {
                   presence "enable uni";
                   description "ATM Layer 2 circuit user-to-network interface trunk mode";
                   uses apply-advanced;
                 }
               }
               case case_2 {
                 container nni {
                   presence "enable nni";
                   description "ATM Layer 2 circuit network-to-network interface trunk mode";
                   uses apply-advanced;
                 }
               }
             }
           }
         }
       }
     }
     leaf atm-cell-relay-accumulation {
       description "Enable ATM cell-relay accumulation mode";
       type empty;
     }
     leaf mlfr-uni-nni-bundles {
       description "Number of multilink Frame Relay UNI NNI (FRF.16) bundles to allocate on PIC";
       type union {
         type string {
           pattern "<.*>|$.*";
         }
         type uint32 {
           range "1 .. 255";
         }
       }
     }
     leaf mlfr-uni-nni-bundles-inline {
       description "Number of inline multilink frame relay UNI NNI bundles";
       type union {
         type string {
           pattern "<.*>|$.*";
         }
         type uint32 {
           range "1 .. 255";
         }
       }
     }
     container ct3 {
       description "CT3 NxDS0 PIC configuration";
       uses apply-advanced;
       list port {
         key name;
         description "CT3 port";
         uses ct3_port_type;
       }
     }
     container ce1 {
       description "CE1 NxDS0 PIC configuration";
       uses apply-advanced;
       list e1 {
         key name;
         description "E1 link";
         uses ce1_channel_type;
       }
     }
     leaf max-queues-per-interface {
       description "Maximum number of queues per interface on QOS-capable PIC";
       type enumeration {
         enum "4" {
           description "Maximum 4 queues per interface";
         }
         enum "8" {
           description "Maximum 8 queues per interface";
         }
       }
     }
     container shdsl {
       description "SHDSL chassis configuration";
       uses apply-advanced;
       leaf pic-mode {
         description "PIC mode";
         default "2-port-atm";
         type enumeration {
           enum "1-port-atm" {
             description "Single port ATM, 8 wire mode";
           }
           enum "2-port-atm" {
             description "Two port ATM, 4 wire mode";
           }
           enum "4-port-atm" {
             description "Four port ATM, 2 wire mode";
           }
           enum "efm" {
             description "Single port EFM, 2 wire mode";
           }
         }
       }
     }
     container ethernet {
       description "J-series Ethernet PIM mode configuration";
       uses apply-advanced;
       leaf pic-mode {
         description "PIC mode";
         default "routing";
         type enumeration {
           enum "switching" {
             description "Switched mode of operation";
           }
           enum "routing" {
             description "Routing mode of operation";
           }
           enum "enhanced-switching" {
             description "Enhanced switching mode of operation";
           }
         }
       }
     }
     leaf tunnel-queuing {
       description "Enable queueing for GRE/IPIP tunnels";
       type empty;
     }
     list port-mirror-instance {
       key name;
       ordered-by user;
       max-elements 2;
       leaf name {
         description "Associate a port mirroring instance with the PIC";
         type string {
           length "1 .. 64";
         }
       }
       uses apply-advanced;
     }
     list port {
       key name;
       description "Port number";
       uses chassis_pic_port_framing;
     }
     list port-range {
       key "port-range-low port-range-high";
       ordered-by user;
       description "Physical ports to channelize";
       leaf port-range-low {
         description "Port range low number";
         type union {
           type string {
             pattern "<.*>|$.*";
           }
           type uint32;
         }
       }
       leaf port-range-high {
         description "Port range high number";
         type union {
           type string {
             pattern "<.*>|$.*";
           }
           type uint32;
         }
       }
       uses apply-advanced;
       leaf short-reach-mode {
         description "Short reach mode (For ports 0..47)";
         type enumeration {
           enum "disable" {
             description "Disable";
           }
           enum "enable" {
             description "Enable";
           }
         }
       }
       leaf channel-speed {
         description "Port channel speed";
         type enumeration {
           enum "10g" {
             description "Set the port speed to 10G. This will restart PFE";
           }
           enum "25g" {
             description "Set the port speed to 25G.";
           }
           enum "50g" {
             description "Set the port speed to 50G.";
           }
           enum "disable-auto-speed-detection" {
             description "Disables automatic speed detection";
           }
         }
       }
     }
     container fibre-channel {
       description "Fibre channel configuration option";
       uses chassis_fibre_channel_type;
     }
     container sfpplus {
       description "Sfpplus configuration option";
       uses apply-advanced;
       leaf pic-mode {
         description "PIC mode";
         type enumeration {
           enum "1g" {
             description "1G SFP mode";
           }
           enum "10g" {
             description "10G SFP+ mode";
           }
         }
       }
     }
     container hash-key {
       description "Select data used in the hash key";
       uses apply-advanced;
       container family {
         description "Protocol family";
         uses apply-advanced;
         container inet {
           description "IPv4 protocol family";
           uses apply-advanced;
           container layer-3 {
             presence "enable layer-3";
             description "Include Layer 3 (IP) data in the hash key";
             uses apply-advanced;
             leaf destination-address {
               description "Include IP destination address in the hash key";
               type empty;
             }
           }
           container layer-4 {
             presence "enable layer-4";
             description "Include Layer 4 (TCP or UDP) data in the hash key";
             uses apply-advanced;
           }
           container symmetric-hash {
             presence "enable symmetric-hash";
             description "Create symmetric hash-key with source & dest ports";
             uses apply-advanced;
             leaf complement {
               description "Create complement of symmetric hash-key";
               type empty;
             }
           }
         }
         container multiservice {
           description "Multiservice protocol family";
           uses apply-advanced;
           leaf source-mac {
             description "Include source MAC address in hash key";
             type empty;
           }
           leaf destination-mac {
             description "Include destination MAC address in hash key";
             type empty;
           }
           container payload {
             description "Include payload data in the hash key";
             uses apply-advanced;
             container ip {
               description "Include IPv4 payload data in the hash key";
               uses apply-advanced;
               container layer-3 {
                 presence "enable layer-3";
                 description "Include layer-3 ip info for VPLS/Bridge";
                 uses apply-advanced;
                 choice layer-3-options {
                   case case_1 {
                     leaf source-ip-only {
                       description "Include source IP only in hash-key";
                       type empty;
                     }
                   }
                   case case_2 {
                     leaf destination-ip-only {
                       description "Include desintation IP only in hash-key";
                       type empty;
                     }
                   }
                 }
               }
               leaf layer-4 {
                 description "Include layer-4 IP information for VPLS/Bridge";
                 type empty;
               }
             }
           }
           container symmetric-hash {
             presence "enable symmetric-hash";
             description "Create a/symmetric hash-key with any attributes";
             uses apply-advanced;
             leaf complement {
               description "Create complement of symmetric hash-key";
               type empty;
             }
           }
         }
       }
     }
     leaf ingress-policer-overhead {
       description "Number of policer overhead bytes in ingress";
       units "bytes";
       type union {
         type string {
           pattern "<.*>|$.*";
         }
         type uint32 {
           range "0 .. 255";
         }
       }
     }
     leaf egress-policer-overhead {
       description "Number of policer overhead bytes in egress";
       units "bytes";
       type union {
         type string {
           pattern "<.*>|$.*";
         }
         type uint32 {
           range "0 .. 255";
         }
       }
     }
     leaf account-layer2-overhead {
       description "Account Layer2 overhead in egress and ingress IFD/IFL stats";
       type empty;
     }
     container forwarding-mode {
       description "Set 100GE PIC packet distribution mode";
       uses apply-advanced;
       choice cap-fpga-packet-distribution-mode {
         case case_1 {
           leaf sa-multicast {
             description "Used for Juniper CGE to Juniper 100GE PIC back to back connection";
             type empty;
           }
         }
         case case_2 {
           container vlan-steering {
             presence "enable vlan-steering";
             description "Steer packet by VLAN id, interoperate with other vendors";
             uses apply-advanced;
             leaf vlan-rule {
               description "Set 100GE PIC forwarding VLAN rule";
               type enumeration {
                 enum "odd-even" {
                   description "Even number VLAN id processed by PFE0; odd number by PFE1";
                 }
                 enum "high-low" {
                   description "VLAN 1~2047 processed by PFE0; others by PFE1";
                 }
               }
             }
           }
         }
       }
     }
     leaf subscriber-aware-services {
       description "Enable subscriber aware services";
       type empty;
     }
     leaf ptp-mode {
       description "Set hardware to run PTP BC applications.";
       type empty;
     }
   }
   grouping ce1_channel_type {
     leaf name {
       description "E1 link number";
       type union {
         type string {
           pattern "<.*>|$.*";
         }
         type uint32 {
           range "0 .. 9";
         }
       }
     }
     uses apply-advanced;
     list channel-group {
       key name;
       description "Define channel group";
       leaf name {
         description "Channel group number";
         type union {
           type string {
             pattern "<.*>|$.*";
           }
           type uint32 {
             range "0 .. 23";
           }
         }
       }
       leaf timeslots {
         description "DS0 timeslots (1..31); for example, 1-3,4,9,22-24 (no spaces)";
         type string;
       }
     }
   }
   grouping chassis_fibre_channel_type {
     description "Fibre channel configuration option";
     uses apply-advanced;
     list port-range {
       key "port-range-low port-range-high";
       ordered-by user;
       description "Fibre channel port range";
       leaf port-range-low {
         description "Port range low number";
         type union {
           type string {
             pattern "<.*>|$.*";
           }
           type uint32 {
             range "0 .. 47";
           }
         }
       }
       leaf port-range-high {
         description "Port range high number";
         type union {
           type string {
             pattern "<.*>|$.*";
           }
           type uint32 {
             range "0 .. 47";
           }
         }
       }
       uses apply-advanced;
     }
   }
   grouping chassis_pic_port_framing {
     leaf name {
       description "Port number";
       type union {
         type string {
           pattern "<.*>|$.*";
         }
         type uint32;
       }
     }
     uses apply-advanced;
     leaf short-reach-mode {
       description "Short reach mode (For ports 0...47)";
       type enumeration {
         enum "disable" {
           description "Disable";
         }
         enum "enable" {
           description "Enable";
         }
       }
     }
     leaf framing {
       description "Framing mode";
       type enumeration {
         enum "sonet" {
           description "SONET mode";
         }
         enum "sdh" {
           description "SDH mode";
         }
         enum "t3" {
           description "T3 mode";
         }
         enum "e3" {
           description "E3 mode";
         }
         enum "t1" {
           description "T1 mode";
         }
         enum "e1" {
           description "E1 mode";
         }
       }
     }
     leaf number-of-sub-ports {
       description "Number of subports per physical port";
       type union {
         type string {
           pattern "<.*>|$.*";
         }
         type uint32;
       }
     }
     leaf unused {
       description "Keep the port unused.";
       type empty;
     }
     leaf speed {
       description "Port speed";
       type enumeration {
         enum "oc3-stm1" {
           description "OC3 or STM1";
         }
         enum "oc12-stm4" {
           description "OC12 or STM4";
         }
         enum "oc48-stm16" {
           description "OC48 or STM16";
         }
         enum "1G" {
           description "1GE-Gigabit Ethernet";
         }
         enum "10g" {
           description "Sets the interface mode to 10Gbps";
         }
         enum "25g" {
           description "Sets the interface mode to 25Gbps";
         }
         enum "40g" {
           description "Sets the interface mode to 40Gbps";
         }
         enum "100g" {
           description "Sets the interface mode to 100Gbps";
         }
         enum "50g" {
           description "Sets the interface mode to 50Gbps";
         }
         enum "200g" {
           description "Sets the interface mode to 200 Gbps";
         }
         enum "400g" {
           description "Sets the interface mode to 400Gbps";
         }
       }
     }
     leaf channel-speed {
       description "Port channel speed";
       type enumeration {
         enum "10g" {
           description "Set the port speed to 10G. This will restart PFE on some platforms.";
         }
         enum "25g" {
           description "Set the port speed to 25G.";
         }
         enum "50g" {
           description "Set the port speed to 50G.";
         }
         enum "disable-auto-speed-detection" {
           description "Disables automatic speed detection";
         }
       }
     }
     container forwarding-mode {
       description "PIC packet distribution mode - Brooklyn interop mode";
       uses apply-advanced;
       leaf sa-multicast {
         description "SA multicast mode - interop with 100G Brooklyn PIC";
         type empty;
       }
     }
     leaf no-mcast-replication {
       description "No multicast replication";
       type empty;
     }
     container traffic-manager {
       description "Configure per port traffic manager mode";
       uses apply-advanced;
       leaf mode {
         description "Configure port traffic manager mode as ingress-and-egress";
         type enumeration {
           enum "ingress-and-egress" {
             description "Enable the ingress and egress traffic managers";
           }
         }
       }
     }
     leaf no-temperature-monitoring {
       description "Disable empolicy";
       type empty;
     }
   }
   grouping chassis_power_off_ports_on_no_master_re_type {
     choice power-off-ports-on-no-master-re {
       case case_1 {
         leaf disable {
           description "Disable powering off ports if no master RE present";
           type empty;
         }
       }
       case case_2 {
         leaf enable {
           description "Enable Powering of ports if no master RE present";
           type empty;
         }
       }
     }
   }
   grouping chassis_redundancy_type {
     uses apply-advanced;
     list routing-engine {
       key name;
       description "Redundancy options for Routing Engines";
       uses chassis_rdd_re_type;
     }
     list ssb {
       key name;
       description "Redundancy options for System Switch Boards";
       uses chassis_rdd_id_type;
     }
     list cfeb {
       key name;
       description "Redundancy options for Compact Forwarding Engine Boards";
       uses chassis_rdd_cfeb_id_type;
     }
     list sfm {
       key name;
       description "Redundancy options for Switching and Forwarding Modules";
       uses chassis_rdd_sfm_id_type;
     }
     container failover {
       description "Failover to other Routing Engine";
       presence "enable failover";
       uses chassis_rdd_failover_type;
     }
     leaf keepalive-time {
       description "Time before Routing Engine failover";
       units "seconds";
       type union {
         type string {
           pattern "<.*>|$.*";
         }
         type uint32 {
           range "2 .. 10000";
         }
       }
     }
     leaf mastership-refresh-timeout {
       description "Mastership refresh timeout";
       units "seconds";
       type union {
         type string {
           pattern "<.*>|$.*";
         }
         type uint32 {
           range "9 .. 30";
         }
       }
     }
     container graceful-switchover {
       description "Enable graceful switchover on supported hardware";
       presence "enable graceful-switchover";
       uses chassis_non_stop_forwarding_type;
     }
     container feb {
       description "Forwarding Engine Board redundancy configuration";
       uses apply-advanced;
       list redundancy-group {
         key name;
         leaf name {
           description "Name of FEB redundancy group";
           type string;
         }
         uses apply-advanced;
         leaf description {
           description "Text description of FEB redundancy group";
           type string;
         }
         list feb {
           key name;
           description "Redundancy settings for a Forwarding Engine Board";
           leaf name {
             description "Slot number";
             type union {
               type string {
                 pattern "<.*>|$.*";
               }
               type uint32;
             }
           }
           uses apply-advanced;
           choice redundancy-option {
             case case_1 {
               leaf primary {
                 description "FEB is default master in the redundancy group";
                 type empty;
               }
             }
             case case_2 {
               leaf backup {
                 description "FEB is backup in the redundancy group";
                 type empty;
               }
             }
           }
         }
         leaf no-auto-failover {
           description "Disable automatic FEB failover";
           type empty;
         }
       }
     }
   }
   grouping chassis_non_stop_forwarding_type {
     uses apply-advanced;
     container traceoptions {
       description "Graceful switchover trace options";
       status deprecated;
       uses apply-advanced;
       list flag {
         key name;
         ordered-by user;
         description "Tracing parameters";
         leaf name {
           type enumeration {
             enum "update" {
               description "Trace state updates";
             }
             enum "all" {
               description "Trace everything";
             }
           }
         }
       }
     }
   }
   grouping chassis_rdd_cfeb_id_type {
     leaf name {
       description "CFEB slot number";
       type union {
         type string {
           pattern "<.*>|$.*";
         }
         type uint32 {
           range "0 .. 1";
         }
       }
     }
     choice priority {
       case case_1 {
         leaf always {
           description "Sole device";
           type empty;
         }
       }
       case case_2 {
         leaf preferred {
           description "Preferred device";
           type empty;
         }
       }
     }
   }
   grouping chassis_rdd_failover_type {
     uses apply-advanced;
     container category {
       description "Failover category";
       presence "enable category";
       uses chassis_rdd_fail_cat_type;
     }
     leaf on-loss-of-keepalives {
       description "Failover on loss of keepalives";
       type empty;
     }
     leaf on-re-to-fpc-stale {
       description "Failover on loss of communication between the re and fpc";
       type empty;
     }
     leaf on-disk-failure {
       description "Failover on disk failure";
       type empty;
     }
     leaf not-on-disk-underperform {
       description "Prevent gstatd from initiating failovers in response to slow disks";
       type empty;
     }
     leaf disk-read-threshold {
       description "Read threshold (ms) on disk underperform monitoring";
       type union {
         type string {
           pattern "<.*>|$.*";
         }
         type uint32 {
           range "1000 .. 10000";
         }
       }
     }
     leaf disk-write-threshold {
       description "Write threshold (ms) on disk underperform monitoring";
       type union {
         type string {
           pattern "<.*>|$.*";
         }
         type uint32 {
           range "1000 .. 10000";
         }
       }
     }
     leaf on-loss-of-vm-host-connection {
       description "Failover on loss of vm host connection";
       type empty;
     }
   }
   grouping chassis_rdd_fail_cat_type {
     uses apply-advanced;
     container component-failure {
       description "Failover due to component failure";
       presence "enable component-failure";
       uses chassis_rdd_fail_cat_sev_type;
     }
     container software-failure {
       description "Failover due to software failure";
       presence "enable software-failure";
       uses chassis_rdd_fail_cat_sev_type;
     }
     container power-failure {
       description "Failover due to power failure";
       presence "enable power-failure";
       uses chassis_rdd_fail_cat_sev_type;
     }
     container clock-failure {
       description "Failover due to clock failure";
       presence "enable clock-failure";
       uses chassis_rdd_fail_cat_sev_type;
     }
     container link-failure {
       description "Failover due to link failure";
       presence "enable link-failure";
       uses chassis_rdd_fail_cat_sev_type;
     }
     container degraded-health {
       description "Failover due to degraded health";
       presence "enable degraded-health";
       uses chassis_rdd_fail_cat_sev_type;
     }
   }
   grouping chassis_rdd_fail_cat_sev_type {
     uses apply-advanced;
     container critical {
       description "Critical severity";
       presence "enable critical";
       uses chassis_rdd_fail_cat_sev_act_type;
     }
     container important {
       description "Important severity";
       presence "enable important";
       uses chassis_rdd_fail_cat_sev_act_type;
     }
   }
   grouping chassis_rdd_fail_cat_sev_act_type {
     uses apply-advanced;
     leaf disable {
       description "Disable action";
       type empty;
     }
   }
   grouping chassis_rdd_id_type {
     leaf name {
       description "SSB slot number";
       type union {
         type string {
           pattern "<.*>|$.*";
         }
         type uint32 {
           range "0 .. 1";
         }
       }
     }
     choice priority {
       case case_1 {
         leaf always {
           description "Sole device";
           type empty;
         }
       }
       case case_2 {
         leaf preferred {
           description "Preferred device";
           type empty;
         }
       }
     }
   }
   grouping chassis_rdd_re_type {
     leaf name {
       description "Routing Engine slot number";
       type union {
         type string {
           pattern "<.*>|$.*";
         }
         type uint32 {
           range "0 .. 1";
         }
       }
     }
     choice priority {
       case case_1 {
         leaf master {
           description "Master Routing Engine";
           type empty;
         }
       }
       case case_2 {
         leaf backup {
           description "Backup Routing Engine";
           type empty;
         }
       }
       case case_3 {
         leaf disabled {
           description "Routing Engine disabled";
           type empty;
         }
       }
     }
   }
   grouping chassis_rdd_sfm_id_type {
     leaf name {
       description "SFM slot number";
       type union {
         type string {
           pattern "<.*>|$.*";
         }
         type uint32;
       }
     }
     choice priority {
       case case_1 {
         leaf always {
           description "Sole device";
           type empty;
         }
       }
       case case_2 {
         leaf preferred {
           description "Preferred device";
           type empty;
         }
       }
     }
   }
   grouping chassis_routing_engine_type {
     uses apply-advanced;
     container on-disk-failure {
       description "Action to take when Routing Engine disk fails";
       uses chassis_re_on_disk_failure;
     }
     container disk {
       description "Action to take for Routing Engine disk";
       uses apply-advanced;
       leaf write-threshold-rate {
         description "Write threshold rate";
         default "4";
         units "MBPS";
         type union {
           type string {
             pattern "<.*>|$.*";
           }
           type uint32 {
             range "1 .. 20";
           }
         }
       }
       leaf write-threshold-duration {
         description "Write threshold duration";
         default "1000";
         units "seconds";
         type union {
           type string {
             pattern "<.*>|$.*";
           }
           type uint32 {
             range "300 .. 2592000";
           }
         }
       }
       leaf smart-check {
         description "Enable smart check command to disk";
         type empty;
       }
       list ssd-series {
         key name;
         ordered-by user;
         description "Specify the ssd vendor series";
         leaf name {
           description "SSD series name";
           type string {
             length "1 .. 40";
           }
         }
         uses apply-advanced;
         list id {
           key name;
           ordered-by user;
           description "Attribute ids to monitor of this series type";
           max-elements 30;
           leaf name {
             description "SSD smart attribute id";
             type union {
               type string {
                 pattern "<.*>|$.*";
               }
               type uint32 {
                 range "1 .. 255";
               }
             }
           }
           uses apply-advanced;
           leaf id-threshold {
             description "SSD smart attribute threshold";
             type union {
               type string {
                 pattern "<.*>|$.*";
               }
               type uint32 {
                 range "1 .. 4294967295";
               }
             }
           }
           leaf id-value {
             description "SSD attribute value";
             type enumeration {
               enum "raw" {
                 description "Raw value to be used for this smart id";
               }
               enum "norm" {
                 description "Normalised value to be used for this smart id";
               }
             }
           }
           leaf id-flag {
             description "SSD attribute flag";
             type enumeration {
               enum "low" {
                 description "Check if value is less than smart threshold";
               }
               enum "high" {
                 description "Check if value is greater than smart threshold";
               }
             }
           }
         }
       }
     }
   }
   grouping chassis_re_on_disk_failure {
     choice reboot_or_halt {
       case case_1 {
         leaf reboot {
           description "Reboot on disk failure";
           status deprecated;
           type empty;
         }
       }
       case case_2 {
         leaf disk-failure-action {
           type enumeration {
             enum "reboot" {
               description "Reboot on disk failure";
             }
             enum "halt" {
               description "Halt on disk failure";
             }
           }
         }
       }
     }
   }
   grouping chassis_sfm_type {
     leaf name {
       description "SFM slot number";
       type union {
         type string {
           pattern "<.*>|$.*";
         }
         type uint32;
       }
     }
     uses apply-advanced;
     choice cache {
     }
     leaf power {
       description "Power SFMs on or off";
       type enumeration {
         enum "off" {
           description "Do not provide power to SFMs";
         }
         enum "on" {
           description "Provide power to SFMs";
         }
       }
     }
     choice mode {
       case case_1 {
         leaf disable-power {
           description "Do not enable power to the card";
           status deprecated;
           type empty;
         }
       }
     }
   }
   grouping chassis_sib_type {
     uses apply-advanced;
     list slot {
       key name;
       description "SIB slot number";
       leaf name {
         description "SIB slot number";
         type union {
           type string {
             pattern "<.*>|$.*";
           }
           type uint32;
         }
       }
       uses apply-advanced;
       container error {
         description "Error level configuration for SIB";
         uses chassis_sib_error_type;
       }
       leaf power {
         description "Power SIBs on or off";
         type enumeration {
           enum "off" {
             description "Do not provide power to SIBs";
           }
           enum "on" {
             description "Provide power to SIBs";
           }
         }
       }
     }
     leaf minimum {
       description "Minimum number of Switch Interface Boards required for normal operation";
       type union {
         type string {
           pattern "<.*>|$.*";
         }
         type uint32 {
           range "2 .. 4";
         }
       }
     }
     container power-off {
       description "Power off the SIB slot";
       uses apply-advanced;
       list slot {
         key name;
         ordered-by user;
         description "SIB slot number to be powered off";
         leaf name {
           description "SIB slot number to be offlined";
           type union {
             type string {
               pattern "<.*>|$.*";
             }
             type uint32;
           }
         }
         uses apply-advanced;
       }
     }
   }
   grouping chassis_sib_error_type {
     description "Chassis SIB Error level";
     uses apply-advanced;
     container fatal {
       description "SIB Fatal errors (default threshold = 1)";
       uses chassis_sib_error_level_major_fatal;
     }
     container major {
       description "SIB Major Level errors (default threshold = 1)";
       uses chassis_sib_error_level_major_fatal;
     }
     container minor {
       description "SIB Minor Level errors (default threshold = 10)";
       uses chassis_sib_error_level_minor;
     }
     container scope {
       description "Error scope";
       uses chassis_sib_scope_type;
     }
   }
   grouping chassis_sib_error_level_major_fatal {
     uses apply-advanced;
     leaf threshold {
       description "Error count at which to take the action";
       type union {
         type string {
           pattern "<.*>|$.*";
         }
         type uint32 {
           range "1 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_error_level_minor {
     uses apply-advanced;
     leaf threshold {
       description "Error count at which to take the action";
       type union {
         type string {
           pattern "<.*>|$.*";
         }
         type uint32 {
           range "0 .. 1024";
         }
       }
     }
     list action {
       key name;
       ordered-by user;
       description "Configure the action for this level";
       leaf name {
         type enumeration {
           enum "reset" {
             description "Reset SIB";
           }
           enum "offline" {
             description "Offline SIB";
           }
           enum "alarm" {
             description "Raise SIB alarm";
           }
           enum "get-state" {
             description "Retreive SIB state for debugging";
           }
           enum "log" {
             description "Log occurence to system log file";
           }
           enum "trap" {
             description "Raise SIB trap";
           }
         }
       }
       uses apply-advanced;
     }
   }
   grouping chassis_sib_scope_type {
     description "Chassis SIB Error Scope";
     uses apply-advanced;
     container board {
       description "Board level scope";
       uses chassis_sib_scope_category;
     }
     container switch {
       description "SIB scope ";
       uses chassis_sib_scope_category;
     }
   }
   grouping chassis_sib_scope_category {
     description "Chassis SIB Error Category";
     uses apply-advanced;
     container category {
       description "SIB error category";
       uses chassis_sib_scope_category_type;
     }
   }
   grouping chassis_sib_scope_category_type {
     description "Chassis SIB Category level";
     uses apply-advanced;
     container functional {
       description "SIB functional category";
       uses chassis_sib_scope_category_error_type;
     }
     container memory {
       description "SIB memory category";
       uses chassis_sib_scope_category_error_type;
     }
     container io {
       description "SIB input-output category";
       uses chassis_sib_scope_category_error_type;
     }
     container storage {
       description "SIB storage category";
       uses chassis_sib_scope_category_error_type;
     }
     container switch {
       description "SIB switch category";
       uses chassis_sib_scope_category_error_type;
     }
     container processing {
       description "SIB processing category";
       uses chassis_sib_scope_category_error_type;
     }
   }
   grouping chassis_sib_scope_category_error_type {
     description "Chassis SIB Error level";
     uses apply-advanced;
     container fatal {
       description "SIB Fatal errors (default threshold = 1)";
       uses chassis_sib_error_level_type;
     }
     container major {
       description "SIB Major Level errors (default threshold = 1)";
       uses chassis_sib_error_level_type;
     }
     container minor {
       description "SIB Minor Level errors (default threshold = 10)";
       uses chassis_sib_error_level_type;
     }
   }
   grouping chassis_sib_error_level_type {
     uses apply-advanced;
     leaf threshold {
       description "Error count at which to take the action (0 - valid for minor only)";
       type union {
         type string {
           pattern "<.*>|$.*";
         }
         type uint32 {
           range "0 .. 1024";
         }
       }
     }
     list action {
       key name;
       ordered-by user;
       description "Configure the action for this level";
       leaf name {
         type enumeration {
           enum "reset" {
             description "Reset device";
           }
           enum "offline" {
             description "Offline device";
           }
           enum "alarm" {
             description "Raise chassis alarm";
           }
           enum "get-state" {
             description "Retreive device state for debugging";
           }
           enum "log" {
             description "Log occurence to system log file";
           }
           enum "trap" {
             description "Raise trap";
           }
         }
       }
       uses apply-advanced;
     }
   }
   grouping chassis_slc_type {
     leaf name {
       description "SLC id";
       type union {
         type string {
           pattern "<.*>|$.*";
         }
         type uint32 {
           range "1 .. 2";
         }
       }
     }
     uses apply-advanced;
     leaf power {
       description "Power SLCs on or off";
       type enumeration {
         enum "off" {
           description "Do not provide power to SLC";
         }
         enum "on" {
           description "Provide power to SLC";
         }
       }
     }
   }
   grouping chassis_tunnel_services_type {
     uses apply-advanced;
     leaf bandwidth {
       description "Bandwidth reserved for tunnel service";
       type string;
     }
   }
   grouping chassisd-redundancy-group-type {
     uses apply-advanced;
     container interface-type {
       uses apply-advanced;
       container redundant-logical-tunnel {
         description "Redundant logical tunnel interface group";
         uses apply-advanced;
         leaf device-count {
           description "Number of devices";
           type union {
             type string {
               pattern "<.*>|$.*";
             }
             type uint32 {
               range "1 .. 255";
             }
           }
         }
       }
       container redundant-virtual-tunnel {
         description "Redundant virtual tunnel interface group";
         uses apply-advanced;
         leaf device-count {
           description "Number of devices";
           type union {
             type string {
               pattern "<.*>|$.*";
             }
             type uint32 {
               range "1 .. 16";
             }
           }
         }
       }
     }
   }
   grouping chassisd_agg_container_type {
     uses apply-advanced;
     leaf device-count {
       description "Number of container devices";
       type union {
         type string {
           pattern "<.*>|$.*";
         }
         type uint32 {
           range "1 .. 128";
         }
       }
     }
   }
   grouping chassisd_agg_enet_type {
     uses apply-advanced;
     leaf device-count {
       description "Number of aggregated Ethernet devices";
       type union {
         type string {
           pattern "<.*>|$.*";
         }
         type uint32;
       }
     }
     container lacp {
       description "Global Link Aggregation Control Protocol configuration";
       uses apply-advanced;
       leaf system-priority {
         description "Priority of the system (0 ... 65535)";
         type string;
       }
       container link-protection {
         presence "enable link-protection";
         uses apply-advanced;
         leaf non-revertive {
           description "Don't revert links when better priority link comes up";
           type empty;
         }
       }
     }
   }
   grouping chassisd_agg_pos_type {
     uses apply-advanced;
     leaf device-count {
       description "Number of aggregated SONET devices";
       type union {
         type string {
           pattern "<.*>|$.*";
         }
         type uint32 {
           range "1 .. 64";
         }
       }
     }
   }
   grouping chassisd_provider_instance_type {
     uses apply-advanced;
     leaf device-count {
       description "Number of provider instance port devices";
       type union {
         type string {
           pattern "<.*>|$.*";
         }
         type uint32 {
           range "1 .. 16";
         }
       }
     }
   }
   grouping ct3_port_type {
     leaf name {
       description "CT3  L2NG_PRODUCTSport number";
       type union {
         type string {
           pattern "<.*>|$.*";
         }
         type int32 {
           range "0 .. 1";
         }
       }
     }
     uses apply-advanced;
     list t1 {
       key name;
       description "T1 link";
       uses ct3_channel_type;
     }
   }
   grouping ct3_channel_type {
     leaf name {
       description "T1 link number";
       type union {
         type string {
           pattern "<.*>|$.*";
         }
         type int32 {
           range "0 .. 27";
         }
       }
     }
     uses apply-advanced;
     list channel-group {
       key name;
       description "Define channel group";
       leaf name {
         description "Channel group number";
         type union {
           type string {
             pattern "<.*>|$.*";
           }
           type uint32 {
             range "0 .. 7";
           }
         }
       }
       leaf timeslots {
         description "DS0 timeslots (1..24); for example, 1-3,4,9,22-24 (no spaces)";
         type string;
       }
     }
   }
   grouping juniper-gnf {
     leaf name {
       description "GNF slot number";
       type union {
         type string {
           pattern "<.*>|$.*";
         }
         type uint32 {
           range "1 .. 10";
         }
       }
     }
     uses apply-advanced;
     leaf description {
       description "Description of guest network function";
       type string {
         length "1 .. 256";
       }
     }
     leaf control-plane-bandwidth-percent {
       description "Percentage of control plane bandwidth";
       units "percent";
       type union {
         type string {
           pattern "<.*>|$.*";
         }
         type uint32 {
           range "0 .. 100";
         }
       }
     }
     leaf-list fpcs {
       description "FPC associated with guest network function";
       type union {
         type string {
           pattern "<.*>|$.*";
         }
         type uint32;
       }
     }
     container fpc-slice {
       description "FPC sub-line cards (SLCs) associated with guest network function";
       uses apply-advanced;
       list fpc {
         key name;
         description "FPC resource parameters for SLC";
         leaf name {
           description "FPC slot";
           type union {
             type string {
               pattern "<.*>|$.*";
             }
             type uint32;
           }
         }
         uses apply-advanced;
         list slc {
           key name;
           description "Sub-line card configuration";
           leaf name {
             description "SLC id";
             type union {
               type string {
                 pattern "<.*>|$.*";
               }
               type uint32 {
                 range "1 .. 2";
               }
             }
           }
           uses apply-advanced;
           leaf-list pfe-id-list {
             description "List of pfe of FPC to be assigned to SLC";
             type string;
           }
           leaf cores {
             description "Number of cpu cores of FPC to be assigned to SLC (2, 4, 6, 8)";
             type union {
               type uint32;
               type string {
                 pattern "<.*>|$.*";
               }
             }
           }
           leaf dram {
             description "Amount of DRAM (in GB) of FPC to be assigned to SLC";
             type union {
               type string {
                 pattern "<.*>|$.*";
               }
               type uint32 {
                 range "5 .. 26";
               }
             }
           }
         }
       }
     }
     list abstract-interface {
       key name;
       uses abstract_interface_type;
     }
   }
   grouping abstract_interface_type {
     description "Abstract-interface";
     leaf name {
       description "Interface name of af";
       type string {
         length "1 .. 3";
       }
     }
     uses apply-advanced;
     leaf description {
       description "Description of AF interface";
       type string {
         length "1 .. 516";
       }
     }
     container peer-gnf {
       presence "enable peer-gnf";
       description "Peer gnf";
       leaf id {
         description "Peer-gnf id";
         type union {
           type string {
             pattern "<.*>|$.*";
           }
           type uint32 {
             range "1 .. 10";
           }
         }
       }
       leaf remote-af-name {
         description "Remote af interface name";
         type string {
           length "1 .. 3";
         }
       }
     }
     container collapsed-forward {
       presence "enable collapsed-forward";
       description "Enable/disable collapsed forwarding";
       choice cfwd_mode {
         case case_1 {
           leaf monitor {
             description "Monitor mode";
             type empty;
           }
         }
         case case_2 {
           leaf optimize {
             description "Optimize mode";
             type empty;
           }
         }
       }
     }
   }
   grouping juniper-protected-system-domain {
     description "Protected system domain configuration";
     leaf name {
       description "Name of protected system domain (psd[1-31], ex. psd2)";
       type string {
       }
     }
     uses apply-advanced;
     leaf description {
       description "Description of protected system domain";
       type string;
     }
     leaf-list fpcs {
       description "FPC associated with protected system domain";
       type union {
         type string {
           pattern "<.*>|$.*";
         }
         type uint32;
       }
     }
     list lcc {
       key name;
       leaf name {
         description "Specific LCC";
         type union {
           type string {
             pattern "<.*>|$.*";
           }
           type uint32;
         }
       }
       uses apply-advanced;
       leaf-list fpcs {
         description "FPC associated with protected system domain";
         type union {
           type string {
             pattern "<.*>|$.*";
           }
           type uint32;
         }
       }
     }
     leaf control-system-id {
       description "Control system identifier";
       type union {
         type string {
           pattern "<.*>|$.*";
         }
         type uint32 {
           range "1 .. 4";
         }
       }
     }
     leaf-list control-slot-numbers {
       ordered-by user;
       description "Slots associated with protected system domain";
       type union {
         type string {
           pattern "<.*>|$.*";
         }
         type uint32 {
           range "1 .. 12";
         }
       }
       max-elements 2;
     }
     leaf control-plane-bandwidth-percent {
       description "Percentage of control plane bandwidth";
       units "percent";
       type union {
         type string {
           pattern "<.*>|$.*";
         }
         type uint32 {
           range "0 .. 100";
         }
       }
     }
   }
   grouping juniper-protected-system-domain-traceoptions {
     description "Protected system domain traceoptions";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "rtsock" {
             description "Trace rtsock messages";
           }
           enum "ipc" {
             description "Trace IPC messages";
           }
           enum "init" {
             description "Trace intialization messages";
           }
           enum "psd" {
             description "Trace psd messages";
           }
           enum "all" {
             description "Trace everything";
           }
         }
       }
     }
   }
   grouping macro-data-type {
     leaf name {
       description "Keyword part of the keyword-value pair";
       type string;
     }
     leaf value {
       description "Value part of the keyword-value pair";
       type string;
     }
   }
   grouping redundancy-group-type {
     description "Redundancy-group provisioning";
     leaf name {
       description "Redundancy-group name";
       type string {
         length "2 .. 64";
       }
     }
     uses apply-advanced;
     leaf redundancy-group-id {
       description "Redundancy Group ID";
       type union {
         type string {
           pattern "<.*>|$.*";
         }
         type uint32 {
           range "1 .. 255";
         }
       }
     }
     container protocol {
       description "Redundancy-group Protocol";
       uses apply-advanced;
       container evpn {
         description "EVPN Redundancy Group";
         uses apply-advanced;
         leaf-list peer-ip {
           ordered-by user;
           description "Peer chassis IPs for EVPN Cluster";
           type jt:ipv4addr;
         }
         leaf local-ip {
           description "Local chassis IP for EVPN Cluster";
           type jt:ipv4addr;
         }
         leaf routing-instance {
           description "Name of routing instance for EVPN Cluster";
           type string;
         }
       }
     }
     list peer-chassis-id {
       key name;
       ordered-by user;
       description "Peer Chassis ID";
       leaf name {
         description "Peer chassis identifier";
         type union {
           type string {
             pattern "<.*>|$.*";
           }
           type uint32 {
             range "1 .. 4";
           }
         }
       }
       uses apply-advanced;
       leaf no-auto-vlan-provisioning {
         description "Disable auto VLAN provisioning on inter-chassis-link";
         type empty;
       }
       leaf inter-chassis-link {
         description "ICL interface name";
         type union {
           type jt:interface-device;
           type string {
             pattern "<.*>|$.*";
           }
         }
       }
       leaf no-auto-iccp-provisioning {
         description "Disable auto ICCP provisioning";
         type empty;
       }
       leaf session-establishment-hold-time {
         description "Time within which connection must succeed with this peer";
         units "seconds";
         type union {
           type string {
             pattern "<.*>|$.*";
           }
           type uint32 {
             range "45 .. 600";
           }
         }
       }
       container liveness-detection {
         presence "enable liveness-detection";
         description "Bidirectional Forwarding Detection options for the peer";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         leaf inline-disable {
           description "Disable inline mode for this BFD session";
           type empty;
         }
         leaf pdu-size {
           description "BFD transport protocol payload size";
           default "24";
           type union {
             type string {
               pattern "<.*>|$.*";
             }
             type uint32 {
               range "24 .. 16000";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
       }
       leaf authentication-key {
         description "MD5 authentication key";
         type string {
           length "1 .. 126";
         }
       }
       container traceoptions {
         description "Trace options for ICCP";
         uses apply-advanced;
         leaf no-remote-trace {
           description "Disable remote tracing";
           type empty;
         }
         container file {
           description "Trace file information";
           leaf filename {
             description "Name of file in which to write trace information";
             type string {
               length "1 .. 1024";
             }
           }
           leaf size {
             description "Maximum trace file size";
             type string;
           }
           leaf files {
             description "Maximum number of trace files";
             default "3";
             type union {
               type string {
                 pattern "<.*>|$.*";
               }
               type uint32 {
                 range "2 .. 1000";
               }
             }
           }
           choice world-readable-choice {
             leaf world-readable {
               description "Allow any user to read the log file";
               type empty;
             }
             leaf no-world-readable {
               description "Don't allow any user to read the log file";
               type empty;
             }
           }
           leaf match {
             description "Regular expression for lines to be logged";
             type jt:regular-expression;
           }
         }
         list flag {
           key name;
           ordered-by user;
           description "Trace flag information";
           leaf name {
             type enumeration {
               enum "error" {
                 description "Trace all errors";
               }
               enum "event" {
                 description "Trace all events";
               }
               enum "packet" {
                 description "Trace all packets";
               }
               enum "pipe" {
                 description "Trace pipe messages";
               }
               enum "pipe-detail" {
                 description "Trace pipe messages in detail";
               }
               enum "all" {
                 description "Trace everything";
               }
             }
           }
         }
       }
     }
     leaf-list satellite {
       ordered-by user;
       description "Satellite slot-id or range or all";
       type string {
         length "1 .. 100";
       }
     }
     leaf system-mac-address {
       description "System MAC address";
       type jt:mac-unicast;
     }
     list cluster {
       key name;
       description "Cluster member of redundancy-group";
       leaf name {
         description "Cluster name";
         type string;
       }
       uses apply-advanced;
     }
   }
   grouping satellite-bridge-filter {
     leaf name {
       description "Filter name";
       type string {
       }
     }
     uses apply-advanced;
     list term {
       key name;
       ordered-by user;
       description "Define a firewall term";
       leaf name {
         description "Term name";
         type string {
         }
       }
       uses apply-advanced;
       container from {
         description "Define match criteria";
         uses apply-advanced;
         list source-mac-address {
           key name;
           ordered-by user;
           description "Match MAC source address";
           uses firewall_mac_addr_object;
         }
         list destination-mac-address {
           key name;
           ordered-by user;
           description "Match MAC destination address";
           uses firewall_mac_addr_object;
         }
         list ip-source-address {
           key name;
           ordered-by user;
           description "Match IP source address";
           uses firewall_addr_object;
         }
         list ip-destination-address {
           key name;
           ordered-by user;
           description "Match IP destination address";
           uses firewall_addr_object;
         }
         choice ip-protocol_choice {
           case case_1 {
             leaf-list ip-protocol {
               ordered-by user;
               type string;
             }
           }
           case case_2 {
             leaf-list ip-protocol-except {
               ordered-by user;
               type string;
             }
           }
         }
         choice source-port_choice {
           case case_1 {
             leaf-list source-port {
               ordered-by user;
               type string;
             }
           }
           case case_2 {
             leaf-list source-port-except {
               ordered-by user;
               type string;
             }
           }
         }
         choice destination-port_choice {
           case case_1 {
             leaf-list destination-port {
               ordered-by user;
               type string;
             }
           }
           case case_2 {
             leaf-list destination-port-except {
               ordered-by user;
               type string;
             }
           }
         }
         choice user-vlan-id_choice {
           case case_1 {
             leaf-list user-vlan-id {
               ordered-by user;
               description "Range of values";
               type string;
             }
           }
           case case_2 {
             leaf-list user-vlan-id-except {
               ordered-by user;
               description "Range of values";
               type string;
             }
           }
         }
       }
       container then {
         description "Action to take if the 'from' condition is matched";
         uses apply-advanced;
         choice designation {
           case case_1 {
             leaf accept {
               description "Accept the packet";
               type empty;
             }
           }
           case case_2 {
             leaf discard {
               description "Discard the packets";
               type empty;
             }
           }
         }
         leaf next-hop-group {
           description "Use specified next-hop group";
           type string;
         }
       }
     }
   }
   grouping firewall_addr_object {
     leaf name {
       description "Prefix to match";
       type jt:ipv4prefix;
     }
     leaf except {
       description "Match address not in this prefix";
       type empty;
     }
   }
   grouping firewall_mac_addr_object {
     leaf name {
       description "MAC address to match";
       type jt:mac-addr-prefix;
     }
     leaf except {
       description "Match MAC address not in this range";
       type empty;
     }
   }
   grouping upgrade-group-type {
     description "Upgrade group";
     leaf name {
       description "Upgrade group name";
       type string {
         length "2 .. 64";
       }
     }
     uses apply-advanced;
     leaf-list satellite {
       ordered-by user;
       description "Satellite slot-id or range or all";
       type string {
         length "1 .. 100";
       }
     }
   }
 }
