/*
 * Copyright (c) 2024 Juniper Networks, Inc.
 * All rights reserved.
 */
 module junos-rpc-database-replication {
   namespace "http://yang.juniper.net/junos/rpc/database-replication";

   prefix database-replication;

   import junos-common-types {
     prefix jt;
     revision-date 2024-01-01;
   }

   organization "Juniper Networks, Inc.";

   contact "yang-support@juniper.net";

   description "Junos RPC YANG module for database-replication command(s)";

   revision 2024-01-01 {
     description "Junos: 24.2R1.17";
   }

   rpc get-database-replication-statistics-information {
     description "Show database replication statistics";
     output {
       container database-replication-statistics-information {
         uses database-replication-statistics-information-block;
       }
     }
   }
   rpc get-database-replication-summary-information {
     description "Show database replication summary";
     output {
       container database-replication-summary-information {
         uses database-replication-summary-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping database-replication-statistics-information-block {
     leaf dropped-connections-total {
       type uint32;
       description "Total number times connection was restarted";
     }
     leaf max-buffer-count {
       type uint32;
       description "Maximum number of outstanding buffers";
     }
     leaf msg-received-bytes {
       type uint32;
       description "Total number bytes received";
     }
     leaf msgs-received-total {
       type uint32;
       description "Total number messages received";
     }
     leaf msg-sent-bytes {
       type uint32;
       description "Total number bytes sent";
     }
     leaf msgs-sent-total {
       type uint32;
       description "Total number messages sent";
     }
     leaf queue-full-total {
       type uint32;
       description "Total number times queue was full";
     }
     leaf queue-max-size {
       type uint32;
       description "Maximum size queue reached";
     }
     leaf queue-current-size {
       type uint32;
       description "Current size of the queue";
     }
   }
   grouping database-replication-summary-information-block {
     leaf replication-graceful-restart-type {
       type string;
       description "Mode of the chassis graceful restart";
     }
     leaf replication-mastership-type {
       type string;
       description "Mode of the database replication";
     }
     leaf replication-connection-type {
       type string;
       description "Connection status of the database replication";
     }
     leaf replication-connection-disconnection-reason {
       type string;
       description "Connection status of the database replication";
     }
     leaf replication-database-type {
       type string;
       description "Synchronizing status of the database replication";
     }
     leaf replication-queue-type {
       type string;
       description "Queue status of the database replication";
     }
   }
 }
