/*
 * Copyright (c) 2024 Juniper Networks, Inc.
 * All rights reserved.
 */
 module junos-rpc-dhcp {
   namespace "http://yang.juniper.net/junos/rpc/dhcp";

   prefix dhcp;

   import junos-common-types {
     prefix jt;
     revision-date 2024-01-01;
   }

   organization "Juniper Networks, Inc.";

   contact "yang-support@juniper.net";

   description "Junos RPC YANG module for dhcp command(s)";

   revision 2024-01-01 {
     description "Junos: 24.2R1.17";
   }

   rpc get-dhcp-service-statistics-information {
     description "Show DHCP service statistics";
     input {
       leaf level {
         default "summary";
         type enumeration {
           enum "summary" {
             description "Display summary information";
           }
         }
       }
       leaf interface {
         description "Name of interface";
         type union {
           type jt:interface-name;
           type string {
             pattern "<.*>|$.*";
           }
         }
       }
     }
     output {
       container dhcp-service-statistics-information {
         uses dhcp-service-statistics-information-block;
       }
     }
   }
   rpc get-dhcp-active-leasequery-neighbors {
     description "Show dhcp active-leasequery neighbors";
     output {
       container dhcp-active-leasequery-neighbors {
         uses dhcp-active-leasequery-neighbors-block;
       }
     }
   }
   rpc get-dhcp-relay-binding-information {
     description "Show DHCP relay client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IP address/MAC address/Session Id of DHCP client binding";
             type string;
           }
         }
         case interfaces-wildcard {
           leaf interfaces-wildcard {
             description "Interfaces to show bindings on (can be '*' wildcard)";
             type string {
             }
           }
         }
         case interfaces-vlan {
           leaf interfaces-vlan {
             description "Interface VLAN-ID/SVLAN-ID on which to show bindings";
             type string {
             }
           }
         }
       }
       leaf routing-instance {
         description "Name of routing instance";
         type string;
       }
       leaf bridge-domain {
         description "Name of bridge domain";
         type string;
       }
       choice lsys-tenant {
       }
       choice daemon-select {
         case logical-system {
           leaf logical-system {
             description "Name of logical system";
             type string {
             }
           }
         }
       }
     }
     output {
       container dhcp-relay-binding-information {
         uses dhcp-relay-binding-information-block;
       }
     }
   }
   rpc get-dhcp-relay-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       choice daemon-select {
         case logical-system {
           leaf logical-system {
             description "Name of logical system";
             type string {
             }
           }
         }
       }
     }
     output {
       container dhcp-relay-binding-information {
         uses dhcp-relay-binding-information-block;
       }
     }
   }
   rpc get-dhcp-relay-interface-bindings {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcp-relay-binding-information {
         uses dhcp-relay-binding-information-block;
       }
     }
   }
   rpc get-dhcp-relay-interface-tag-bindings {
     description "Interface tag on which to show bindings";
     input {
       leaf interface-tag-name {
         description "Name of interface tag";
         type string {
           length "1 .. 64";
         }
         mandatory true;
       }
       leaf level {
         default "brief";
         type enumeration {
           enum "brief" {
             description "Display brief information";
           }
           enum "detail" {
             description "Display detailed information";
           }
           enum "summary" {
             description "Display summary information";
           }
         }
       }
     }
     output {
       container dhcp-relay-binding-information {
         uses dhcp-relay-binding-information-block;
       }
     }
   }
   rpc get-dhcp-relay-statistics-information {
     description "Show DHCP statistics";
     input {
       leaf level {
         default "summary";
         type enumeration {
           enum "summary" {
             description "Display summary information";
           }
         }
       }
       leaf routing-instance {
         description "Name of routing instance";
         type string;
       }
       leaf bridge-domain {
         description "Name of bridge domain";
         type string;
       }
       choice lsys-tenant {
       }
       choice daemon-select {
         case logical-system {
           leaf logical-system {
             description "Name of logical system";
             type string {
             }
           }
         }
       }
     }
     output {
       container dhcp-relay-statistics-information {
         uses dhcp-relay-statistics-information-block;
       }
     }
   }
   rpc get-dhcp-relay-leasequery-statistics {
     description "Show DHCP relay leasequery statistics";
     input {
       leaf level {
         default "summary";
         type enumeration {
           enum "summary" {
             description "Display summary information";
           }
         }
       }
       leaf routing-instance {
         description "Name of routing instance";
         type string;
       }
       choice daemon-select {
         case logical-system {
           leaf logical-system {
             description "Name of logical system";
             type string {
             }
           }
         }
       }
     }
     output {
       container dhcp-relay-leasequery-statistics {
         uses dhcp-relay-leasequery-statistics-block;
       }
     }
   }
   rpc get-dhcp-relay-bulk-leasequery-conn-statistics {
     description "Show DHCP relay bulk leasequery statistics";
     input {
       leaf level {
         default "summary";
         type enumeration {
           enum "summary" {
             description "Display summary information";
           }
         }
       }
       leaf routing-instance {
         description "Name of routing instance";
         type string;
       }
       choice daemon-select {
         case logical-system {
           leaf logical-system {
             description "Name of logical system";
             type string {
             }
           }
         }
       }
     }
     output {
       container dhcp-relay-bulk-leasequery-conn-statistics {
         uses dhcp-relay-bulk-leasequery-conn-statistics-block;
       }
     }
   }
   rpc get-dhcp-relay-lockout-entries-information {
     description "Show DHCP lockout entries";
     input {
       leaf level {
         default "all";
         type enumeration {
           enum "all" {
             description "Display all the lockout entries";
           }
         }
       }
       leaf index {
         description "Display lockout information per index";
         type union {
           type uint32;
           type string {
             pattern "<.*>|$.*";
           }
         }
       }
       leaf routing-instance {
         description "Name of routing instance";
         type string;
       }
       choice daemon-select {
         case logical-system {
           leaf logical-system {
             description "Name of logical system";
             type string {
             }
           }
         }
       }
     }
     output {
       container dhcp-relay-lockout-entries-information {
         uses dhcp-relay-lockout-entries-information-block;
       }
     }
   }
   rpc get-dhcp-active-leasequery-information {
     description "Show DHCP active-leasequery entries";
     input {
       leaf level {
         default "summary";
         type enumeration {
           enum "summary" {
             description "Display summary information";
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-alq-information-peer {
     description "Active-leasequery peer";
     input {
       leaf peer-address {
         description "Active-leasequery peer address";
         type string;
         mandatory true;
       }
       leaf details {
         description "Active-leasequery peer details";
         type empty;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-alq-information-statistics-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-alq-information-statistics-interface {
     description "Active-leasequery interface";
     input {
       leaf interface-name {
         description "Active-leasequery interface name";
         type string;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-server-binding-information {
     description "Show DHCP server client binding information";
     input {
       leaf level {
         default "brief";
         type enumeration {
           enum "brief" {
             description "Display brief information";
           }
           enum "detail" {
             description "Display detailed information";
           }
           enum "summary" {
             description "Display summary information";
           }
         }
       }
       choice show-choice {
         case address {
           leaf address {
             description "IP address/MAC address/Session Id of DHCP client binding";
             type string;
           }
         }
         case interfaces-wildcard {
           leaf interfaces-wildcard {
             description "Interfaces to show bindings on (can be '*' wildcard)";
             type string {
             }
           }
         }
         case interfaces-vlan {
           leaf interfaces-vlan {
             description "Interface VLAN-ID/SVLAN-ID on which to show bindings";
             type string {
             }
           }
         }
       }
       leaf routing-instance {
         description "Name of routing instance";
         type string;
       }
       choice lsys-tenant {
       }
       choice daemon-select {
         case logical-system {
           leaf logical-system {
             description "Name of logical system";
             type string {
             }
           }
         }
       }
     }
     output {
       container dhcp-server-binding-information {
         uses dhcp-server-binding-information-block;
       }
     }
   }
   rpc get-dhcp-server-binding-ltv-information {
     description "Display lease time violated client bindings";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       choice daemon-select {
         case logical-system {
           leaf logical-system {
             description "Name of logical system";
             type string {
             }
           }
         }
       }
     }
     output {
       container dhcp-server-binding-information {
         uses dhcp-server-binding-information-block;
       }
     }
   }
   rpc get-dhcp-relay-binding-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
           enum "summary" {
             description "Display summary information";
           }
         }
       }
     }
     output {
       container dhcp-relay-binding-information {
         uses dhcp-relay-binding-information-block;
       }
     }
   }
   rpc get-dhcp-server-binding-interface-tag {
     description "Interface tag on which to show bindings";
     input {
       leaf interface-tag-name {
         description "Name of interface tag";
         type string {
           length "1 .. 64";
         }
         mandatory true;
       }
       leaf level {
         default "brief";
         type enumeration {
           enum "brief" {
             description "Display brief information";
           }
           enum "detail" {
             description "Display detailed information";
           }
           enum "summary" {
             description "Display summary information";
           }
         }
       }
     }
     output {
       container dhcp-server-binding-information {
         uses dhcp-server-binding-information-block;
       }
     }
   }
   rpc get-dhcp-server-statistics-information {
     description "Show DHCP server statistics";
     input {
       leaf level {
         default "summary";
         type enumeration {
           enum "summary" {
             description "Display summary information";
           }
         }
       }
       leaf routing-instance {
         description "Name of routing instance";
         type string;
       }
       choice lsys-tenant {
       }
       choice daemon-select {
         case logical-system {
           leaf logical-system {
             description "Name of logical system";
             type string {
             }
           }
         }
       }
     }
     output {
       container dhcp-server-statistics-information {
         uses dhcp-server-statistics-information-block;
       }
     }
   }
   rpc get-dhcp-server-bulk-leasequery-conn-statistics {
     description "Show DHCP server bulk leasequeery conn statistics";
     input {
       leaf routing-instance {
         description "Name of routing instance";
         type string;
       }
       choice daemon-select {
         case logical-system {
           leaf logical-system {
             description "Name of logical system";
             type string {
             }
           }
         }
       }
     }
     output {
       container dhcp-server-bulk-leasequery-conn-statistics {
         uses dhcp-server-bulk-leasequery-conn-statistics-block;
       }
     }
   }
   rpc get-dhcp-server-active-leasequery-information {
     description "Show DHCP active-leasequery entries";
     input {
       leaf level {
         default "summary";
         type enumeration {
           enum "summary" {
             description "Display summary information";
           }
         }
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-server-alq-information-peer {
     description "Active-leasequery peer";
     input {
       leaf peer-address {
         description "Active-leasequery peer address";
         type string;
         mandatory true;
       }
       leaf details {
         description "Active-leasequery peer details";
         type empty;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-server-alq-information-statistics-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-server-alq-info-statistics-interface {
     description "Active-leasequery interface";
     input {
       leaf interface-name {
         description "Active-leasequery interface name";
         type string;
         mandatory true;
       }
       leaf routing-instance {
         description "Name of routing instance";
         type string;
       }
       choice daemon-select {
         case logical-system {
           leaf logical-system {
             description "Name of logical system";
             type string {
             }
           }
         }
       }
     }
     output {
       choice output_c {
         case output-tag {
           leaf output {
             type string;
           }
         }
         case multichassis-tag {
           anyxml multi-routing-engine-results;
         }
       }
     }
   }
   rpc get-dhcp-server-lockout-entries-information {
     description "Show DHCP lockout entries";
     input {
       leaf level {
         default "all";
         type enumeration {
           enum "all" {
             description "Display all the lockout entries";
           }
         }
       }
       leaf index {
         description "Display lockout information per index";
         type union {
           type uint32;
           type string {
             pattern "<.*>|$.*";
           }
         }
       }
       leaf routing-instance {
         description "Name of routing instance";
         type string;
       }
       choice daemon-select {
         case logical-system {
           leaf logical-system {
             description "Name of logical system";
             type string {
             }
           }
         }
       }
     }
     output {
       container dhcp-server-lockout-entries-information {
         uses dhcp-server-lockout-entries-information-block;
       }
     }
   }
   rpc get-dhcp-client-binding-information {
     description "Show DHCP client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       choice lsys-tenant {
       }
       choice daemon-select {
         case logical-system {
           leaf logical-system {
             description "Name of logical system";
             type string {
             }
           }
         }
       }
     }
     output {
       container dhcp-client-binding-information {
         uses dhcp-client-binding-information-block;
       }
     }
   }
   rpc get-dhcp-client-binding-information-by-interface {
     description "Name of interface on which to show bindings";
     input {
       leaf interface-name {
         description "Name of interface";
         type string;
         mandatory true;
       }
       leaf level {
         default "brief";
         type enumeration {
           enum "brief" {
             description "Display brief information";
           }
           enum "detail" {
             description "Display detailed information";
           }
         }
       }
     }
     output {
       container dhcp-client-binding-information {
         uses dhcp-client-binding-information-block;
       }
     }
   }
   rpc get-dhcp-client-statistics-information {
     description "Show DHCP client statistics";
     input {
       leaf routing-instance {
         description "Name of routing instance";
         type string;
       }
       choice lsys-tenant {
       }
       choice daemon-select {
         case logical-system {
           leaf logical-system {
             description "Name of logical system";
             type string {
             }
           }
         }
       }
     }
     output {
       container dhcp-client-statistics-information {
         uses dhcp-client-statistics-information-block;
       }
     }
   }
   rpc get-dhcp-proxy-client-binding-information {
     description "Show DHCP proxy-client binding information";
     input {
       leaf level {
         default "brief";
         type enumeration {
           enum "brief" {
             description "Display brief information";
           }
           enum "detail" {
             description "Display detailed information";
           }
           enum "summary" {
             description "Display summary information";
           }
         }
       }
       leaf routing-instance {
         description "Name of routing instance";
         type string;
       }
       choice daemon-select {
         case logical-system {
           leaf logical-system {
             description "Name of logical system";
             type string {
             }
           }
         }
       }
     }
     output {
       container dhcp-client-binding-information {
         uses dhcp-client-binding-information-block;
       }
     }
   }
   rpc get-proxy-dhcp-client-statistics-information {
     description "Show DHCP proxy-client statistics";
     input {
       leaf routing-instance {
         description "Name of routing instance";
         type string;
       }
       choice daemon-select {
         case logical-system {
           leaf logical-system {
             description "Name of logical system";
             type string {
             }
           }
         }
       }
     }
     output {
       container dhcp-proxy-client-statistics-information {
         uses dhcp-proxy-client-statistics-information-block;
       }
     }
   }
   rpc get-dhcp-proxy-client-profile-servers-info {
     description "Show DHCP-Proxy server list of profile";
     input {
       leaf logical-system {
         description "Name of logical system";
         type string;
         mandatory true;
       }
       leaf routing-instance {
         description "Name of routing instance";
         type string;
         mandatory true;
       }
       leaf profile-name {
         description "Name of profile name";
         type string;
         mandatory true;
       }
     }
     output {
       container dhcp-proxy-client-profile-servers-information {
         uses dhcp-proxy-client-profile-servers-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping dhcp-service-statistics-information-block {
     leaf dropped-packet-dhcp-service-total {
       type uint32;
       description "Total packets discard by DHCP service";
     }
     leaf dropped-packet-read-error {
       type uint32;
       description "Packets discarded due to read error";
     }
     leaf dropped-packet-bad-ip-header {
       type uint32;
       description "Packets discarded due to bad IP header";
     }
     leaf dropped-packet-short-packet {
       type uint32;
       description "Packets discarded due to runt packet";
     }
     leaf dropped-packet-no-interface {
       type uint32;
       description "Packets discarded due to no interface";
     }
     leaf dropped-packet-no-routing-instance {
       type uint32;
       description "Packets discarded due to no routing instance";
     }
     leaf dropped-packet-no-mem {
       type uint32;
       description "Packets discarded due to no memory";
     }
     leaf dropped-packet-recovery-in-progress {
       type uint32;
       description "Packets discarded due to switchover recovery in progress";
     }
     leaf clients-marked-for-deletion {
       type uint32;
       description "Number of clients marked for deletion";
     }
   }
   grouping dhcp-active-leasequery-neighbors-block {
     container dhcp-active-leasequery-neighbors-all {
       leaf interface-name {
         type string;
         description "Name of the interface via which the DHCP server transmitted the address assignment";
       }
       leaf neighbor-address {
         type jt:ipaddr;
         description "Active leasequery neighbor address";
       }
     }
   }
   grouping dhcp-relay-binding-information-block {
     container binding-summary {
       leaf binding-count {
         type int32;
         description "Number of bindings in this routing instance";
       }
       leaf init-count {
         type int32;
       }
       leaf bound-count {
         type int32;
       }
       leaf selecting-count {
         type int32;
       }
       leaf requesting-count {
         type int32;
       }
       leaf renewing-count {
         type int32;
       }
       leaf rebinding-count {
         type int32;
       }
       leaf releasing-count {
         type int32;
       }
       leaf restore-count {
         type int32;
         description "Number of clients waiting to be restored";
       }
     }
     container binding-internal-states {
       leaf init {
         type int32;
         description "Number of clients init state";
       }
       leaf selecting {
         type int32;
         description "Number of clients in selecting state";
       }
       leaf requesting {
         type int32;
         description "Number of clients in requesting state";
       }
       leaf bound {
         type int32;
         description "Number of clients in bound state";
       }
       leaf renewing {
         type int32;
         description "Number of clients in renewing state";
       }
       leaf rebinding {
         type int32;
         description "Number of clients in rebinding state";
       }
       leaf wait-cm-add {
         type int32;
         description "Number of clients in wait-cm-add state";
       }
       leaf wait-cm-add-delete {
         type int32;
         description "Number of clients in wait-cm-add-delete state";
       }
       leaf wait-cm-delete {
         type int32;
         description "Number of clients in wait-cm-delete state";
       }
       leaf wait-subscr-add {
         type int32;
         description "Number of clients in wait-subscr-add state";
       }
       leaf wait-subscr-add-delete {
         type int32;
         description "Number of clients in wait-subscr-add-delete state";
       }
       leaf wait-subscr-delete {
         type int32;
         description "Number of clients in wait-subscr-delete state";
       }
       leaf wait-cm-update {
         type int32;
         description "Number of clients in wait-cm-update state";
       }
       leaf wait-cm-update-delete {
         type int32;
         description "Number of clients in wait-cm-update-delete state";
       }
       leaf wait-auth-req {
         type int32;
         description "Number of clients in wait-auth-req state";
       }
       leaf wait-auth-req-delete {
         type int32;
         description "Number of clients in wait-auth-req-delete state";
       }
       leaf wait-auth-req-release {
         type int32;
         description "Number of clients in wait-auth-req-release state";
       }
       leaf wait-auth-req-release-terminated {
         type int32;
         description "Number of clients in wait-auth-req-release-terminated state";
       }
       leaf wait-auth-act-prof {
         type int32;
         description "Number of clients in wait-auth-act-prof state";
       }
       leaf wait-auth-act-prof-delete {
         type int32;
         description "Number of clients in wait-auth-act-prof-delete state";
       }
       leaf wait-service-deactivation {
         type int32;
         description "Number of clients in wait-service-deactivation state";
       }
       leaf wait-dual-stack-peer-logout {
         type int32;
         description "Number of clients in wait-dual-stack-peer-logout state";
       }
       leaf wait-prof-inst {
         type int32;
         description "Number of clients in wait-prof-inst state";
       }
       leaf wait-prof-inst-delete {
         type int32;
         description "Number of clients in wait-prof-inst-delete state";
       }
       leaf wait-prof-delete {
         type int32;
         description "Number of clients in wait-prof-delete state";
       }
       leaf wait-interface {
         type int32;
         description "Number of clients in wait-interface state";
       }
       leaf wait-sdb-init-mirror-req {
         type int32;
         description "Number of clients in wait-sdb-init-mirror-req state";
       }
       leaf wait-sdb-init-mirror-req-delete {
         type int32;
         description "Number of clients in wait-sdb-init-mirror-req-delete state";
       }
       leaf wait-sdb-active-mirror-req {
         type int32;
         description "Number of clients in wait-sdb-active-mirror-req state";
       }
       leaf wait-sdb-active-mirror-req-delete {
         type int32;
         description "Number of clients in wait-sdb-active-mirror-req-delete state";
       }
       leaf wait-sdb-terminated-mirror-req {
         type int32;
         description "Number of clients in wait-sdb-terminated-mirror-req state";
       }
       leaf wait-sdb-dual-stack-terminating {
         type int32;
         description "Number of clients in wait-sdb-dual-stack-terminating state";
       }
       leaf wait-sdb-dual-stack-clear {
         type int32;
         description "Number of clients in wait-sdb-dual-stack-clear state";
       }
       leaf bound-on-intf-delete {
         type int32;
         description "Number of clients in bound-on-intf-delete state";
       }
     }
     list dhcp-binding {
       leaf allocated-address {
         type jt:ipaddr;
         description "IPv4 or IPv6 address assigned to the DHCP client";
       }
       leaf session-id {
         type string;
         description "Session ID of the client";
       }
       leaf mac-address {
         type jt:mac-addr;
         description "Media access control (hardware) address of the DHCP client";
       }
       leaf lease-expires {
         type int32;
         description "Number of seconds lease will expire in";
       }
       leaf lease-state {
         type string;
         description "Status of the address assignment";
       }
       leaf interface-name {
         type string;
         description "Name of the interface via which the DHCP server transmitted the address assignment";
       }
       leaf lease-end-time {
         type string;
         description "Time when the address assignment will expire, in the format YYYY-MM-DD hh:mm:ss TZ (year, month, date, hour in 24-hour format, minute, second, time zone). The value 'never' indicates that the lease does not expire";
       }
       leaf lease-start-time {
         type string;
         description "Time when the client obtained the address assignment, in the format YYYY-MM-DD hh:mm:ss TZ (year, month, date, hour in 24-hour format, minute, second, time zone)";
       }
       leaf lease-time-violated {
         type string;
         description "Status of lease time validation violation";
       }
       leaf last-packet-received-time {
         type string;
         description "Time at which the most recent packet from the client was received, in the format YYYY-MM-DD hh:mm:ss TZ (year, month, date, hour in 24-hour format, minute, second, time zone)";
       }
       leaf interface-tag-name {
         type string;
         description "Name of the interface tag associated";
       }
       leaf vlan-id {
         type int32;
         description "Vlan id of the client interface";
       }
       leaf svlan-id {
         type int32;
         description "Svlan id of the client interface";
       }
       leaf demux-interface-name {
         type string;
         description "Demux interface name";
       }
       leaf server-ip-address {
         type jt:ipaddr;
         description "IP address of the DHCP server";
       }
       leaf server-interface-name {
         type string;
         description "Interface that server was from";
       }
       leaf bootp-relay-address {
         type jt:ipaddr;
         description "IP address of the bootstrap protocol server that relayed the address assigned by the DHCP server";
       }
       leaf previous-bootp-relay-address {
         type jt:ipaddr;
         description "Previous IP address of the bootstrap protocol server that relayed the address assigned by the DHCP server";
       }
       leaf pool-name {
         type string;
         description "Client pool name";
       }
       leaf profile-name {
         type string;
         description "Client profile name";
       }
       leaf liveness-detection-state {
         type string;
         description "Status of the liveness detection session with the client";
       }
       leaf liveness-detection-method {
         type string;
         description "Method being used for liveness-detection";
       }
       leaf dual-stack-group {
         type string;
         description "Dual stack group referenece by this client";
       }
       leaf dual-stack-key {
         type string;
         description "DUAL STACK key";
       }
       leaf dual-stack-peer-address {
         type jt:ipaddr;
         description "Peer IP or IPV6 address for this dual stack client";
       }
       leaf dual-stack-peer-prefix {
         type jt:ipaddr;
         description "Peer IPV6 prefix for this dual stack client";
       }
       leaf generated-circuit-id {
         type string;
         description "Generated circuit id";
       }
       leaf generated-remote-id {
         type string;
         description "Generated remote id";
       }
       leaf dhcp-lease-binding-type {
         type string;
         description "Type of the address assignment";
       }
       leaf client-id-len {
         type int32;
         description "Number of bytes in client id";
       }
       leaf client-id {
         type string;
         description "Four bytes of the client id";
       }
       leaf alt-client-id-len {
         type int32;
         description "Number of bytes in alternate client id";
       }
       leaf alt-client-id {
         type string;
         description "Four byte of the alternate client id";
       }
       leaf client-option-type {
         type string;
         description "Type option 60 or option 82";
       }
       leaf client-option-len {
         type int32;
         description "Number of bytes in client option 60 / option 82 data";
       }
       leaf client-option-data {
         type string;
         description "Hex dump of client option 60 / option 82 data";
       }
       leaf option-82-length-from-client {
         type int32;
         description "Option 82 length from client";
       }
       leaf option-82-data-from-client {
         type string;
         description "Option 82 data from client";
       }
       leaf hardware-type {
         type string;
         description "Client hardware type";
       }
       leaf logical-system-routing-instance {
         type string;
         description "Client router context logical system and routing instance";
       }
       leaf bridge-domain {
         type string;
         description "Client router context bridge domain";
       }
       leaf client-info {
         type string;
         description "General information about the client";
       }
       leaf retail-logical-system-routing-instance {
         type string;
         description "L3 wholesale retail client router context logical system and routing instance";
       }
       leaf wholesale-logical-system-routing-instance {
         type string;
         description "L3 wholesale client router context logical system and routing instance";
       }
       leaf antispoof-filter-name {
         type string;
         description "Antispoof filter name";
       }
       leaf antispoof-filter-flags {
         type string;
         description "Antispoof filter flags";
       }
       leaf antispoof-filter-state {
         type string;
         description "Antispoof filter state";
       }
       leaf antispoof-filter-type {
         type string;
         description "Antispoof filter type";
       }
       leaf antispoof-filter-term-id {
         type string;
         description "Antispoof filter term id";
       }
       leaf antispoof-filter-action {
         type string;
         description "Antispoof filter type";
       }
       leaf antispoof-filter-parent {
         type string;
         description "Antispoof filter parent pointer";
       }
       leaf antispoof-filter-owner {
         type string;
         description "Antispoof filter owner pointer";
       }
       leaf authentication-num-servers {
         type int32;
         description "Number of servers in authentication group";
       }
       leaf client-stale-count {
         type int32;
         description "Number of clients in stale list";
       }
       leaf auth-client-limit {
         type int32;
         description "Client limit from authentication daemon";
       }
       leaf auth-relay-server-group {
         type string;
         description "Value of pointer to authentication daemon server group";
       }
       leaf aci-iflset-name {
         type string;
         description "ACI-VLAN iflset name";
       }
       leaf aci-iflset-index {
         type int32;
         description "ACI-VLAN iflset index";
       }
       leaf aci-iflset-session-id {
         type string;
         description "ACI-VLAN iflset Session ID";
       }
       leaf dhcp-relay-id-len {
         type int32;
         description "Number of bytes in relay id";
       }
       leaf dhcp-relay-id {
         type string;
         description "DHCPv4 relay-id";
       }
     }
   }
   grouping dhcp-relay-statistics-information-block {
     leaf dropped-packet-total {
       type uint32;
       description "Total number of packets discarded by the DHCP relay because of errors";
     }
     leaf dropped-packet-bad-hardware {
       type uint32;
       description "Number of packets discarded by the DHCP relay because they specified an invalid hardware address";
     }
     leaf dropped-packet-bootp-packet {
       type uint32;
       description "Number of packets discarded by the DHCP relay because they  are bootp packets";
     }
     leaf dropped-packet-bad-bootp-opcode {
       type uint32;
       description "Number of packets discarded by the DHCP relay because they specified an invalid operation code in bootp";
     }
     leaf dropped-packet-bad-options {
       type uint32;
       description "Number of packets discarded by the DHCP relay because they specified invalid options";
     }
     leaf dropped-packet-invalid-server-address {
       type uint32;
       description "Number of packets discarded by the DHCP relay because they specified an invalid server address";
     }
     leaf dropped-packet-no-addresses {
       type uint32;
       description "Number of packets discarded by the DHCP relay because there were no addresses available for it to assign";
     }
     leaf dropped-packet-no-interface-cfg {
       type uint32;
       description "Number of packets discarded by the DHCP relay because packets arrived on unconfigured interface";
     }
     leaf dropped-packet-no-local-address {
       type uint32;
       description "Number of packets discarded by the DHCP relay because there was no valid local address";
     }
     leaf dropped-packet-too-short {
       type uint32;
       description "Number of packets discarded by the DHCP relay because they were too short";
     }
     leaf dropped-packet-send-error {
       type uint32;
       description "Number of packets that the DHCP relay could not send";
     }
     leaf dropped-packet-option-60 {
       type uint32;
       description "Number of packets discarded with no matching option-60";
     }
     leaf dropped-packet-relay-option {
       type uint32;
       description "Number of packets discarded due to relay-option processing";
     }
     leaf dropped-packet-option-82 {
       type uint32;
       description "Number of packets discarded because option-82 could not be added";
     }
     leaf dropped-packet-authentication {
       type uint32;
       description "Number of packets discarded because authentication failed";
     }
     leaf dropped-packet-dynamic-profile {
       type uint32;
       description "Number of packets discarded because a dynamic profile failed";
     }
     leaf dropped-packet-license {
       type uint32;
       description "Number of packets discarded because of a license failure";
     }
     leaf dropped-packet-bad-dhcp-opcode {
       type uint32;
       description "Number of packets discarded because of bad DHCP opcode";
     }
     leaf dropped-packet-no-options {
       type uint32;
       description "Number of packets discarded because of no options";
     }
     leaf dropped-packet-hop-limit {
       type uint32;
       description "Number of packets discarded because of hop limit reached";
     }
     leaf dropped-packet-wait-time {
       type uint32;
       description "Number of packets discarded because of less wait time";
     }
     leaf dropped-packet-ttl-expired {
       type uint32;
       description "Number of packets discarded because of ttl expired";
     }
     leaf dropped-packet-bad-udp-checksum {
       type uint32;
       description "Number of packets discarded because of bad udp checksum";
     }
     leaf dropped-packet-inactive-vlan {
       type uint32;
       description "Number of packets discarded because of inactive VLAN";
     }
     leaf dropped-packet-event-rate-analyzer {
       type uint32;
       description "Number of packets discarded because of ERA throttling";
     }
     leaf dropped-packet-client-lookup {
       type uint32;
       description "Number of packets discarded because no client binding was found";
     }
     leaf dropped-packet-proxy-no-server-addr {
       type uint32;
       description "Number of packets discarded because client server address is 0, but should not be";
     }
     leaf lease-time-violations-drop {
       type uint32;
       description "Packets dropped because of lease time violation";
     }
     leaf dropped-packet-leasequery-repl-no-circuitid {
       type uint32;
       description "Packets discarded as no circuit-id in leasequery replies";
     }
     leaf dropped-packet-leasequery-repl-with-error-code {
       type uint32;
       description "Packets discarded, leasequery reply with error code";
     }
     leaf dropped-packet-leasequery-repl-with-query-term {
       type uint32;
       description "Packets discarded, leasequery reply with error code";
     }
     leaf dropped-packet-older-leasequery-repl {
       type uint32;
       description "Number of packets discarded because leasequery reply is of older timestamp";
     }
     leaf dropped-packet-abort-leasequery-repl {
       type uint32;
       description "Number of packets discarded due to abort of leasequery reply processing";
     }
     leaf dropped-packet-during-leasequery-repl {
       type uint32;
       description "Packets discarded as received during leasequery reply processing";
     }
     leaf dropped-packet-relay-source-no-lpbk-interface {
       type uint32;
       description "Number of packets discarded as received with relay source config without loopback config";
     }
     leaf dropped-packet-bad-gi-address {
       type uint32;
       description "Number of packet discarded because of bad gi_address";
     }
     leaf dropped-packet-short-cycle-protect {
       type uint32;
       description "Number of packets discarded because of encapsulation lockout";
     }
     leaf requested-ip-address-drop {
       type uint32;
       description "Packets dropped because of requested ip address already in use";
     }
     leaf dropped-packet-load-balance-user-plane {
       type uint32;
       description "Packet dropped because of load balancing";
     }
     leaf dropped-packet-dhcp-service-total {
       type uint32;
       description "Total number of packets discarded by the DHCP service because of errors";
     }
     leaf forwarded-packets-total {
       type uint32;
       description "Total number of packets forwarded";
     }
     leaf forwarded-bootrequest-packets {
       type uint32;
       description "Number of bootrequest packets forwarded";
     }
     leaf forwarded-bootreply-packets {
       type uint32;
       description "Number of bootreply packets forwarded";
     }
     leaf dhcp-external-server-response-state {
       type string;
       description "Set if external server is responding otherwise Clear";
     }
     list message-table {
       description "Information about one or more DHCP or bootstrap protocol (BOOTP) messages sent or received by the DHCP relay";
       leaf message-direction {
         type string;
         description "Indicator of whether the DHCP relay sent or received the messages";
       }
       list message {
         description "Information about a DHCP or BOOTP message";
         leaf message-name {
           type string;
           description "Name of the message";
         }
         leaf message-count {
           type uint32;
           description "Number of times the DCHP relay received or sent the message";
         }
       }
     }
   }
   grouping dhcp-relay-leasequery-statistics-block {
     leaf in-flight-leasequeries {
       type uint32;
       description "Number of in-flight leasequeries";
     }
     leaf total-leasequeries {
       type uint32;
       description "Total Number of leasequeries";
     }
     leaf total-leasequery-attempts {
       type uint32;
       description "Total Number of leasequery attempts";
     }
     leaf total-leasequery-repl-packet-retries {
       type uint32;
       description "Total Number of packet retries";
     }
     leaf total-leasequery-repl-max-retried {
       type uint32;
       description "Total Number of leasequery reply maximum retried";
     }
     container dhcp-leasequery-info-statistics {
       leaf leasequery-xid {
         type uint32;
         description "Leasequery unique XID";
       }
       leaf leasequery-state {
         type string;
         description "Leasequery state";
       }
       leaf leasequery-confirmed-replies {
         type uint32;
         description "Number of confirmed Leasequery replies";
       }
       leaf leasequery-unconfirmed-replies {
         type uint32;
         description "Numnrt of unconfirmed Leasequery replies";
       }
       leaf leasequery-attempts {
         type uint32;
         description "Number of Leasequery attempts";
       }
       container dhcp-leasequery-server-info-statistics {
         leaf server-ip-address {
           type jt:ipaddr;
           description "IP address of the DHCP server";
         }
         leaf leasequery-server-xid {
           type uint32;
           description "Leasequery Server unique XID";
         }
         leaf leasequery-server-state {
           type string;
           description "Leasequery Server state";
         }
       }
     }
   }
   grouping dhcp-relay-bulk-leasequery-conn-statistics-block {
     leaf total-connections-requested {
       type uint32;
       description "Number of TCP connections requested";
     }
     leaf total-connections-attempted {
       type uint32;
       description "Number of TCP connections attempted";
     }
     leaf total-connections-connected {
       type uint32;
       description "Number of connected TCP connections";
     }
     leaf total-connections-terminated-by-server {
       type uint32;
       description "Number of connections terminated by server";
     }
     leaf total-connections-max-attempted {
       type uint32;
       description "Number of requested TCP connections with max attempts reached";
     }
     leaf total-connections-closed-due-to-error {
       type uint32;
       description "Number of TCP connections closed due to error";
     }
     leaf in-flight-connections-connected {
       type uint32;
       description "Number of in-flight TCP connections in connected state";
     }
     leaf total-bulk-leasequery-repl-packet-retries {
       type uint32;
       description "Number of bulk leasequery reply packet retries";
     }
     leaf total-bulk-leasequery-repl-max-retried {
       type uint32;
       description "Number of bulk leasequery reply max retried";
     }
     container dhcp-bulk-leasequery-info-statistics {
       leaf bulk-leasequery-xid {
         type uint32;
         description "Bulk Leasequery unique XID";
       }
       leaf bulk-leasequery-total-servers {
         type uint32;
         description "Total Bulk Leasequery servers";
       }
       container dhcp-bulk-leasequery-server-info-statistics {
         leaf server-ip-address {
           type jt:ipaddr;
           description "IP address of the DHCP server";
         }
         leaf bulk-leasequery-server-state {
           type string;
           description "Bulk Leasequery Server state";
         }
         leaf bulk-leasequery-server-attempts {
           type uint32;
           description "Bulk Leasequery Server attempts";
         }
       }
     }
   }
   grouping dhcp-relay-lockout-entries-information-block {
     container dhcp-relay-lockout-entries-all {
       leaf dhcp-lockout-index {
         type int32;
         description "Index of the lockout entry";
       }
       leaf dhcp-lockout-key {
         type string;
         description "Key of the lockout entry";
       }
       leaf dhcp-lockout-state {
         type string;
         description "Lockout state";
       }
       leaf dhcp-lockout-expiry {
         type int32;
         description "Number of second before timer in current state expires";
       }
       leaf dhcp-lockout-elapsed-time {
         type int32;
         description "Time elapsed in current state";
       }
       leaf dhcp-lockout-count {
         type int32;
         description "Number of consecutive lockouts ";
       }
     }
     container dhcp-relay-lockout-entry {
       leaf dhcp-lockout-index {
         type int32;
         description "Index of the lockout entry";
       }
       leaf dhcp-lockout-key {
         type string;
         description "Key of the lockout entry";
       }
       leaf dhcp-lockout-state {
         type string;
         description "Lockout state";
       }
       leaf dhcp-lockout-expiry-time {
         type string;
         description "Absolute expiry time of current state ";
       }
       leaf dhcp-lockout-expiry-relative-time {
         type int32;
         description "Number of second before timer in current state expires ";
       }
       leaf dhcp-lockout-count {
         type int32;
         description "Number of consecutive lockouts ";
       }
       leaf dhcp-lockout-next-time {
         type int32;
         description "Next lockout interval ";
       }
       leaf dhcp-lockout-min-time {
         type int32;
         description "Minimun lockout interval ";
       }
       leaf dhcp-lockout-err-code {
         type int32;
         description "Lockout error code ";
       }
     }
   }
   grouping dhcp-server-binding-information-block {
     container binding-summary {
       leaf binding-count {
         type int32;
         description "Number of bindings in this routing instance";
       }
       leaf init-count {
         type int32;
       }
       leaf bound-count {
         type int32;
       }
       leaf selecting-count {
         type int32;
       }
       leaf requesting-count {
         type int32;
       }
       leaf renewing-count {
         type int32;
       }
       leaf releasing-count {
         type int32;
       }
       leaf restore-count {
         type int32;
         description "Number of clients waiting to be restored";
       }
     }
     container binding-internal-states {
       leaf init {
         type int32;
         description "Number of clients init state";
       }
       leaf wait-auth-req {
         type int32;
         description "Number of clients in wait-auth-req state";
       }
       leaf selecting {
         type int32;
         description "Number of clients in selecting state";
       }
       leaf wait-auth-req-delete {
         type int32;
         description "Number of clients in wait-auth-req-delete state";
       }
       leaf wait-auth-req-release {
         type int32;
         description "Number of clients in wait-auth-req-release state";
       }
       leaf wait-auth-req-release-terminated {
         type int32;
         description "Number of clients in wait-auth-req-release-terminated state";
       }
       leaf wait-cm-add {
         type int32;
         description "Number of clients in wait-cm-add state";
       }
       leaf wait-cm-add-delete {
         type int32;
         description "Number of clients in wait-cm-add-delete state";
       }
       leaf wait-cm-delete {
         type int32;
         description "Number of clients in wait-cm-delete state";
       }
       leaf wait-subscr-add {
         type int32;
         description "Number of clients in wait-subscr-add state";
       }
       leaf wait-subscr-add-delete {
         type int32;
         description "Number of clients in wait-subscr-add-delete state";
       }
       leaf wait-subscr-delete {
         type int32;
         description "Number of clients in wait-subscr-delete state";
       }
       leaf bound {
         type int32;
         description "Number of clients in bound state";
       }
       leaf wait-grace-period {
         type int32;
         description "Number of clients in wait-grace-period state";
       }
       leaf wait-auth-act-prof {
         type int32;
         description "Number of clients in wait-auth-act-prof state";
       }
       leaf wait-auth-act-prof-delete {
         type int32;
         description "Number of clients in wait-auth-act-prof-delete state";
       }
       leaf wait-prof-inst {
         type int32;
         description "Number of clients in wait-prof-inst state";
       }
       leaf wait-prof-inst-delete {
         type int32;
         description "Number of clients in wait-prof-inst-delete state";
       }
       leaf wait-prof-delete {
         type int32;
         description "Number of clients in wait-prof-delete state";
       }
       leaf wait-interface {
         type int32;
         description "Number of clients in wait-interface state";
       }
       leaf wait-sdb-init-mirror-req {
         type int32;
         description "Number of clients in wait-sdb-init-mirror-req state";
       }
       leaf wait-sdb-init-mirror-req-delete {
         type int32;
         description "Number of clients in wait-sdb-init-mirror-req-delete state";
       }
       leaf wait-sdb-active-mirror-req {
         type int32;
         description "Number of clients in wait-sdb-active-mirror-req state";
       }
       leaf wait-sdb-active-mirror-req-delete {
         type int32;
         description "Number of clients in wait-sdb-active-mirror-req-delete state";
       }
       leaf wait-sdb-terminated-mirror-req {
         type int32;
         description "Number of clients in wait-sdb-terminated-mirror-req state";
       }
       leaf reconfigure {
         type int32;
         description "Number of clients in reconfigure state";
       }
       leaf bound-on-intf-delete {
         type int32;
         description "Number of clients in bound-on-intf-delete state";
       }
       leaf wait-defer-delete {
         type int32;
         description "Number of clients in wait-defer-delete state";
       }
       leaf wait-service-deactivation {
         type int32;
         description "Number of clients in wait-service-deactivation state";
       }
       leaf wait-dual-stack-peer-logout {
         type int32;
         description "Number of clients in wait-dual-stack-peer-logout state";
       }
       leaf wait-sdb-dual-stack-terminating {
         type int32;
         description "Number of clients in wait-sdb-dual-stack-terminating state";
       }
       leaf wait-sdb-dual-stack-clear {
         type int32;
         description "Number of clients in wait-sdb-dual-stack-clear state";
       }
       leaf wait-auth-addr-on-demand {
         type int32;
         description "Number of clients in wait-auth-addr-on-demand state";
       }
       leaf wait-auth-addr-on-demand-delete {
         type int32;
         description "Number of clients in wait-auth-addr-on-demand-delete state";
       }
     }
     list dhcp-binding {
       leaf allocated-address {
         type jt:ipaddr;
         description "IPv4 or IPv6 address assigned to the DHCP client";
       }
       leaf session-id {
         type string;
         description "Session ID of the client";
       }
       leaf mac-address {
         type jt:mac-addr;
         description "Media access control (hardware) address of the DHCP client";
       }
       leaf lease-expires {
         type int32;
         description "Number of seconds lease will expire in";
       }
       leaf lease-state {
         type string;
         description "Status of the address assignment";
       }
       leaf interface-name {
         type string;
         description "Name of the interface via which the DHCP server transmitted the address assignment";
       }
       leaf protocol-used {
         type string;
         description "Protocol used by client to perform this binding BOOTP/DHCP";
       }
       leaf lease-end-time {
         type string;
         description "Time when the address assignment will expire, in the format YYYY-MM-DD hh:mm:ss TZ (year, month, date, hour in 24-hour format, minute, second, time zone). The value 'never' indicates that the lease does not expire";
       }
       leaf lease-start-time {
         type string;
         description "Time when the client obtained the address assignment, in the format YYYY-MM-DD hh:mm:ss TZ (year, month, date, hour in 24-hour format, minute, second, time zone)";
       }
       leaf lease-time-violated {
         type string;
         description "Status of binding wrt lease time validation";
       }
       leaf last-packet-received-time {
         type string;
         description "Time at which the most recent packet from the client was received, in the format YYYY-MM-DD hh:mm:ss TZ (year, month, date, hour in 24-hour format, minute, second, time zone)";
       }
       leaf interface-tag-name {
         type string;
         description "Name of the interface tag associated to particular interface";
       }
       leaf vlan-id {
         type int32;
         description "Vlan id of the client interface";
       }
       leaf svlan-id {
         type int32;
         description "Svlan id of the client interface";
       }
       leaf demux-interface-name {
         type string;
         description "Demux interface name";
       }
       leaf server-ip-address {
         type jt:ipaddr;
         description "IP address of the DHCP server";
       }
       leaf bootp-relay-address {
         type jt:ipaddr;
         description "IP address of the bootstrap protocol server that relayed the address assigned by the DHCP server";
       }
       leaf previous-bootp-relay-address {
         type jt:ipaddr;
         description "Previous IP address of the bootstrap protocol server that relayed the address assigned by the DHCP server";
       }
       leaf pool-name {
         type string;
         description "Client pool name";
       }
       leaf profile-name {
         type string;
         description "Client profile name";
       }
       leaf liveness-detection-state {
         type string;
         description "Status of the liveness detection session with the client";
       }
       leaf liveness-detection-method {
         type string;
         description "Method being used for liveness-detection";
       }
       leaf dual-stack-group {
         type string;
         description "Dual stack group referenece by this client";
       }
       leaf dual-stack-key {
         type string;
         description "DUAL STACK key";
       }
       leaf dual-stack-peer-address {
         type jt:ipaddr;
         description "Peer IP or IPV6 address for this dual stack client";
       }
       leaf dual-stack-peer-prefix {
         type jt:ipaddr;
         description "Peer IPV6 prefix for this dual stack client";
       }
       leaf reconfigure-status {
         type string;
         description "Reconfigure/forcerenew abort action for this client";
       }
       leaf dhcp-lease-binding-type {
         type string;
         description "Type of the address assignment";
       }
       leaf client-id-len {
         type int32;
         description "Number of bytes in client id";
       }
       leaf client-id {
         type string;
         description "Client id";
       }
       leaf alt-client-id-len {
         type int32;
         description "Number of bytes in alternate client id";
       }
       leaf alt-client-id {
         type string;
         description "Alternate client id";
       }
       leaf client-option-type {
         type string;
         description "Type option 60 or option 82";
       }
       leaf client-option-len {
         type int32;
         description "Number of bytes in client option 60 / option 82 data";
       }
       leaf client-option-data {
         type string;
         description "Hex dump of client option 60 / option 82 data";
       }
       leaf option-82-length-from-client {
         type int32;
         description "Option 82 length from client";
       }
       leaf option-82-data-from-client {
         type string;
         description "Option 82 data from client";
       }
       leaf hardware-type {
         type string;
         description "Client hardware type";
       }
       leaf logical-system-routing-instance {
         type string;
         description "Client router context logical system and routing instance";
       }
       leaf bridge-domain {
         type string;
         description "Client router context bridge domain";
       }
       leaf client-info {
         type string;
         description "General information about the client";
       }
       leaf address-pool-drain-info {
         type string;
         description "Address pool drain information";
       }
       leaf lease-time-info {
         type int32;
         description "Lease time";
       }
       leaf t1-renewal-time-info {
         type string;
         description "T1 renewal time";
       }
       leaf t2-rebinding-time-info {
         type string;
         description "T2 rebinding time";
       }
       leaf reauth-vsa-info {
         type string;
         description "Reauthenticate VSA information";
       }
       leaf reauth-renew-info {
         type string;
         description "Reauthenticate lease-renewal information";
       }
       leaf reauth-remote-id-mismatch-info {
         type string;
         description "Reauthenticate remote-id-mismatch information";
       }
       leaf retail-logical-system-routing-instance {
         type string;
         description "L3 wholesale retail client router context logical system and routing instance";
       }
       leaf retail-bridge-domain {
         type string;
         description "L3 wholesale retail client router context bridge domain";
       }
       leaf wholesale-logical-system-routing-instance {
         type string;
         description "L3 wholesale client router context logical system and routing instance";
       }
       leaf wholesale-bridge-domain {
         type string;
         description "L3 wholesale client router context bridge domain";
       }
       leaf antispoof-filter-name {
         type string;
         description "Antispoof filter name";
       }
       leaf antispoof-filter-flags {
         type string;
         description "Antispoof filter flags";
       }
       leaf antispoof-filter-state {
         type string;
         description "Antispoof filter state";
       }
       leaf antispoof-filter-type {
         type string;
         description "Antispoof filter type";
       }
       leaf antispoof-filter-term-id {
         type string;
         description "Antispoof filter term id";
       }
       leaf antispoof-filter-action {
         type string;
         description "Antispoof filter type";
       }
       leaf antispoof-filter-parent {
         type string;
         description "Antispoof filter parent pointer";
       }
       leaf antispoof-filter-owner {
         type string;
         description "Antispoof filter owner pointer";
       }
       leaf authentication-num-servers {
         type int32;
         description "Number of servers in authentication group";
       }
       leaf client-stale-count {
         type int32;
         description "Number of clients in stale list";
       }
       leaf auth-client-limit {
         type int32;
         description "Client limit from authentication daemon";
       }
       leaf auth-relay-server-group {
         type string;
         description "Value of pointer to authentication daemon server group";
       }
       leaf aci-iflset-name {
         type string;
         description "ACI-VLAN iflset name";
       }
       leaf aci-iflset-index {
         type int32;
         description "ACI-VLAN iflset index";
       }
       leaf aci-iflset-session-id {
         type string;
         description "ACI-VLAN iflset Session ID";
       }
       leaf dhcp-relay-id-len {
         type int32;
         description "Number of bytes in relay id";
       }
       leaf dhcp-relay-id {
         type string;
         description "DHCPv4 relay-id";
       }
     }
   }
   grouping dhcp-server-statistics-information-block {
     leaf dropped-packet-total {
       type uint32;
       description "Total number of packets discarded by the DHCP server because of errors";
     }
     leaf dropped-packet-bad-hardware {
       type uint32;
       description "Number of packets discarded by the DHCP server because they specified an invalid hardware address";
     }
     leaf dropped-packet-bootp-packet {
       type uint32;
       description "Number of packets discarded by the DHCP server because they are bootp packets";
     }
     leaf dropped-packet-bad-bootp-opcode {
       type uint32;
       description "Number of packets discarded by the DHCP server because they specified an invalid operation code in bootp";
     }
     leaf dropped-packet-bad-options {
       type uint32;
       description "Number of packets discarded by the DHCP server because they specified invalid options";
     }
     leaf dropped-packet-invalid-server-address {
       type uint32;
       description "Number of packets discarded by the DHCP server because they specified an invalid server address";
     }
     leaf dropped-packet-no-addresses {
       type uint32;
       description "Number of packets discarded by the DHCP server because there were no addresses available for it to assign";
     }
     leaf dropped-packet-no-interface-cfg {
       type uint32;
       description "Number of packets discarded by the DHCP server because packets arrived on unconfigured interface";
     }
     leaf dropped-packet-no-local-address {
       type uint32;
       description "Number of packets discarded by the DHCP server because there was no valid local address";
     }
     leaf dropped-packet-too-short {
       type uint32;
       description "Number of packets discarded by the DHCP server because they were too short";
     }
     leaf dropped-packet-send-error {
       type uint32;
       description "Number of packets that the DHCP server could not send";
     }
     leaf dropped-packet-option-60 {
       type uint32;
       description "Number of packets discarded with no matching option-60";
     }
     leaf dropped-packet-option-82 {
       type uint32;
       description "Number of packets discarded because option-82 could not be added";
     }
     leaf dropped-packet-authentication {
       type uint32;
       description "Number of packets discarded because authentication failed";
     }
     leaf dropped-packet-dynamic-profile {
       type uint32;
       description "Number of packets discarded because a dynamic profile failed";
     }
     leaf dropped-packet-license {
       type uint32;
       description "Number of packets discarded because of a license failure";
     }
     leaf dropped-packet-bad-dhcp-opcode {
       type uint32;
       description "Number of packets discarded because of bad DHCP opcode";
     }
     leaf dropped-packet-no-options {
       type uint32;
       description "Number of packets discarded because of no options";
     }
     leaf dropped-packet-hop-limit {
       type uint32;
       description "Number of packets discarded because of hop limit reached";
     }
     leaf dropped-packet-wait-time {
       type uint32;
       description "Number of packets discarded because of less wait time";
     }
     leaf dropped-packet-ttl-expired {
       type uint32;
       description "Number of packets discarded because of ttl expired";
     }
     leaf dropped-packet-bad-udp-checksum {
       type uint32;
       description "Number of packets discarded because of bad udp checksum";
     }
     leaf dropped-packet-inactive-vlan {
       type uint32;
       description "Number of packets discarded because of inactive VLAN";
     }
     leaf dropped-packet-event-rate-analyzer {
       type uint32;
       description "Number of packets discarded because of ERA throttling";
     }
     leaf dropped-packet-client-lookup {
       type uint32;
       description "Number of packets discarded because no client binding was found";
     }
     leaf lease-time-violations-drop {
       type uint32;
       description "Packets dropped because of lease time violation";
     }
     leaf dropped-packet-bad-gi-address {
       type uint32;
       description "Number of packet discarded because of bad gi_address";
     }
     leaf dropped-packet-short-cycle-protect {
       type uint32;
       description "Number of packet discarded because of encap lockout";
     }
     leaf dropped-packet-invalid-subnet {
       type uint32;
       description "Number of packets discarded because of invalid subnet in server mode";
     }
     leaf dropped-packet-load-balance-user-plane {
       type uint32;
       description "Number of packets discarded because of load balancing";
     }
     leaf dropped-packet-dhcp-service-total {
       type uint32;
       description "Number of packets discarded at dhcp-service level";
     }
     leaf forwarded-packets-total {
       type uint32;
       description "Total number of packets forwarded";
     }
     leaf forwarded-bootrequest-packets {
       type uint32;
       description "Number of bootrequest packets forwarded";
     }
     leaf forwarded-bootreply-packets {
       type uint32;
       description "Number of bootreply packets forwarded";
     }
     list offer-delay-info {
       description "Information about offer delay queue status of the DHCP server";
       leaf delay-string {
         type string;
         description "Indicator of offer delay";
       }
       list queue {
         description "Information about the Delay Queue status";
         leaf delay-status {
           type string;
           description "Status of packets in delay queue";
         }
         leaf delay-count {
           type uint32;
           description "Number of packets in this status";
         }
       }
     }
     list message-table {
       description "Information about one or more DHCP or bootstrap protocol (BOOTP) messages sent or received by the DHCP server";
       leaf message-direction {
         type string;
         description "Indicator of whether the DHCP server sent or received the messages";
       }
       list message {
         description "Information about a DHCP or BOOTP message";
         leaf message-name {
           type string;
           description "Name of the message";
         }
         leaf message-count {
           type uint32;
           description "Number of times the DCHP server received or sent the message";
         }
       }
     }
   }
   grouping dhcp-server-bulk-leasequery-conn-statistics-block {
     leaf total-accepted-tcp-connections {
       type uint32;
       description "Number of accepted TCP connections";
     }
     leaf total-not-accepted-tcp-connections {
       type uint32;
       description "Number of not accepted TCP connections";
     }
     leaf tcp-connections-closed-due-to-error {
       type uint32;
       description "Number of connections closed due to error";
     }
     leaf tcp-connections-closed-due-to-max-empty-replies {
       type uint32;
       description "Number of connections closed due to max-empty-replies";
     }
     leaf in-flight-tcp-connections {
       type uint32;
       description "In-flight TCP connections";
     }
   }
   grouping dhcp-server-lockout-entries-information-block {
     container dhcp-server-lockout-entries-all {
       leaf dhcp-lockout-index {
         type int32;
         description "Index of the lockout entry";
       }
       leaf dhcp-lockout-key {
         type string;
         description "Key of the lockout entry";
       }
       leaf dhcp-lockout-state {
         type string;
         description "Lockout state";
       }
       leaf dhcp-lockout-expiry {
         type int32;
         description "Number of second before timer in current state expires";
       }
       leaf dhcp-lockout-elapsed-time {
         type int32;
         description "Time elapsed in current state";
       }
       leaf dhcp-lockout-count {
         type int32;
         description "Number of consecutive lockouts ";
       }
     }
     container dhcp-server-lockout-entry {
       leaf dhcp-lockout-index {
         type int32;
         description "Index of the lockout entry";
       }
       leaf dhcp-lockout-key {
         type string;
         description "Key of the lockout entry";
       }
       leaf dhcp-lockout-state {
         type string;
         description "Lockout state";
       }
       leaf dhcp-lockout-expiry-time {
         type string;
         description "Absolute expiry time of current state ";
       }
       leaf dhcp-lockout-expiry-relative-time {
         type int32;
         description "Number of second before timer in current state expires ";
       }
       leaf dhcp-lockout-count {
         type int32;
         description "Number of consecutive lockouts ";
       }
       leaf dhcp-lockout-next-time {
         type int32;
         description "Next lockout interval ";
       }
       leaf dhcp-lockout-min-time {
         type int32;
         description "Minimun lockout interval ";
       }
       leaf dhcp-lockout-err-code {
         type int32;
         description "Lockout error code ";
       }
     }
   }
   grouping dhcp-client-binding-information-block {
     container binding-summary {
       leaf binding-count {
         type int32;
         description "Number of bindings in this routing instance";
       }
       leaf init-count {
         type int32;
       }
       leaf bound-count {
         type int32;
       }
       leaf selecting-count {
         type int32;
       }
       leaf requesting-count {
         type int32;
       }
       leaf renewing-count {
         type int32;
       }
       leaf releasing-count {
         type int32;
       }
       leaf declining-count {
         type int32;
       }
       leaf arpcheck-count {
         type int32;
       }
       leaf restore-count {
         type int32;
         description "Number of clients waiting to be restored";
       }
     }
     list dhcp-binding {
       leaf allocated-address {
         type jt:ipaddr;
         description "IPv4 or IPv6 address assigned to the DHCP client";
       }
       leaf mac-address {
         type jt:mac-addr;
         description "Media access control (hardware) address of the DHCP client";
       }
       leaf lease-expires {
         type int32;
         description "Number of seconds lease will expire in";
       }
       leaf lease-state {
         type string;
         description "Status of the address assignment";
       }
       leaf interface-name {
         type string;
         description "Name of the interface via which the DHCP server transmitted the address assignment";
       }
       container dhcp-option-table {
         list dhcp-option {
           leaf dhcp-option-code {
             type int32;
             description "Numeric code assigned to the DHCP option";
           }
           leaf dhcp-option-name {
             type string;
             description "Name of the DHCP option";
           }
           leaf dhcp-option-type {
             type string;
             description "Type of value for the DHCP option (for example, string [word], integer, IP address)";
           }
           leaf dhcp-option-value {
             type string;
             description "Value of the DHCP option";
           }
         }
       }
       container dhcp-update-ra-interface-table {
         list dhcp-update-ra-interface {
           leaf dhcp-update-ra-interface-name {
             type string;
             description "Name of the interface which dhcp client update router advertisement for";
           }
           leaf dhcp-update-ra-prefix {
             type string;
             description "The prefix sent to router advertisement";
           }
           leaf dhcp-update-ra-ndra-pool-name {
             type string;
             description "The NDRA pool name which updated by dhcp client ";
           }
         }
       }
       container dhcp-update-dynamic-pool-table {
         list dhcp-update-dynamic-pool {
           leaf dhcp-update-dynamic-pool-name {
             type string;
             description "Name of the dynamic pool which dhcp client update";
           }
           leaf dhcp-update-dynamic-pool-prefix {
             type string;
             description "The prefix update to dynamic pool by dhcp client";
           }
           leaf dhcp-update-dynamic-pool-low-prefix {
             type string;
             description "The low IPv6 prefix assigned to the dynamic pool";
           }
           leaf dhcp-update-dynamic-pool-high-prefix {
             type string;
             description "The high IPv6 prefix assigned to the dynamic pool";
           }
         }
       }
       leaf allocated-prefix {
         type string;
         description "IPv4 or IPv6 address assigned to the DHCP client";
       }
       leaf client-type {
         type string;
         description "Client type for the interface";
       }
       leaf client-duid {
         type string;
         description "Client duid of the client interface";
       }
       leaf server-ip {
         type jt:ipaddr;
         description "IP address of the DHCPV6 server";
       }
       leaf lease-end-time {
         type string;
         description "Time when the address assignment will expire, in the format YYYY-MM-DD hh:mm:ss TZ (year, month, date, hour in 24-hour format, minute, second, time zone). The value 'never' indicates that the lease does not expire";
       }
       leaf lease-start-time {
         type string;
         description "Time when the client obtained the address assignment, in the format YYYY-MM-DD hh:mm:ss TZ (year, month, date, hour in 24-hour format, minute, second, time zone)";
       }
       leaf vlan-id {
         type int32;
         description "Vlan id of the client interface";
       }
       leaf svlan-id {
         type int32;
         description "Svlan id of the client interface";
       }
       leaf vendor-id {
         type string;
         description "Vendor identifier of the client interface";
       }
       leaf server-ip-address {
         type jt:ipaddr;
         description "IP address of the DHCP server";
       }
       leaf bind-type {
         type string;
         description "Client bind type for the interface";
       }
       leaf rapid-commit {
         type string;
         description "Rapid commit two msg exchange flag";
       }
       leaf preferred-prefix-length {
         type int32;
         description "Preferred prefix length";
       }
       leaf sub-prefix-length {
         type int32;
         description "Sub prefix length";
       }
       leaf requested-prefix {
         type string;
         description "IPv4 or IPv6 address assigned to the DHCP client";
       }
       leaf update-server {
         type string;
         description "Update server flag to update TCP/IP settings downstream";
       }
       leaf bootp-relay-address {
         type jt:ipaddr;
         description "IP address of the bootstrap protocol server that relayed the address assigned by the DHCP server";
       }
       leaf previous-bootp-relay-address {
         type jt:ipaddr;
         description "Previous IP address of the bootstrap protocol server that relayed the address assigned by the DHCP server";
       }
       leaf dhcp-lease-binding-type {
         type string;
         description "Type of the address assignment";
       }
       leaf client-id-len {
         type int32;
         description "Number of bytes in client id";
       }
       leaf client-id {
         type string;
         description "Client id";
       }
       leaf alt-client-id-len {
         type int32;
         description "Number of bytes in alternate client id";
       }
       leaf alt-client-id {
         type string;
         description "Alternate client id";
       }
       leaf client-option-type {
         type string;
         description "Type option 60 or option 82";
       }
       leaf client-option-len {
         type int32;
         description "Number of bytes in client option 60 / option 82 data";
       }
       leaf client-option-data {
         type string;
         description "Hex dump of client option 60 / option 82 data";
       }
       leaf option-82-length-from-client {
         type int32;
         description "Option 82 length from client";
       }
       leaf option-82-data-from-client {
         type string;
         description "Option 82 data from client";
       }
       leaf hardware-type {
         type string;
         description "Client hardware type";
       }
       leaf logical-system-routing-instance {
         type string;
         description "Client router context logical system and routing instance";
       }
       leaf bridge-domain {
         type string;
         description "Client router context bridge domain";
       }
     }
   }
   grouping dhcp-client-statistics-information-block {
     leaf dropped-packet-total {
       type uint32;
       description "Total packet discard count for the DHCP interface";
     }
     leaf dropped-packet-bad-hardware {
       type uint32;
       description "Packets discarded due to invalid hardware address";
     }
     leaf dropped-packet-bad-bootp-opcode {
       type uint32;
       description "Packets discarded due to invalid operation code in bootp";
     }
     leaf dropped-packet-bad-options {
       type uint32;
       description "Packets discarded due to invalid option";
     }
     leaf dropped-packet-invalid-server-address {
       type uint32;
       description "Packets discarded due to invalid server address";
     }
     leaf dropped-packet-no-addresses {
       type uint32;
       description "Packets discarded due to no addresses available";
     }
     leaf dropped-packet-no-interface-cfg {
       type uint32;
       description "Packets discarded due to unconfigured interface";
     }
     leaf dropped-packet-no-routing-instance {
       type uint32;
       description "Number of packets discarded by the DHCP client because of a routing-instance mismatch";
     }
     leaf dropped-packet-no-local-address {
       type uint32;
       description "Packets discarded due to invalid local address";
     }
     leaf dropped-packet-too-short {
       type uint32;
       description "Packets discarded due to runt packets";
     }
     leaf dropped-packet-read-error {
       type uint32;
       description "Number of packets discarded by the DHCP client because of a read error";
     }
     leaf dropped-packet-send-error {
       type uint32;
       description "Packets discarded due to transmit error";
     }
     leaf dropped-packet-authentication {
       type uint32;
       description "Packets discarded due to authentication failure";
     }
     leaf dropped-packet-dynamic-profile {
       type uint32;
       description "Packets discarded due to dynamic profile failure";
     }
     leaf dropped-packet-license {
       type uint32;
       description "Packets discarded due to license failure";
     }
     leaf dropped-packet-bad-dhcp-opcode {
       type uint32;
       description "Packets discarded due to bad DHCP opcode";
     }
     leaf dropped-packet-no-options {
       type uint32;
       description "Packets discarded due to no DHCP options";
     }
     leaf forwarded-packets-total {
       type uint32;
       description "Total number of packets forwarded";
     }
     leaf forwarded-bootrequest-packets {
       type uint32;
       description "Number of bootrequest packets forwarded";
     }
     leaf forwarded-bootreply-packets {
       type uint32;
       description "Number of bootreply packets forwarded";
     }
     list message-table {
       description "Packet counts for DHCP messages sent or received by the dhcp client";
       leaf message-direction {
         type string;
         description "Indicates send or receive operation";
       }
       list message {
         description "Information about a DHCP or BOOTP message";
         leaf message-name {
           type string;
           description "Name of the message";
         }
         leaf message-count {
           type uint32;
           description "Number of times the DHCP client received or sent the message";
         }
       }
     }
     leaf dropped-client-packet-total {
       type uint32;
       description "Total number of packets discarded by the DHCP client because of errors";
     }
     leaf dropped-client-packet-invalid-server-address {
       type uint32;
       description "Number of packets discarded by the DHCP client because they specified an invalid server address";
     }
     leaf dropped-client-packet-too-short {
       type uint32;
       description "Number of packets discarded by the DHCP client because they were too short";
     }
     leaf dropped-client-packet-read-error {
       type uint32;
       description "Number of packets discarded by the DHCP client because of a read error";
     }
     leaf dropped-client-packet-send-error {
       type uint32;
       description "Number of packets that the DHCP client could not send";
     }
     list message-client-table {
       description "Information about one or more DHCP or bootstrap protocol (BOOTP) messages sent or received by the DHCP client";
       leaf message-client-direction {
         type string;
         description "Indicator of whether the DHCP client sent or received the messages";
       }
       list message-client {
         description "Information about a DHCP or BOOTP message";
         leaf message-client-name {
           type string;
           description "Name of the message";
         }
         leaf message-client-count {
           type uint32;
           description "Number of times the DCHP client received or sent the message";
         }
       }
     }
   }
   grouping dhcp-proxy-client-statistics-information-block {
     container dhcp-client-statistics-information {
       description "Statistics from the Dynamic Host Configuration Protocol Client";
       leaf dropped-packet-total {
         type uint32;
         description "Total packet discard count for the DHCP interface";
       }
       leaf dropped-packet-bad-hardware {
         type uint32;
         description "Packets discarded due to invalid hardware address";
       }
       leaf dropped-packet-bad-bootp-opcode {
         type uint32;
         description "Packets discarded due to invalid operation code in bootp";
       }
       leaf dropped-packet-bad-options {
         type uint32;
         description "Packets discarded due to invalid option";
       }
       leaf dropped-packet-invalid-server-address {
         type uint32;
         description "Packets discarded due to invalid server address";
       }
       leaf dropped-packet-no-addresses {
         type uint32;
         description "Packets discarded due to no addresses available";
       }
       leaf dropped-packet-no-interface-cfg {
         type uint32;
         description "Packets discarded due to unconfigured interface";
       }
       leaf dropped-packet-no-routing-instance {
         type uint32;
         description "Number of packets discarded by the DHCP client because of a routing-instance mismatch";
       }
       leaf dropped-packet-no-local-address {
         type uint32;
         description "Packets discarded due to invalid local address";
       }
       leaf dropped-packet-too-short {
         type uint32;
         description "Packets discarded due to runt packets";
       }
       leaf dropped-packet-read-error {
         type uint32;
         description "Number of packets discarded by the DHCP client because of a read error";
       }
       leaf dropped-packet-send-error {
         type uint32;
         description "Packets discarded due to transmit error";
       }
       leaf dropped-packet-authentication {
         type uint32;
         description "Packets discarded due to authentication failure";
       }
       leaf dropped-packet-dynamic-profile {
         type uint32;
         description "Packets discarded due to dynamic profile failure";
       }
       leaf dropped-packet-license {
         type uint32;
         description "Packets discarded due to license failure";
       }
       leaf dropped-packet-bad-dhcp-opcode {
         type uint32;
         description "Packets discarded due to bad DHCP opcode";
       }
       leaf dropped-packet-no-options {
         type uint32;
         description "Packets discarded due to no DHCP options";
       }
       leaf forwarded-packets-total {
         type uint32;
         description "Total number of packets forwarded";
       }
       leaf forwarded-bootrequest-packets {
         type uint32;
         description "Number of bootrequest packets forwarded";
       }
       leaf forwarded-bootreply-packets {
         type uint32;
         description "Number of bootreply packets forwarded";
       }
       list message-table {
         description "Packet counts for DHCP messages sent or received by the dhcp client";
         leaf message-direction {
           type string;
           description "Indicates send or receive operation";
         }
         list message {
           description "Information about a DHCP or BOOTP message";
           leaf message-name {
             type string;
             description "Name of the message";
           }
           leaf message-count {
             type uint32;
             description "Number of times the DHCP client received or sent the message";
           }
         }
       }
     }
   }
   grouping dhcp-proxy-client-profile-servers-information-block {
     list servers {
       description "Information about confiuration parameters";
       leaf server-ip-address {
         type jt:ipaddr;
         description "IP address of the DHCP server";
       }
       leaf server-priority {
         type uint32;
         description "Priority of the DHCP server";
       }
       leaf server-status {
         type string;
         description "Status of the DHCP server";
       }
       leaf server-dead-timer {
         type string;
         description "Dead timer of the DHCP server";
       }
       leaf server-retry-count {
         type uint32;
         description "Retry count of the DHCP server";
       }
     }
   }
 }
