/*
 * Copyright (c) 2024 Juniper Networks, Inc.
 * All rights reserved.
 */
 module junos-nfx-rpc-services {
   namespace "http://yang.juniper.net/junos-nfx/rpc/services";

   prefix services;

   import junos-common-types {
     prefix jt;
     revision-date 2024-01-01;
   }

   organization "Juniper Networks, Inc.";

   contact "yang-support@juniper.net";

   description "Junos RPC YANG module for services command(s)";

   revision 2024-01-01 {
     description "Junos: 24.2R1.17";
   }

   rpc get-fwa-statistics {
     description "Show fixed wireless access statistics";
     output {
       container fwa-statistics {
         uses fwa-statistics-block;
       }
     }
   }
   rpc get-pcef-subscribers {
     description "Show subscriber information";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
   }
   rpc get-pcef-subscribers-summary {
     description "Display pcef subscriber summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
   }
   rpc get-pcef-pic {
     description "Show physical interface card information";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         default "terse";
         type enumeration {
           enum "terse" {
             description "Display terse output";
           }
         }
       }
     }
   }
   rpc get-uac-debug-counters {
     description "Show uac debug counters";
     input {
       uses command-forwarding;
     }
     output {
       container uac-debug-counters {
         uses uac-debug-counters-block;
       }
     }
   }
   rpc get-uac-policies {
     description "Access policies from infranet controller";
     input {
       uses command-forwarding;
       leaf detail {
         description "Display detail output";
         type empty;
       }
       leaf identifier {
         description "Show specified policy information";
         type string;
       }
     }
   }
   rpc get-uac-auth-table {
     description "Show authentication table configured from infranet controller";
     input {
       uses command-forwarding;
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
   }
   rpc get-uac-status {
     description "Show connection status with infranet controller";
     input {
       uses command-forwarding;
     }
   }
   rpc get-uac-role-entries {
     description "Show list of available roles";
     input {
       uses command-forwarding;
     }
   }
   rpc get-uac-counters {
     description "Show unified access control(uac) service related counters";
     input {
       uses command-forwarding;
     }
     output {
       container uac-counters {
         uses uac-counters-block;
       }
     }
   }
   rpc get-ift-global-information {
     description "Show inband telemetry information";
     output {
       container ift-global-information {
         uses ift-global-information-block;
       }
     }
   }
   rpc get-ift-profile-information {
     description "Show inband telemetry profile details";
     input {
       leaf profile-name {
         description "Name of the profile";
         type string;
       }
     }
     output {
       container ift-profile-information {
         uses ift-profile-information-block;
       }
     }
   }
   rpc get-ift-stats-information {
     description "Show inband telemetry stats information";
     output {
       container ift-stats-information {
         uses ift-stats-information-block;
       }
     }
   }
   rpc get-services-flow-collector-information {
     description "Show flow collector service information";
     input {
       leaf display {
         default "terse";
         type enumeration {
           enum "extensive" {
             description "Display extensive output";
           }
           enum "detail" {
             description "Display detailed output";
           }
           enum "terse" {
             description "Display terse output (default)";
           }
         }
       }
       leaf interface {
         description "Interface name";
         type string;
         mandatory true;
       }
     }
     output {
       container services-flow-collector-information {
         uses services-flow-collector-information-block;
       }
     }
   }
   rpc get-services-flow-collector-file-information {
     description "Show file status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
   }
   rpc get-services-flow-collector-input-information {
     description "Show input status information";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
   }
   rpc get-cpcd-pic-statistics {
     description "Show captive portal and content delivery statistics by PIC";
     input {
       leaf pic-name {
         type union {
           type jt:interface-name;
           type string {
             pattern "<.*>|$.*";
           }
         }
         mandatory true;
       }
     }
     output {
       container cpcd-pic-statistics {
         uses cpcd-pic-statistics-block;
       }
     }
   }
   rpc get-cpcd-profile {
     description "Show profile database";
     input {
       leaf profile-name {
         type string;
       }
     }
     output {
       container cpcd-profile {
         uses cpcd-profile-block;
       }
     }
   }
   rpc get-cpcd-rule {
     description "Show rule database";
     input {
       leaf rule-name {
         type string;
       }
       leaf term {
         description "Term name";
         type string;
       }
     }
     output {
       container cpcd-rule {
         uses cpcd-rule-block;
       }
     }
   }
   rpc get-cpcd-rule-set {
     description "Show rule set database";
     input {
       leaf ruleset-name {
         type string;
       }
     }
   }
   rpc get-cpcd-pic-information {
     description "Show pic database";
     input {
       leaf pic-name {
         type union {
           type jt:interface-name;
           type string {
             pattern "<.*>|$.*";
           }
         }
       }
     }
     output {
       container cpcd-pic-information {
         uses cpcd-pic-information-block;
       }
     }
   }
   rpc get-cpcd-service-set {
     description "Show service set database";
     input {
       leaf sset-name {
         type string;
         mandatory true;
       }
       leaf level {
         default "brief";
         type enumeration {
           enum "brief" {
             description "Display brief output (default)";
           }
           enum "detail" {
             description "Display detailed output";
           }
           enum "summary" {
             description "Display summary output";
           }
         }
       }
     }
   }
   rpc get-services-dfc-statistics-information {
     description "Show capture group statistics";
     input {
       leaf capture-group {
         description "Capture group name";
         type string;
         mandatory true;
       }
       leaf per-protocol-details {
         description "Shows ipv4 ipv6 also";
         type empty;
       }
     }
   }
   rpc get-services-dynamic-flow-capture-control-source-information {
     description "Show DFC control source information";
     input {
       leaf display {
         default "terse";
         type enumeration {
           enum "detail" {
             description "Display detailed output";
           }
           enum "terse" {
             description "Display terse output (default)";
           }
         }
       }
       leaf capture-group {
         description "Capture group name";
         type string;
         mandatory true;
       }
       leaf source-identifier {
         description "Control source identifier";
         type string;
         mandatory true;
       }
       leaf per-protocol-details {
         description "Shows ipv4 ipv6 also";
         type empty;
       }
     }
   }
   rpc get-services-dynamic-flow-capture-content-destination-information {
     description "Show DFC content destination information";
     input {
       leaf display {
         default "terse";
         type enumeration {
           enum "terse" {
             description "Display terse output (default)";
           }
         }
       }
       leaf capture-group {
         description "Capture group name";
         type string;
         mandatory true;
       }
       leaf destination-identifier {
         description "Content destination identifier";
         type string;
         mandatory true;
       }
     }
   }
   rpc get-dynamic-filtering-statistics {
     description "Show Cloud Connection Status";
     input {
       uses command-forwarding;
     }
     output {
       container dynamic-filtering-connection-status {
         uses dynamic-filtering-connection-status-block;
       }
     }
   }
   rpc get-aamw-statistics {
     description "Show advanced-anti-malware statistics";
     input {
       uses command-forwarding;
     }
     output {
       container aamw-statistics {
         uses aamw-statistics-block;
       }
     }
   }
   rpc get-aamw-redirect-files {
     description "Show redirect files information";
     input {
       uses command-forwarding;
       leaf file-name {
         description "Show redirect-file content";
         type string;
       }
     }
     output {
       container aamw-redirect-files {
         uses aamw-redirect-files-block;
       }
     }
   }
   rpc get-aamw-policy {
     description "Show advanced-anti-malware policy";
     input {
       uses command-forwarding;
       leaf policy-name {
         description "Policy name";
         type string;
       }
     }
     output {
       container aamw-policy {
         uses aamw-policy-block;
       }
     }
   }
   rpc get-aamw-profile {
     description "Show advanced-anti-malware profile";
     input {
       uses command-forwarding;
       leaf profile-name {
         description "Profile name";
         type string;
       }
     }
     output {
       container aamw-profile {
         uses aamw-profile-block;
       }
     }
   }
   rpc get-aamw-status {
     description "Show advanced-anti-malware status";
     input {
       uses command-forwarding;
     }
     output {
       container aamw-status {
         uses aamw-status-block;
       }
     }
   }
   rpc get-aamw-version {
     description "Show advanced-anti-malware version";
     input {
       uses command-forwarding;
     }
     output {
       container aamw-version {
         uses aamw-version-block;
       }
     }
   }
   rpc get-aamw-session-summary {
     description "Show advanced-anti-malware session summary";
     status deprecated;
     input {
       uses command-forwarding;
     }
   }
   rpc get-aamw-db-statistics {
     description "Show advanced-anti-malware database-statistics";
     input {
       uses command-forwarding;
     }
   }
   rpc get-appid-application-signature-detail {
     description "Show application signature details";
     input {
       uses command-forwarding;
       leaf application-name {
         type string;
       }
       leaf start {
         description "Show application details from a given position";
         type union {
           type string {
             pattern "<.*>|$.*";
           }
           type uint32 {
             range "1 .. 65535";
           }
         }
       }
       leaf count {
         description "Number of applications to show";
         type union {
           type string {
             pattern "<.*>|$.*";
           }
           type uint32 {
             range "1 .. 65535";
           }
         }
       }
     }
   }
   rpc get-appid-application-signature-summary {
     description "Show application signature summary";
     input {
       uses command-forwarding;
     }
   }
   rpc get-appid-micro-applications-list {
     description "Show micro-applications list";
     input {
       uses command-forwarding;
     }
   }
   rpc get-appid-non-configurable-application-list {
     description "Show non-configurable application list";
     input {
       uses command-forwarding;
     }
   }
   rpc get-appid-obsolete-application-list {
     description "Show obsolete application list";
     input {
       uses command-forwarding;
     }
   }
   rpc get-appid-entry-signature-detail {
     description "Show application/group signature details";
     input {
       leaf entry-name {
         type string;
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
   }
   rpc get-appid-entry-signature-filter {
     description "Apply filter on entry details";
     input {
       leaf category {
         description "Filter by entry category";
         type string;
       }
       leaf definition {
         description "Filter by predefined/custom entry";
         type enumeration {
           enum "predefined" {
             description "Predefined app";
           }
           enum "custom" {
             description "Customer defined app";
           }
         }
       }
       leaf entry-name {
         description "Filter by entry name";
         type string;
       }
       leaf risk {
         description "Filter by entry risk";
         type union {
           type string {
             pattern "<.*>|$.*";
           }
           type uint32 {
             range "1 .. 5";
           }
         }
       }
       leaf subcategory {
         description "Filter by entry subcategory";
         type string;
       }
       leaf status {
         description "Filter by entry enabled/disabled";
         type enumeration {
           enum "enabled" {
             description "Application is enabled";
           }
           enum "disabled" {
             description "Application is disabled";
           }
         }
       }
       leaf type {
         description "Filter by application/group entry";
         type enumeration {
           enum "application" {
             description "Application";
           }
           enum "group" {
             description "Group";
           }
         }
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
   }
   rpc get-appid-entry-category-detail {
     description "List of categories of application available";
   }
   rpc get-appid-entry-subcategory-detail {
     description "List of subcategories of application available";
   }
   rpc get-appid-application-group-detail {
     description "Show application group details";
     input {
       uses command-forwarding;
       leaf group-name {
         type string;
       }
     }
   }
   rpc get-appid-application-group-summary {
     description "Show application group summary";
     input {
       uses command-forwarding;
     }
   }
   rpc get-appid-application-system-cache {
     description "Show application system cache";
     input {
       uses command-forwarding;
       choice lsys {
         case logical-system {
         }
         case tenant {
         }
       }
       leaf interface {
         description "Services interface to query";
         type string;
       }
     }
     output {
       container appid-application-system-cache-information {
         uses appid-application-system-cache-information-block;
       }
     }
   }
   rpc get-appid-counter {
     description "Show the application identification counters";
     input {
       uses command-forwarding;
       choice lsys {
         case logical-system {
         }
         case tenant {
         }
       }
       leaf interface {
         description "Services interface to query";
         type string;
       }
     }
     output {
       container appid-counter-information {
         uses appid-counter-information-block;
       }
     }
   }
   rpc get-appid-counter-encrypted {
     description "Counters for SSL encrypted sessions";
     status deprecated;
     input {
       uses command-forwarding;
     }
     output {
       container appid-counter-information {
         uses appid-counter-information-block;
       }
     }
   }
   rpc get-commit-status {
     description "Show config commit status";
     input {
       uses command-forwarding;
     }
     output {
       container appid-commit-status {
         uses appid-commit-status-block;
       }
     }
   }
   rpc get-appid-application-statistics {
     description "Show the application statistics";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
     output {
       container appid-application-statistics-information {
         uses appid-application-statistics-information-block;
       }
     }
   }
   rpc get-appid-application-statistics-detail {
     description "Show the application statistics detail";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
   }
   rpc get-appid-application-group-statistics {
     description "Show the application group statistics";
     input {
       uses command-forwarding;
       choice lsys {
         case logical-system {
         }
         case tenant {
         }
       }
       leaf interval {
         description "Displays current interval application group statistics irrespective of interval";
         default "1";
         type union {
           type string {
             pattern "<.*>|$.*";
           }
           type uint32 {
             range 1;
           }
         }
       }
     }
     output {
       container appid-application-group-statistics-information {
         uses appid-application-group-statistics-information-block;
       }
     }
   }
   rpc get-application-id-status-information {
     description "Show the application identification status";
     input {
       uses command-forwarding;
     }
     output {
       container appid-status-information {
         uses appid-status-information-block;
       }
     }
   }
   rpc get-appid-package-version {
     description "Show the current application package version";
     input {
       uses command-forwarding;
       leaf detail {
         description "Detail status of sigpack & failed sigpack version";
         type empty;
       }
     }
     output {
       container appid-package-version {
         uses appid-package-version-block;
       }
     }
   }
   rpc get-appid-pkt-capture-counter {
     description "Show the application identification packet capture counters";
     input {
       uses command-forwarding;
     }
     output {
       container appid-pkt-capture-counter-information {
         uses appid-pkt-capture-counter-information-block;
       }
     }
   }
   rpc get-recent-appid-sigpack-information {
     description "Show the recent application package versions";
     input {
       uses command-forwarding;
     }
     output {
       container recent-appid-sigpack-information {
         uses recent-appid-sigpack-information-block;
       }
     }
   }
   rpc get-ssl-statistics {
     description "Show ssl proxy statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-statistics {
         uses ssl-statistics-block;
       }
     }
   }
   rpc get-ssl-status {
     description "Show ssl proxy status";
     input {
       uses command-forwarding;
       leaf pic-info {
         description "PIC ID";
         type string;
       }
     }
     output {
       container ssl-status {
         uses ssl-status-block;
       }
     }
   }
   rpc get-ssl-counters {
     description "Show all ssl proxy counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-ssl-error-counters {
     description "Show ssl proxy error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-ssl-info-counters {
     description "Show ssl proxy info counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-ssl-proxy-profile-all {
     description "Show all ssl proxy profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-profile-list {
         uses ssl-profile-list-block;
       }
     }
   }
   rpc get-ssl-proxy-profile-detail {
     description "Show profile information matching the given profile name";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf profile-name {
         description "Ssl proxy profile name";
         type string;
         mandatory true;
       }
     }
     output {
       container ssl-profile-detail {
         uses ssl-profile-detail-block;
       }
     }
   }
   rpc get-ssl-proxy-session-cache-entries-summary {
     description "Show summary of session cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-sess-cache-entries {
         uses ssl-proxy-sess-cache-entries-block;
       }
     }
   }
   rpc get-ssl-proxy-session-cache-entries-detail {
     description "Show detailed output of session cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-sess-cache-entries {
         uses ssl-proxy-sess-cache-entries-block;
       }
     }
   }
   rpc get-ssl-proxy-session-cache-statistics {
     description "Show session cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-sess-cache-statistics {
         uses ssl-proxy-sess-cache-statistics-block;
       }
     }
   }
   rpc get-ssl-proxy-certificate-cache-entries-summary {
     description "Show summary of certificate cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-cert-cache-entries {
         uses ssl-proxy-cert-cache-entries-block;
       }
     }
   }
   rpc get-ssl-proxy-certificate-cache-entries-detail {
     description "Show detailed output of certificate cache entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-cert-cache-entries {
         uses ssl-proxy-cert-cache-entries-block;
       }
     }
   }
   rpc get-ssl-proxy-cert-cache-statistics {
     description "Show certificate cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-proxy-cert-cache-statistics {
         uses ssl-proxy-cert-cache-statistics-block;
       }
     }
   }
   rpc get-ssl-certificate-all {
     description "Show all ssl certificates";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-certificate {
         uses ssl-certificate-block;
       }
     }
   }
   rpc get-ssl-certificate-id-brief {
     description "Show brief information about certificate id";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       container ssl-certificate-id-detail {
         uses ssl-certificate-id-detail-block;
       }
     }
   }
   rpc get-ssl-certificate-id-detail {
     description "Show detail information about certificate id";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       container ssl-certificate-id-detail {
         uses ssl-certificate-id-detail-block;
       }
     }
   }
   rpc get-terminator-counters {
     description "Show all ssl terminator counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-terminator-error-counters {
     description "Show ssl terminator error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-terminator-handshake-counters {
     description "Show ssl terminator handshake counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-ssl-terminator-profile-all {
     description "Show all ssl terminator profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-profile-list {
         uses ssl-profile-list-block;
       }
     }
   }
   rpc get-ssl-terminator-profile-brief {
     description "Terminator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       container ssl-term-profile-detail {
         uses ssl-term-profile-detail-block;
       }
     }
   }
   rpc get-ssl-terminator-profile-detail {
     description "Terminator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       container ssl-term-profile-detail {
         uses ssl-term-profile-detail-block;
       }
     }
   }
   rpc get-initiator-counters {
     description "Show all ssl initiator counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-initiator-error-counters {
     description "Show ssl initiator error counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-initiator-handshake-counters {
     description "Show ssl initiator handshake counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-counters {
         uses ssl-counters-block;
       }
     }
   }
   rpc get-ssl-initiator-profile-all {
     description "Show all ssl initiator profiles";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-profile-list {
         uses ssl-profile-list-block;
       }
     }
   }
   rpc get-ssl-initiator-profile-brief {
     description "Initiator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       container ssl-term-profile-detail {
         uses ssl-term-profile-detail-block;
       }
     }
   }
   rpc get-ssl-initiator-profile-detail {
     description "Initiator profile name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       container ssl-term-profile-detail {
         uses ssl-term-profile-detail-block;
       }
     }
   }
   rpc get-ssl-session {
     description "Show ssl session details";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf flow_session_id {
         description "Flow session id";
         type string;
         mandatory true;
       }
     }
     output {
       container ssl-session {
         uses ssl-session-block;
       }
     }
   }
   rpc get-ssl-droplogs {
     description "Show ssl droplogs";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       container ssl-droplog {
         uses ssl-droplog-block;
       }
     }
   }
   rpc get-icap-redir-statistics {
     description "Show ICAP redirect service statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container icap-redir-statistics {
         uses icap-redir-statistics-block;
       }
     }
   }
   rpc get-icap-redir-status {
     description "Show ICAP redirect profile status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container icap-redir-status {
         uses icap-redir-status-block;
       }
     }
   }
   rpc get-services-screen-ids-whitelist {
     description "Show white list data";
     input {
       uses command-forwarding;
       leaf wlist-name {
         description "White list name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container show-ids-whitelist {
         uses show-ids-whitelist-block;
       }
     }
   }
   rpc get-services-screen-ids-status {
     description "Show status of screen object";
     input {
       uses command-forwarding;
       leaf screen-name {
         description "Screen name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container show-ids-status {
         uses show-ids-status-block;
       }
     }
   }
   rpc get-services-ids-statistics {
     description "Show screen attack statistics information";
     input {
       uses command-forwarding;
       choice filter {
         case service-set {
           leaf service-set {
             description "IDS statistics service-set";
             type string;
           }
         }
         case interface {
           leaf interface {
             description "IDS statistics interface";
             type string;
           }
         }
       }
       leaf ip {
         description "IDS statistics ip";
         type enumeration {
           enum "tunnel" {
             description "IDS statistics ip tunnel";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-screen-drops {
     description "Show screen ids packet drop statistics";
     input {
       uses command-forwarding;
       choice filter {
         case service-set {
           leaf service-set {
             description "IDS statistics service-set";
             type string;
           }
         }
         case interface {
           leaf interface {
             description "IDS statistics interface";
             type string;
           }
         }
       }
     }
   }
   rpc get-screen-session-limit-counters {
     description "Show service set screen session limit counters";
     input {
       uses command-forwarding;
       choice filter {
         case service-set {
           leaf service-set {
             description "IDS statistics service-set";
             type string;
           }
         }
         case interface {
           leaf interface {
             description "IDS statistics interface";
             type string;
           }
         }
       }
     }
   }
   rpc get-service-set-packet-drop-statistics {
     description "Show service set packet drop statistics";
     input {
       leaf interface {
         description "Name of adaptive services interface";
         type string;
       }
     }
     output {
       container service-set-packet-drop-statistics {
         uses service-set-packet-drop-statistics-block;
       }
     }
   }
   rpc get-service-set-drop-flow-statistics {
     description "Show drop flow stats";
     input {
       leaf interface {
         description "Name of adaptive services interface";
         type string;
       }
     }
     output {
       container service-set-drop-flow-statistics {
         uses service-set-drop-flow-statistics-block;
       }
     }
   }
   rpc get-service-set-integrity-drops-statistics {
     description "Show header integrity drops";
     input {
       leaf service-set {
         description "Name of service set";
         type string;
       }
       leaf interface {
         description "Name of adaptive services interface";
         type string;
       }
     }
     output {
       container service-set-integrity-drops-statistics {
         uses service-set-integrity-drops-statistics-block;
       }
     }
   }
   rpc get-service-set-tcp-tracker-statistics {
     description "Show tcp tracker statistics";
     input {
       leaf service-set {
         description "Name of service set";
         type string;
       }
       leaf interface {
         description "Name of adaptive services interface";
         type string;
       }
     }
     output {
       container msp-service-set-tcp-statistics {
         uses msp-service-set-tcp-statistics-block;
       }
     }
   }
   rpc get-service-set-tcp-mss-statistics {
     description "Show service set TCP MSS statistics";
     input {
       leaf interface {
         description "Name of adaptive services interface";
         type string;
       }
     }
     output {
       container service-set-tcp-mss-statistics {
         uses service-set-tcp-mss-statistics-block;
       }
     }
   }
   rpc get-service-set-syslog-statistics {
     description "Show service set syslog statistics";
     input {
       leaf host {
         description "Syslog host address";
         type string;
       }
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       container syslog-stats-interface {
         uses syslog-stats-interface-block;
       }
     }
   }
   rpc get-service-set-jflow-log-statistics {
     description "Show service set jflow-log statistics";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       container jflow-log-stats-interface {
         uses jflow-log-stats-interface-block;
       }
     }
   }
   rpc get-service-set-ids-drops-statistics {
     description "Show service set IDS drops statistics";
     input {
       leaf service-set {
         description "Name of service set";
         type string;
       }
       leaf interface {
         description "Name of adaptive services interface";
         type string;
       }
     }
   }
   rpc get-ids-session-limits-counters-statistics {
     description "Show the session-limits counters";
     input {
       leaf service-set {
         description "Name of service set";
         type string;
       }
       leaf interface {
         description "Name of adaptive services interface";
         type string;
       }
     }
   }
   rpc get-service-set-log-profile-template {
     description "Show service-set log profile template info";
     input {
       leaf template-name {
         description "Specify the rtlog profile template name";
         type enumeration {
           enum "traditional-firewall" {
             description "Template traditional-firewall";
           }
         }
         mandatory true;
       }
     }
     output {
       container security-log-profile-template {
         uses security-log-profile-template-block;
       }
     }
   }
   rpc get-service-set-log-profile_sset {
     description "Show configured log profile ";
     input {
       leaf service-set {
         description "Specify service set name";
         type string {
           length "1 .. 64";
         }
         mandatory true;
       }
     }
     output {
       container security-log-profile-config {
         uses security-log-profile-config-block;
       }
     }
   }
   rpc get-service-set-memory-statistics {
     description "Show service interface memory utilization";
     input {
       leaf service-set {
         description "Name of service set";
         type string;
       }
       leaf interface {
         description "Name of adaptive services interface";
         type string;
       }
     }
     output {
       container service-set-memory-statistics-information {
         uses service-set-memory-statistics-information-block;
       }
     }
   }
   rpc get-service-set-cpu-statistics {
     description "Show service interface CPU utilization as a percentage";
     input {
       leaf service-set {
         description "Name of service set";
         type string;
       }
       leaf interface {
         description "Name of adaptive services interface";
         type string;
       }
     }
     output {
       container service-set-cpu-statistics-information {
         uses service-set-cpu-statistics-information-block;
       }
     }
   }
   rpc get-service-set-summary-information {
     description "Show service set summary information";
     input {
       leaf interface {
         description "Name of adaptive services interface";
         type string;
       }
     }
     output {
       container service-set-summary-information {
         uses service-set-summary-information-block;
       }
     }
   }
   rpc get-service-set-plugin-summary {
     description "Show service set plugins summary";
     input {
       leaf interface {
         description "Name of extension provider interface";
         type string;
       }
     }
     output {
       container service-set-plugin-summary {
         uses service-set-plugin-summary-block;
       }
     }
   }
   rpc retrieve-srv-source-nat-pool-information {
     description "Show source NAT information of this pool";
     input {
       uses command-forwarding;
       choice pool-choice {
         case pool-name {
           leaf pool-name {
             description "Source address pool name";
             type string;
             mandatory true;
           }
         }
         case all {
           leaf all {
             description "Display all source NAT pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-pool-information {
         uses source-nat-pool-information-block;
       }
     }
   }
   rpc get-serv-src-nat-port-block {
     description "Show port block allocation information";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-serv-det-nat {
     description "Show deterministic port block allocation information";
     input {
       uses command-forwarding;
       leaf interface {
         description "Name of adaptive services interface";
         type string;
       }
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-serv-det-nat-host-sddr-range {
     description "Show deterministic host address range without overlap";
     input {
       uses command-forwarding;
       leaf pool {
         description "Source NAT pool name";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-srv-source-nat-rule-sets-information {
     description "Show source NAT rule-set information";
     input {
       uses command-forwarding;
       choice rule-choice {
         case rule-name {
           leaf rule-name {
             description "Source NAT rule name";
             type string {
               length "1 .. 64";
             }
             mandatory true;
           }
         }
         case all {
           leaf all {
             description "Display all source NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
   }
   rpc get-srv-source-nat-rule-app-information {
     description "Show source NAT rule application information";
     input {
       uses command-forwarding;
       choice rule-choice {
         case rule-name {
           leaf rule-name {
             description "Source NAT rule name";
             type string {
               length "1 .. 64";
             }
             mandatory true;
           }
         }
         case all {
           leaf all {
             description "Display all source NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-rule-application-information {
         uses source-nat-rule-application-information-block;
       }
     }
   }
   rpc retrieve-srv-source-nat-summary {
     description "Show source NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-summary {
         uses source-nat-summary-block;
       }
     }
   }
   rpc get-nat-endpoint-independent-mapping {
     description "Show NAT Endpoint Independent mapping";
     input {
       uses command-forwarding;
       leaf private {
         description "Private IP/IPv6 prefix to use as filter";
         type string;
       }
       leaf public {
         description "Public IP prefix to use as filter";
         type string;
       }
       leaf pool-name {
         description "Name of pool";
         type string;
       }
     }
   }
   rpc get-nat-app-mapping {
     description "Show NAT address pooling paired mapping";
     input {
       uses command-forwarding;
       leaf private {
         description "Private IP/IPv6 prefix to use as filter";
         type string;
       }
       leaf public {
         description "Public IP prefix to use as filter";
         type string;
       }
       leaf pool-name {
         description "Name of pool";
         type string;
       }
     }
   }
   rpc get-nat-mapping-pcp {
     description "Show NAT PCP mapping";
     input {
       uses command-forwarding;
     }
   }
   rpc get-nat-mapping {
     description "Show NAT mapping";
     input {
       uses command-forwarding;
       leaf pool-name {
         description "Name of pool";
         type string;
       }
     }
   }
   rpc get-nat-mapping-summary {
     description "Show NAT mapping entries count";
     input {
       uses command-forwarding;
     }
   }
   rpc get-srv-dst-nat-pool-information {
     description "Show destination NAT address-pool information";
     input {
       uses command-forwarding;
       choice pool-choice {
         case pool-name {
           leaf pool-name {
             description "Destination address pool name";
             type string {
               length "1 .. 64";
             }
             mandatory true;
           }
         }
         case all {
           leaf all {
             description "Display all destination NAT address-pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-pool-information {
         uses destination-nat-pool-information-block;
       }
     }
   }
   rpc get-srv-dst-nat-rule-sets-information {
     description "Show destination NAT rule-set information";
     input {
       uses command-forwarding;
       choice rule-choice {
         case rule-name {
           leaf rule-name {
             description "Destination NAT rule name";
             type string {
               length "1 .. 64";
             }
             mandatory true;
           }
         }
         case all {
           leaf all {
             description "Display all destination NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
   }
   rpc get-srv-dst-nat-rule-app-information {
     description "Show destination NAT rule application information";
     input {
       uses command-forwarding;
       choice rule-choice {
         case rule-name {
           leaf rule-name {
             description "Destination NAT rule name";
             type string {
               length "1 .. 64";
             }
             mandatory true;
           }
         }
         case all {
           leaf all {
             description "Display all destination NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-rule-application-information {
         uses destination-nat-rule-application-information-block;
       }
     }
   }
   rpc retrieve-srv-dst-nat-summary-information {
     description "Show destination NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-summary-information {
         uses destination-nat-summary-information-block;
       }
     }
   }
   rpc retrieve-srv-source-nat-pool-resource-usage {
     description "Show source pool resource usage information";
     input {
       uses command-forwarding;
       choice pool-choice {
         case pool-name {
           leaf pool-name {
             description "Source address pool name";
             type string;
             mandatory true;
           }
         }
         case all {
           leaf all {
             description "Display all source NAT pool resource usage";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-srv-static-nat-rule-information {
     description "Show static NAT rule information";
     input {
       uses command-forwarding;
       choice rule-choice {
         case rule-name {
           leaf rule-name {
             description "Static NAT rule name";
             type string {
               length "1 .. 64";
             }
             mandatory true;
           }
         }
         case all {
           leaf all {
             description "Display all static NAT rule information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container static-nat-rule-information {
         uses static-nat-rule-information-block;
       }
     }
   }
   rpc get-service-nat-pool-information {
     description "Show NAT pools information";
     input {
       leaf pool-name {
         description "Name of pool";
         type string;
       }
       leaf display {
         default "brief";
         type enumeration {
           enum "brief" {
             description "Display brief output (default)";
           }
           enum "detail" {
             description "Display detailed output";
           }
         }
       }
     }
     output {
       container service-nat-pool-information {
         uses service-nat-pool-information-block;
       }
     }
   }
   rpc get-service-detnat-information {
     description "Show deterministic NAT internal-host information";
     input {
       leaf nat-address {
         description "NAT address";
         type string;
         mandatory true;
       }
       leaf nat-port {
         description "NAT port";
         type string;
         mandatory true;
       }
     }
     output {
       container service-detnat-information {
         uses service-detnat-information-block;
       }
     }
   }
   rpc get-service-detnat-pb-information {
     description "Show deterministic NAT port blocks assigned to internal-host";
     input {
       leaf internal-address {
         description "Subscriber IP address";
         type string;
         mandatory true;
       }
     }
     output {
       container service-detnat-information {
         uses service-detnat-information-block;
       }
     }
   }
   rpc get-service-nat-ipv6-multicast-information {
     description "Show interfaces with IPv6 multicast filter";
     output {
       container service-nat-ipv6-multicast-interfaces-information {
         uses service-nat-ipv6-multicast-interfaces-information-block;
       }
     }
   }
   rpc get-service-nat-mapping-address-pooling-paired {
     description "Show NAT Address Pooling Paired mapping";
     input {
       leaf private {
         description "Private IP/IPv6 prefix to use as filter";
         type string;
       }
       leaf public {
         description "Public IP/IPv6 prefix to use as filter";
         type string;
       }
     }
   }
   rpc get-service-nat-mapping-endpoint-independent {
     description "Show NAT Endpoint Independent mapping";
     input {
       leaf private {
         description "Private IP/IPv6 prefix to use as filter";
         type string;
       }
       leaf public {
         description "Public IP prefix to use as filter";
         type string;
       }
     }
   }
   rpc get-service-nat-mapping-pcp {
     description "Show NAT PCP mapping";
   }
   rpc get-service-nat-mapping-summary {
     description "Show NAT mapping entries count";
   }
   rpc get-service-nat-mapping-brief {
     description "Show NAT mapping brief";
     input {
       leaf pool-name {
         description "Name of pool";
         type string;
       }
     }
   }
   rpc get-service-nat-mapping-detail {
     description "Show NAT mapping detail";
     input {
       leaf pool-name {
         description "Name of pool";
         type string;
       }
     }
   }
   rpc get-service-nat-mapping-nptv6 {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
     output {
       container service-nat-mapping-nptv6-information {
         uses service-nat-mapping-nptv6-information-block;
       }
     }
   }
   rpc get-service-nat-statistics-information {
     description "Show NAT statistics";
     input {
       leaf interface {
         description "Name of extension provider interface";
         type string;
       }
     }
     output {
       container service-nat-statistics-information {
         uses service-nat-statistics-information-block;
       }
     }
   }
   rpc get-services-firewall-policies {
     description "Show services policies";
     input {
       uses command-forwarding;
       leaf policy-name {
         description "Show the policy information matching the given policy name";
         type string;
       }
       leaf detail {
         description "Show the detailed information";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
       leaf stateful-firewall-rule {
         description "Show policy info matching given stateful-firewall-rule name";
         type string;
       }
     }
   }
   rpc get-services-firewall-policies-information {
     description "Show the policy information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-services-policy-checksum-information {
     description "Show policy information checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
   }
   rpc get-services-policies-hit-count {
     description "Show the hit count of policies";
     input {
       uses command-forwarding;
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container policy-hit-count-service-router {
         uses policy-hit-count-service-router-block;
       }
     }
   }
   rpc get-security-metadata-dns-statistics {
     description "Show security metadata streaming DNS statistics";
     input {
       uses command-forwarding;
     }
     output {
       container sm-dns-statistics {
         uses sm-dns-statistics-block;
       }
     }
   }
   rpc get-security-metadata-statistics {
     description "Show security metadata streaming HTTP statistics";
     input {
       uses command-forwarding;
     }
   }
   rpc get-security-metadata-streaming-whitelist {
     description "Show security metadata streaming HTTP whitelist";
     input {
       uses command-forwarding;
     }
     output {
       container security-dynamic-address {
         uses security-dynamic-address-block;
       }
     }
   }
   rpc get-av-policy {
     description "Show anti-virus policy";
     input {
       uses command-forwarding;
       leaf policy-name {
         description "Policy name";
         type string;
       }
     }
     output {
       container av-policy {
         uses av-policy-block;
       }
     }
   }
   rpc get-av-statistics {
     description "Show anti-virus statistic";
     input {
       uses command-forwarding;
     }
     output {
       container av-statistics {
         uses av-statistics-block;
       }
     }
   }
   rpc get-av-ml-statistics {
     description "Show anti-virus machine learning scan statistics";
     input {
       uses command-forwarding;
     }
     output {
       container av-ml-statistics {
         uses av-ml-statistics-block;
       }
     }
   }
   rpc get-user-group-all-debug-counters {
     description "Show debug counters";
     output {
       container user-group-debug-counters {
         uses user-group-debug-counters-block;
       }
     }
   }
   rpc get-user-group-ager-debug-counters {
     output {
       container user-group-debug-counters {
         uses user-group-debug-counters-block;
       }
     }
   }
   rpc get-user-group-batch-query-debug-counters {
     output {
       container user-group-debug-counters {
         uses user-group-debug-counters-block;
       }
     }
   }
   rpc get-user-group-ip-query-debug-counters {
     output {
       container user-group-debug-counters {
         uses user-group-debug-counters-block;
       }
     }
   }
   rpc get-user-group-message-exchange-debug-counters {
     output {
       container user-group-debug-counters {
         uses user-group-debug-counters-block;
       }
     }
   }
   rpc get-user-group-general-debug-counters {
     output {
       container user-group-debug-counters {
         uses user-group-debug-counters-block;
       }
     }
   }
   rpc get-authentication-table-counter {
     description "Show authentication table entry internal counter";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-counter {
         uses authentication-table-counter-block;
       }
     }
   }
   rpc get-authentication-table-by-address {
     description "Show authentication table entry by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-by-address {
         uses authentication-table-by-address-block;
       }
     }
   }
   rpc get-authentication-table-by-session-id {
     description "Show authentication table entry by session-id";
     input {
       uses command-forwarding;
       leaf session-id {
         description "Session-id";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-authentication-table-by-address-type {
     description "Show authentication table entry with auth type by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-by-address {
         uses authentication-table-by-address-block;
       }
     }
   }
   rpc get-authentication-table-all {
     description "Show the entire authentication table in the userid daemon";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       leaf service-id {
         description "Show authentication table entries for service identities only";
         default "all";
         type string;
       }
     }
     output {
       container authentication-table-all {
         uses authentication-table-all-block;
       }
     }
   }
   rpc get-authentication-table-all-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-all-by-group {
         uses authentication-table-all-by-group-block;
       }
     }
   }
   rpc get-authentication-table-all-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-all-by-user {
         uses authentication-table-all-by-user-block;
       }
     }
   }
   rpc get-authentication-table-all-type {
     description "Show the entire authentication table in the userid daemon";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       container authentication-table-all {
         uses authentication-table-all-block;
       }
     }
   }
   rpc get-authentication-table-all-type-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-all-by-group {
         uses authentication-table-all-by-group-block;
       }
     }
   }
   rpc get-authentication-table-all-type-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-all-by-user {
         uses authentication-table-all-by-user-block;
       }
     }
   }
   rpc get-authentication-table-cp {
     description "Authentication source from Aruba ClearPass";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       container authentication-table-cp {
         uses authentication-table-cp-block;
       }
     }
   }
   rpc get-authentication-table-cp-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-cp-by-group {
         uses authentication-table-cp-by-group-block;
       }
     }
   }
   rpc get-authentication-table-cp-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-cp-by-user {
         uses authentication-table-cp-by-user-block;
       }
     }
   }
   rpc get-authentication-table-ad {
     description "Show the active directory authentication table";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       container authentication-table-ad {
         uses authentication-table-ad-block;
       }
     }
   }
   rpc get-authentication-table-ad-by-group {
     description "Show authentication table entry by group name";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-ad-by-group {
         uses authentication-table-ad-by-group-block;
       }
     }
   }
   rpc get-authentication-table-ad-by-user {
     description "Show authentication table entry by user name";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-ad-by-user {
         uses authentication-table-ad-by-user-block;
       }
     }
   }
   rpc get-authentication-table-ims {
     description "Identity management server";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf source-name {
         description "Authentication source name";
         type string {
           length "1 .. 65";
         }
       }
       leaf domain {
         description "Show identity-management-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       leaf service-id {
         description "Show authentication table entries for service identities only";
         default "all";
         type string;
       }
     }
     output {
       container authentication-table-ims {
         uses authentication-table-ims-block;
       }
     }
   }
   rpc get-authentication-table-ims-by-group {
     description "Show authentication table entry by group name";
     input {
       uses command-forwarding;
       leaf group-name {
         description "Group name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-ims-by-group {
         uses authentication-table-ims-by-group-block;
       }
     }
   }
   rpc get-authentication-table-ims-by-user {
     description "Show authentication table entry by user name";
     input {
       uses command-forwarding;
       leaf user-name {
         description "User name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container authentication-table-ims-by-user {
         uses authentication-table-ims-by-user-block;
       }
     }
   }
   rpc get-domain-controller-status {
     description "Show domain-controller status";
     input {
       uses command-forwarding;
       leaf domain {
         description "Show domain-controller status per domain";
         type string {
           length "1 .. 65";
         }
       }
       leaf level {
         default "brief";
         type enumeration {
           enum "brief" {
             description "Show brief output (default)";
           }
           enum "extensive" {
             description "Show extensive output";
           }
         }
       }
     }
     output {
       container domain-controller-status {
         uses domain-controller-status-block;
       }
     }
   }
   rpc get-ip-user-mapping-statistics {
     description "Show ip-user-mapping statistics";
     input {
       uses command-forwarding;
       leaf domain {
         description "Show ip-user-mapping statistics per domain";
         type string {
           length "1 .. 65";
         }
       }
     }
     output {
       container ip-user-mapping-statistics {
         uses ip-user-mapping-statistics-block;
       }
     }
   }
   rpc get-ip-user-probe-statistics {
     description "Show ip-user-probe statistics";
     input {
       uses command-forwarding;
       leaf domain {
         description "Show ip-user-probe statistics per domain";
         type string {
           length "1 .. 65";
         }
       }
     }
     output {
       container ip-user-probe-statistics {
         uses ip-user-probe-statistics-block;
       }
     }
   }
   rpc get-user-group-mapping-statistics {
     description "Show user-group-mapping statistics";
     input {
       uses command-forwarding;
       leaf domain {
         description "Show user-group-mapping statistics per domain";
         type string {
           length "1 .. 65";
         }
       }
     }
     output {
       container user-group-mapping-statistics {
         uses user-group-mapping-statistics-block;
       }
     }
   }
   rpc get-all-configuration {
     description "Show active-directory-access configuration";
     input {
       uses command-forwarding;
     }
   }
   rpc get-users-by-group {
     description "Show specified group's users. If timeout, wait several minutes and try again.";
     input {
       uses command-forwarding;
       leaf group-name {
         description "Specified group name";
         type string {
           length "1 .. 65";
         }
         mandatory true;
       }
       leaf domain {
         description "Show users per domain";
         type string {
           length "1 .. 65";
         }
         mandatory true;
       }
     }
     output {
       container users-by-group {
         uses users-by-group-block;
       }
     }
   }
   rpc get-groups-by-user {
     description "Show specified user's groups. If timeout, wait several minutes and try again.";
     input {
       uses command-forwarding;
       leaf user-name {
         description "Specified user name";
         type string {
           length "1 .. 65";
         }
         mandatory true;
       }
       leaf domain {
         description "Show groups per domain";
         type string {
           length "1 .. 65";
         }
         mandatory true;
       }
       leaf in-local-cache {
         description "Show only groups in local cache";
         type empty;
       }
     }
     output {
       container groups-by-user {
         uses groups-by-user-block;
       }
     }
   }
   rpc get-user-group-mapping-status {
     description "Show user-group-mapping status";
     input {
       uses command-forwarding;
       leaf domain {
         description "Show user-group-mapping status per domain";
         type string {
           length "1 .. 65";
         }
       }
     }
     output {
       container user-group-mapping-status {
         uses user-group-mapping-status-block;
       }
     }
   }
   rpc get-ad-ug-mapping-fetching {
     description "Show user-group-mapping fetching";
     input {
       uses command-forwarding;
     }
     output {
       choice output_c {
         case output-tag {
           leaf output {
             type string;
           }
         }
         case multichassis-tag {
           anyxml multi-routing-engine-results;
         }
       }
     }
   }
   rpc get-fetching-status {
     description "Show user-group-mapping fetching status";
     input {
       uses command-forwarding;
     }
     output {
       container fetching-status {
         uses fetching-status-block;
       }
     }
   }
   rpc get-periodic-fetching {
     description "Show user-group-mapping periodic fetching";
     input {
       uses command-forwarding;
     }
     output {
       choice output_c {
         case output-tag {
           leaf output {
             type string;
           }
         }
         case multichassis-tag {
           anyxml multi-routing-engine-results;
         }
       }
     }
   }
   rpc get-periodic-fetching-status {
     description "Show user-group-mapping periodic fetching status";
     input {
       uses command-forwarding;
     }
     output {
       container periodic-fetching-status {
         uses periodic-fetching-status-block;
       }
     }
   }
   rpc get-periodic-fetching-configuration {
     description "Show user-group-mapping periodic fetching configuration";
     input {
       uses command-forwarding;
     }
     output {
       container periodic-fetching-configuration {
         uses periodic-fetching-configuration-block;
       }
     }
   }
   rpc get-ad-ug-mapping-refreshing {
     description "Show user-group-mapping refreshing";
     input {
       uses command-forwarding;
     }
     output {
       choice output_c {
         case output-tag {
           leaf output {
             type string;
           }
         }
         case multichassis-tag {
           anyxml multi-routing-engine-results;
         }
       }
     }
   }
   rpc get-refreshing-status {
     description "Show user-group-mapping refreshing status";
     input {
       uses command-forwarding;
     }
     output {
       container refreshing-status {
         uses refreshing-status-block;
       }
     }
   }
   rpc get-all-groups {
     description "Show all groups";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
   }
   rpc get-all-users {
     description "Show all users";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
   }
   rpc get-ad-auth-table-all-information {
     description "Show the entire active directory authentication table";
     input {
       uses command-forwarding;
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
   }
   rpc get-ad-auth-table-by-address-information {
     description "Show active directory authentication table entry by ip-address";
     input {
       uses command-forwarding;
       leaf ip-address {
         description "IP address";
         type jt:ipaddr;
         mandatory true;
       }
     }
     output {
       choice output_c {
         case output-tag {
           leaf output {
             type string;
           }
         }
         case multichassis-tag {
           anyxml multi-routing-engine-results;
         }
       }
     }
   }
   rpc get-ad-auth-table-by-group-information {
     description "Show active directory authentication table entry by group name";
     input {
       uses command-forwarding;
       leaf group-name {
         description "Group name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc get-ad-auth-table-by-user-information {
     description "Show active directory authentication table entry by user name";
     input {
       uses command-forwarding;
       leaf user-name {
         description "User name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc get-cp-user-query-statistics {
     description "Show ClearPass user query counters";
     input {
       uses command-forwarding;
     }
     output {
       container cp-user-query-statistics {
         uses cp-user-query-statistics-block;
       }
     }
   }
   rpc get-cp-user-query-status {
     description "Show ClearPass user query status";
     input {
       uses command-forwarding;
     }
     output {
       container cp-user-query-status {
         uses cp-user-query-status-block;
       }
     }
   }
   rpc get-device-identity-table-all {
     description "Show the entire device identity table";
     input {
       uses command-forwarding;
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container device-identity-table-all {
         uses device-identity-table-all-block;
       }
     }
   }
   rpc get-device-identity-table-by-address {
     description "Show device identity table entry by ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container device-identity-table-by-address {
         uses device-identity-table-by-address-block;
       }
     }
   }
   rpc get-device-identity-table-by-device-id {
     description "Show device identity table entry by device id";
     input {
       uses command-forwarding;
       leaf device-id {
         description "Device ID";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container device-identity-table-by-device-id {
         uses device-identity-table-by-device-id-block;
       }
     }
   }
   rpc get-device-identity-table-by-group {
     description "Show device identity table entry by group name";
     input {
       uses command-forwarding;
       leaf group-name {
         description "Group name";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       container device-identity-table-by-group {
         uses device-identity-table-by-group-block;
       }
     }
   }
   rpc dump-property-lib {
     description "Dump property lib content";
   }
   rpc get-end-user-profile-address {
     description "Specified all address of specified end-user-profile";
     input {
       leaf profile-name {
         description "Specified profile name";
         type string {
           length "1 .. 65";
         }
       }
       leaf ip-start {
         description "IP from address";
         type jt:ipaddr;
       }
       leaf ip-end {
         description "IP to address";
         type jt:ipaddr;
       }
       leaf sort-by-profile {
         description "Sort by end-user-profile";
         type empty;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
   }
   rpc get-end-user-profile-statistics {
     description "Show end-user-profile ip-mapping statistics";
     input {
       uses command-forwarding;
     }
   }
   rpc get-jims-query-statistics {
     description "Show identity management query counters";
     input {
       uses command-forwarding;
       choice session_or_ip {
         case session {
           leaf session {
             description "Show identity management session counters";
             type empty;
           }
         }
         case ip {
           leaf ip {
             description "Show identity management ip counters";
             type empty;
           }
         }
       }
     }
     output {
       container jims-query-statistics {
         uses jims-query-statistics-block;
       }
     }
   }
   rpc get-jims-query-status {
     description "Show identity management query status";
     input {
       uses command-forwarding;
     }
     output {
       container jims-query-status {
         uses jims-query-status-block;
       }
     }
   }
   rpc get-jims-more-information {
     description "Show more information of identity management";
     input {
       uses command-forwarding;
     }
     output {
       container jims-more-info {
         uses jims-more-info-block;
       }
     }
   }
   rpc get-jims-validator-information {
     description "Show counter and status of jims validator query server of identity management";
     input {
       uses command-forwarding;
     }
     output {
       choice output_c {
         case output-tag {
           leaf output {
             type string;
           }
         }
         case multichassis-tag {
           anyxml multi-routing-engine-results;
         }
       }
     }
   }
   rpc get-jims-validator-query-statistics {
     description "Show identity management jims validator query counters";
     input {
       uses command-forwarding;
     }
     output {
       container jims-validator-query-statistics {
         uses jims-validator-query-statistics-block;
       }
     }
   }
   rpc get-jims-validator-query-status {
     description "Show identity management jims validator query status";
     input {
       uses command-forwarding;
     }
     output {
       container jims-validator-query-status {
         uses jims-validator-query-status-block;
       }
     }
   }
   rpc get-dispatcher-statistics {
     description "Show statistics";
     input {
       uses command-forwarding;
     }
   }
   rpc get-ld-jims-query-statistics {
     description "Show logical domain identity management query counters";
     input {
       uses command-forwarding;
     }
     output {
       container ld-jims-query-statistics {
         uses ld-jims-query-statistics-block;
       }
     }
   }
   rpc get-ld-jims-query-status {
     description "Show logical domain identity management query status";
     input {
       uses command-forwarding;
     }
     output {
       container ld-jims-query-status {
         uses ld-jims-query-status-block;
       }
     }
   }
   rpc get-validate-statistics-from-jims {
     description "Show validate statistics device/group/user from JIMS";
     input {
       uses command-forwarding;
     }
     output {
       choice output_c {
         case output-tag {
           leaf output {
             type string;
           }
         }
         case multichassis-tag {
           anyxml multi-routing-engine-results;
         }
       }
     }
   }
   rpc get-swgauth-profile-statistics {
     description "Show captive portal statistics for given profile";
     input {
       leaf profile-name {
         description "Captive portal profile name";
         type string {
           length "1 .. 65";
         }
       }
     }
     output {
       container swgauth-profile-statistics {
         uses swgauth-profile-statistics-block;
       }
     }
   }
   rpc swgauth-captiveportal-redirect-statistics {
     description "Show captive portal statistics for redirects";
     output {
       container swgauth-captiveportal-redirect-statistics {
         uses swgauth-captiveportal-redirect-statistics-block;
       }
     }
   }
   rpc swgauth-captiveportal-connection-statistics {
     description "Show captive oprtal statistics for connection";
     output {
       container swgauth-captiveportal-connection-statistics {
         uses swgauth-captiveportal-connection-statistics-block;
       }
     }
   }
   rpc get-web-transparent-proxy-session-detail {
     description "Show web transparent-proxy session detail";
     input {
       uses command-forwarding;
     }
     output {
       container web-transparent-proxy-session-information {
         uses web-transparent-proxy-session-information-block;
       }
     }
   }
   rpc get-web-transparent-proxy-session-summary {
     description "Show web transparent proxy session summary";
     input {
       uses command-forwarding;
     }
     output {
       container web-transparent-proxy-session-information {
         uses web-transparent-proxy-session-information-block;
       }
     }
   }
   rpc get-web-transparent-proxy-statistics {
     description "Show web transparent proxy staticstics";
     input {
       uses command-forwarding;
     }
     output {
       container web-transparent-proxy-statistics {
         uses web-transparent-proxy-statistics-block;
       }
     }
   }
   rpc get-web-explicit-proxy-session-detail {
     description "Show web explicit-proxy session detail";
     input {
       uses command-forwarding;
     }
     output {
       container web-explicit-proxy-session-information {
         uses web-explicit-proxy-session-information-block;
       }
     }
   }
   rpc get-web-explicit-proxy-session-summary {
     description "Show web explicit proxy session summary";
     input {
       uses command-forwarding;
     }
     output {
       container web-explicit-proxy-session-information {
         uses web-explicit-proxy-session-information-block;
       }
     }
   }
   rpc get-web-explicit-proxy-statistics {
     description "Show web explicit proxy staticstics";
     input {
       uses command-forwarding;
     }
     output {
       container web-explicit-proxy-statistics {
         uses web-explicit-proxy-statistics-block;
       }
     }
   }
   rpc get-web-proxy-dns-fc-entries {
     description "Show web proxy forwarding cache information";
     input {
       uses command-forwarding;
     }
     output {
       container web-proxy-dns-fc-entries {
         uses web-proxy-dns-fc-entries-block;
       }
     }
   }
   rpc get-web-proxy-dns-fc-entries-dump {
     description "Show web proxy forwarding cache information for specified dns-name";
     input {
       leaf dns-name {
         description "Show DNS cache matching the given DNS name";
         type string;
         mandatory true;
       }
     }
     output {
       container web-proxy-dns-fc-entries {
         uses web-proxy-dns-fc-entries-block;
       }
     }
   }
   rpc get-web-proxy-dns-fc-statistics {
     description "Show web proxy staticstics";
     input {
       uses command-forwarding;
     }
     output {
       container web-proxy-dns-fc-statistics {
         uses web-proxy-dns-fc-statistics-block;
       }
     }
   }
   rpc get-web-proxy-dns-gc-entries {
     description "Show web proxy global cache information";
     input {
       uses command-forwarding;
     }
     output {
       container web-proxy-dns-fc-entries {
         uses web-proxy-dns-fc-entries-block;
       }
     }
   }
   rpc get-web-proxy-dns-gc-entries-dump {
     description "Show web proxy global cache information for specified dnsname";
     input {
       uses command-forwarding;
       leaf dns-name {
         description "Show DNS cache matching the given DNS name";
         type string;
       }
     }
     output {
       container web-proxy-dns-fc-entries {
         uses web-proxy-dns-fc-entries-block;
       }
     }
   }
   rpc get-web-proxy-dns-gc-statistics {
     description "Show web proxy global staticstics";
     input {
       uses command-forwarding;
     }
     output {
       container web-proxy-dns-gc-statistics {
         uses web-proxy-dns-gc-statistics-block;
       }
     }
   }
   rpc get-lrf-statistics {
     description "Show lrf statistics";
     output {
       container lrf-statistics-summary {
         uses lrf-statistics-summary-block;
       }
     }
   }
   rpc get-lrf-collector-statistics {
     description "Show lrf collector statistics";
     input {
       leaf collector-name {
         description "Name of collector";
         type string;
       }
     }
     output {
       container lrf-collector-statistics-summary {
         uses lrf-collector-statistics-summary-block;
       }
     }
   }
   rpc get-lrf-rule-statistics {
     description "Show lrf rule statistics";
     input {
       leaf rule-name {
         description "Name of rule";
         type string;
       }
     }
     output {
       container lrf-rule-statistics-summary {
         uses lrf-rule-statistics-summary-block;
       }
     }
   }
   rpc get-lrf-template {
     description "Show lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       container lrf-template {
         uses lrf-template-block;
       }
     }
   }
   rpc get-service-accounting-information {
     description "Show sampled accounting service";
   }
   rpc get-service-accounting-status-information {
     description "Show service accounting parameters";
     input {
       leaf status-information {
         description "Name of service, wildcard, or 'all'";
         type string;
       }
     }
   }
   rpc get-service-accounting-status-inline-jflow-information {
     description "Show service accounting inline Jflow parameters";
     input {
       leaf inline-jflow-information {
         description "FPC Slot for inline Jflow";
         type union {
           type string {
             pattern "<.*>|$.*";
           }
           type uint32;
         }
       }
     }
   }
   rpc get-service-accounting-usage-information {
     description "Show CPU usage";
     input {
       leaf usage-information {
         description "Name of service, wildcard, or 'all'";
         type string;
       }
     }
   }
   rpc get-service-accounting-memory-information {
     description "Show memory information";
     input {
       leaf memory-information {
         description "Name of service, wildcard, or 'all'";
         type string;
       }
     }
   }
   rpc get-service-accounting-flow-information {
     description "Show flow information";
     input {
       leaf flow-information {
         description "Name of service, wildcard, or 'all'";
         type string;
       }
       leaf logical-system {
         description "Name of logical system";
         type string {
         }
       }
     }
   }
   rpc get-service-accounting-status-inline-jflow-flow-information {
     description "Show service accounting inline Jflow flow information";
     input {
       leaf inline-jflow-flow-information {
         description "FPC Slot for inline Jflow";
         type union {
           type string {
             pattern "<.*>|$.*";
           }
           type uint32;
         }
       }
     }
   }
   rpc get-service-accounting-flow-detail {
     description "Show flow detail";
     input {
       leaf flow-detail-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
       leaf source-as {
         description "Filter term source AS";
         type union {
           type uint32;
           type string {
             pattern "<.*>|$.*";
           }
         }
       }
       leaf destination-as {
         description "Filter term destination AS";
         type union {
           type uint32;
           type string {
             pattern "<.*>|$.*";
           }
         }
       }
       leaf tos {
         description "Filter term ToS";
         type union {
           type uint32;
           type string {
             pattern "<.*>|$.*";
           }
         }
       }
       leaf proto {
         description "Filter term protocol";
         type union {
           type uint32;
           type string {
             pattern "<.*>|$.*";
           }
         }
       }
     }
   }
   rpc get-service-accounting-aggregation-information {
     description "Show aggregation information";
   }
   rpc get-service-accounting-aggregation-as-information {
     description "Show aggregation type AS";
     input {
       leaf as-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type union {
           type uint32;
           type string {
             pattern "<.*>|$.*";
           }
         }
       }
       leaf destination-as {
         description "Filter term destination AS";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
     }
   }
   rpc get-service-accounting-aggregation-protocol-port-information {
     description "Show aggregation type protocol-port";
     input {
       leaf protocol-port-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type union {
           type uint32;
           type string {
             pattern "<.*>|$.*";
           }
         }
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
     }
   }
   rpc get-service-accounting-aggregation-source-prefix-information {
     description "Show aggregation type source-prefix";
     input {
       leaf source-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
     }
   }
   rpc get-service-accounting-aggregation-destination-prefix-information {
     description "Show aggregation type destination-prefix";
     input {
       leaf destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
   }
   rpc get-service-accounting-aggregation-source-destination-prefix-information {
     description "Show aggregation type source-destination-prefix";
     input {
       leaf source-destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
   }
   rpc get-service-accounting-aggregation-template-information {
     description "Show aggregation type template";
     input {
       leaf template-name {
         description "Name of template";
         type string;
         mandatory true;
       }
       leaf logical-system {
         description "Name of logical system";
         type string {
         }
       }
       leaf display {
         default "terse";
         type enumeration {
           enum "extensive" {
             description "Display extensive output";
           }
           enum "detail" {
             description "Display detailed output";
           }
           enum "terse" {
             description "Display terse output (default)";
           }
         }
       }
     }
   }
   rpc get-service-accounting-errors-information {
     description "Show error statistics";
     input {
       leaf error-information {
         description "Name of service, wildcard, or 'all'";
         type string;
       }
     }
   }
   rpc get-service-accounting-error-inline-jflow-information {
     description "Show service accounting inline Jflow error information";
     input {
       leaf inline-jflow-error-information {
         description "FPC Slot for inline Jflow";
         type union {
           type string {
             pattern "<.*>|$.*";
           }
           type uint32;
         }
       }
     }
   }
   rpc get-packet-distribution-information {
     description "Show packet size distribution";
     input {
       leaf packet-size-distribution-information {
         description "Name of service, wildcard, or 'all'";
         type string;
       }
     }
   }
   rpc get-service-video-monitoring-information {
     description "Show video-monitoring information";
   }
   rpc get-service-video-monitoring-mdi-information {
     description "Show MDI flows information";
   }
   rpc get-service-video-monitoring-mdi-stats-information {
     description "Show MDI flows stats information";
     input {
       leaf fpc-slot {
         description "FPC Slot number";
         type union {
           type string {
             pattern "<.*>|$.*";
           }
           type uint32;
         }
         mandatory true;
       }
     }
   }
   rpc get-service-video-monitoring-mdi-errors-information {
     description "Show MDI flows error information";
     input {
       leaf fpc-slot {
         description "FPC Slot number";
         type union {
           type string {
             pattern "<.*>|$.*";
           }
           type uint32;
         }
         mandatory true;
       }
     }
   }
   rpc get-service-video-monitoring-mdi-flows-information {
     description "Show MDI flows information";
     input {
       leaf fpc-slot {
         description "FPC Slot number";
         type union {
           type string {
             pattern "<.*>|$.*";
           }
           type uint32;
         }
         mandatory true;
       }
       leaf flow-count {
         description "Count of flows to display";
         type union {
           type string {
             pattern "<.*>|$.*";
           }
           type uint32 {
             range "1 .. 10000";
           }
         }
       }
       leaf flow-identifier {
         description "Flow Identifier";
         type union {
           type uint32;
           type string {
             pattern "<.*>|$.*";
           }
         }
       }
       leaf source-address {
         description "Source address of flow";
         type jt:ipprefix-optional;
       }
       leaf destination-address {
         description "Destination address of flow";
         type jt:ipprefix-optional;
       }
       leaf source-port {
         description "Source port of flow";
         type union {
           type uint32;
           type string {
             pattern "<.*>|$.*";
           }
         }
       }
       leaf destination-port {
         description "Destination port of flow";
         type union {
           type uint32;
           type string {
             pattern "<.*>|$.*";
           }
         }
       }
       leaf template-name {
         description "Template name";
         type string;
       }
       leaf ifl-name {
         description "Interface name";
         type union {
           type jt:interface-name;
           type string {
             pattern "<.*>|$.*";
           }
         }
       }
       leaf flow-direction {
         description "Direction of flow";
         type enumeration {
           enum "input" {
             description "Input flows";
           }
           enum "output" {
             description "Output flows";
           }
         }
       }
       leaf flow-type {
         description "Type of flow";
         type enumeration {
           enum "udp" {
             description "UDP flows";
           }
           enum "rtp" {
             description "RTP flows";
           }
         }
       }
       leaf flow-family-type {
         description "Type of flow";
         type enumeration {
           enum "flow-over-ipv4" {
             description "Flows over IPv4";
           }
           enum "flow-over-ipv4-over-mpls" {
             description "Flows over IPv4 over MPLS";
           }
           enum "flow-over-ipv6" {
             description "Flows over IPv6";
           }
           enum "flow-over-ipv6-over-mpls" {
             description "Flows over IPv6 over MPLS";
           }
         }
       }
       leaf split-display {
         description "Display terse/details output with DF and MLR in split format";
         type enumeration {
           enum "df-mlr-split-view" {
             description "Display detailed/brief flow output with DF and MLR split";
           }
         }
       }
       leaf flow-display {
         description "Display terse/details output";
         type enumeration {
           enum "detail" {
             description "Display detailed output";
           }
           enum "brief" {
             description "Display breif output (default)";
           }
         }
       }
     }
   }
   rpc get-services-video-monitoring-mdi-alarms-information {
     description "Show Alarm information";
   }
   rpc get-services-video-monitoring-mdi-alarms-stats-information {
     description "Show MDI alarm stats information";
     input {
       leaf fpc-slot {
         description "FPC Slot number";
         type union {
           type string {
             pattern "<.*>|$.*";
           }
           type uint32;
         }
         mandatory true;
       }
     }
   }
   rpc get-service-inline-monitoring-information {
     description "Show inline-monitoring information";
     output {
       choice output_c {
         case output-tag {
           leaf output {
             type string;
           }
         }
         case multichassis-tag {
           anyxml multi-routing-engine-results;
         }
       }
     }
   }
   rpc get-service-inline-monitoring-stats-information {
     description "Show inline-monitoring statistical information";
     input {
       leaf fpc-slot {
         description "FPC Slot number";
         type union {
           type string {
             pattern "<.*>|$.*";
           }
           type uint32;
         }
         mandatory true;
       }
     }
     output {
       container services-accounting-information {
         uses services-accounting-information-block;
       }
     }
   }
   rpc get-service-inline-monitoring-flow-ctr-map {
     description "Show inline-monitoring flow counter mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-service-inline-monitoring-flow-feature-map {
     description "Show inline-monitoring flow feature mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-services-mobile-edge-peers-info {
     description "Show SAEGW peers";
     output {
       container services-mobile-edge-peers-info {
         uses services-mobile-edge-peers-info-block;
       }
     }
   }
   rpc get-services-mobile-edge-peers-stats-info {
     description "Show SAEGW peers statistics";
     output {
       container services-mobile-edge-peers-stats-info {
         uses services-mobile-edge-peers-stats-info-block;
       }
     }
   }
   rpc get-services-mobile-edge-sessions-information {
     description "Show sessions";
     output {
       container services-mobile-edge-sessions-information {
         uses services-mobile-edge-sessions-information-block;
       }
     }
   }
   rpc get-services-mobile-edge-sessions-detail-info {
     description "Display session detail output";
     output {
       container services-mobile-edge-sessions-detail-info {
         uses services-mobile-edge-sessions-detail-info-block;
       }
     }
   }
   rpc get-services-mobile-edge-sessions-detail-tran {
     description "Display session detail output for transient-state sessions";
     output {
       container services-mobile-edge-sessions-detail-info {
         uses services-mobile-edge-sessions-detail-info-block;
       }
     }
   }
   rpc get-services-mobile-edge-sessions-detail-cpp {
     description "Display session detail output for control plane peers";
     input {
       leaf address {
         description "Display session detail output for control plane peer";
         type string;
         mandatory true;
       }
     }
     output {
       container services-mobile-edge-sessions-detail-cpp {
         uses services-mobile-edge-sessions-detail-cpp-block;
       }
     }
   }
   rpc get-services-mobile-edge-sessions-extensive {
     description "Display session extensive output";
     input {
       leaf get-services-mobile-edge-session-extensive-lseid {
         description "Display session extensive output of local-seid";
         type string;
       }
     }
     output {
       container services-mobile-edge-sessions-extensive {
         uses services-mobile-edge-sessions-extensive-block;
       }
     }
   }
   rpc get-services-mobile-edge-sessions-extensive-tran {
     description "Display sessions extensive output for transient-state sessions";
     output {
       container services-mobile-edge-sessions-extensive {
         uses services-mobile-edge-sessions-extensive-block;
       }
     }
   }
   rpc get-services-mobile-edge-sessions-histogram {
     description "Display established sessions histogram";
     output {
       container services-mobile-edge-sessions-histogram {
         uses services-mobile-edge-sessions-histogram-block;
       }
     }
   }
   rpc get-services-mobile-edge-session-summary {
     description "Display summary output";
     output {
       container services-mobile-edge-session-summary {
         uses services-mobile-edge-session-summary-block;
       }
     }
   }
   rpc get-services-mobile-edge-session-summary-cpp {
     description "Display control plane peers summary output";
     input {
       leaf address {
         description "Display control plane peers <IP ADDRESS> summary output";
         type string;
       }
     }
     output {
       container services-mobile-edge-session-summary-cpp {
         uses services-mobile-edge-session-summary-cpp-block;
       }
     }
   }
   rpc get-services-mobile-edge-session-summary-anp {
     description "Display access network peers summary output";
     input {
       leaf address {
         description "Display access network peers summary output";
         type string;
       }
     }
     output {
       container services-mobile-edge-session-summary-anp {
         uses services-mobile-edge-session-summary-anp-block;
       }
     }
   }
   rpc get-services-mobile-edge-session-summary-pic {
     description "Display pic summary output";
     input {
       leaf pic-name {
         description "Display pic summary output of <pfe-x/y>";
         type string {
         }
       }
     }
     output {
       container services-mobile-edge-session-summary-pic {
         uses services-mobile-edge-session-summary-pic-block;
       }
     }
   }
   rpc get-services-mobile-edge-session-summary-slot {
     description "Display slot summary output";
     input {
       leaf slot-name {
         description "Display slot summary output of <pfe-x>";
         type string {
         }
       }
     }
     output {
       container services-mobile-edge-session-summary-slot {
         uses services-mobile-edge-session-summary-slot-block;
       }
     }
   }
   rpc get-services-mobile-edge-session-summary-apns {
     description "Display APN name summary output";
     input {
       leaf apn-name {
         description "Display summary output of APN <APN-NAME>";
         type string {
           length "1 .. 100";
         }
       }
     }
     output {
       container services-mobile-edge-session-summary-apns {
         uses services-mobile-edge-session-summary-apns-block;
       }
     }
   }
   rpc get-services-mobile-edge-session-summary-ag {
     description "Display anchor group summary output";
     input {
       leaf apfe-name {
         description "Display summary output of anchor-group apfe<x>";
         type string {
           length "1 .. 100";
         }
       }
     }
     output {
       container services-mobile-edge-session-summary-ag {
         uses services-mobile-edge-session-summary-ag-block;
       }
     }
   }
   rpc get-services-mobile-edge-session-summary-cnp {
     description "Display core network peers summary output";
     input {
       leaf address {
         description "Display core network peers summary output";
         type string;
       }
     }
     output {
       container services-mobile-edge-session-summary-cnp {
         uses services-mobile-edge-session-summary-cnp-block;
       }
     }
   }
   rpc get-services-mobile-edge-sessions-summary-tran {
     description "Display transient-state summary output";
     output {
       container services-mobile-edge-sessions-summary-tran {
         uses services-mobile-edge-sessions-summary-tran-block;
       }
     }
   }
   rpc get-services-mobile-edge-sessions-cpp-info {
     description "Display session output for control plane peers";
     input {
       leaf address {
         description "Display session output for control plane peer";
         type string;
       }
     }
     output {
       container services-mobile-edge-sessions-cpp-info {
         uses services-mobile-edge-sessions-cpp-info-block;
       }
     }
   }
   rpc get-services-mobile-edge-summary-info {
     description "Show SAE gateway summary";
     output {
       container services-mobile-edge-summary-info {
         uses services-mobile-edge-summary-info-block;
       }
     }
   }
   rpc get-services-mobile-edge-apfe-dl-cos {
     description "Show APFE CoS settings";
   }
   rpc get-services-mobile-edge-resources-cac-stats {
     description "CAC status and statistics";
     output {
       container services-mobile-edge-resources-cac-stats {
         uses services-mobile-edge-resources-cac-stats-block;
       }
     }
   }
   rpc get-analytics-agent-information {
     description "Show analytics service agent information";
     input {
       leaf level {
         default "brief";
         type enumeration {
           enum "detail" {
             description "Display detailed data";
           }
           enum "brief" {
             description "Display brief data (default)";
           }
         }
       }
     }
     output {
       container analytics-agent-information {
         uses analytics-agent-information-block;
       }
     }
   }
   rpc get-probe-results {
     description "Show probe results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       container probe-results {
         uses probe-results-block;
       }
     }
   }
   rpc get-history-results {
     description "Show history results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       container history-results {
         uses history-results-block;
       }
     }
   }
   rpc get-active-servers {
     description "Show configured servers";
     output {
       container active-servers {
         uses active-servers-block;
       }
     }
   }
   rpc twamp-information {
     description "Show TWAMP information";
     output {
       choice output_c {
         case output-tag {
           leaf output {
             type string;
           }
         }
         case multichassis-tag {
           anyxml multi-routing-engine-results;
         }
       }
     }
   }
   rpc twamp-client-information {
     description "Show TWAMP client information";
     output {
       container twamp-client-information {
         uses twamp-client-information-block;
       }
     }
   }
   rpc twamp-client-connection-information {
     description "Display connection information";
     input {
       leaf connection-name {
         description "Control connection name";
         default "all";
         type string;
       }
     }
     output {
       choice output_c {
         case output-tag {
           leaf output {
             type string;
           }
         }
         case multichassis-tag {
           anyxml multi-routing-engine-results;
         }
       }
     }
   }
   rpc twamp-client-test-session {
     description "Display test session information";
     input {
       leaf control-connection {
         description "Control connection name";
         type string {
           length "1 .. 32";
         }
       }
       leaf test-session {
         description "Test session name";
         type string {
           length "1 .. 32";
         }
       }
     }
     output {
       choice output_c {
         case output-tag {
           leaf output {
             type string;
           }
         }
         case multichassis-tag {
           anyxml multi-routing-engine-results;
         }
       }
     }
   }
   rpc twamp-get-probe-results {
     description "Display test session results";
     input {
       leaf control-connection {
         description "Control connection name";
         type string;
       }
       leaf test-session {
         description "Test session name";
         type string;
       }
     }
     output {
       container probe-results {
         uses probe-results-block;
       }
     }
   }
   rpc twamp-get-history-results {
     description "Display test session history results";
     input {
       leaf verbosity_level {
         default "brief";
         type enumeration {
           enum "brief" {
             description "Display brief output (default)";
           }
           enum "detail" {
             description "Display detailed output";
           }
         }
       }
       leaf control-connection {
         description "Control connection name";
         type string;
       }
       leaf test-session {
         description "Test session name";
         type string;
       }
       leaf since {
         description "Show history since YYYY-MM-DD.HH:MM:SS";
         type jt:time;
       }
     }
     output {
       container history-results {
         uses history-results-block;
       }
     }
   }
   rpc twamp-server-information {
     description "Show TWAMP server information";
     output {
       container twamp-server-information {
         uses twamp-server-information-block;
       }
     }
   }
   rpc twamp-server-connection-information {
     description "Display connection information";
     input {
       leaf connection-id {
         description "Connection ID";
         default "all";
         type string;
       }
     }
     output {
       choice output_c {
         case output-tag {
           leaf output {
             type string;
           }
         }
         case multichassis-tag {
           anyxml multi-routing-engine-results;
         }
       }
     }
   }
   rpc twamp-server-session-information {
     description "Display session information";
     input {
       leaf session-id {
         description "Session ID";
         default "all";
         type string;
       }
     }
     output {
       choice output_c {
         case output-tag {
           leaf output {
             type string;
           }
         }
         case multichassis-tag {
           anyxml multi-routing-engine-results;
         }
       }
     }
   }
   rpc get-rfc2544-information {
     description "Show rfc2544 information";
   }
   rpc get-test-id-information {
     description "Show rfc2544 test id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
   }
   rpc get-active-tests-information {
     description "Show rfc2544 active tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
   }
   rpc get-aborted-tests-information {
     description "Show rfc2544 aborted tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
   }
   rpc get-completed-tests-information {
     description "Show rfc2544 completed tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
   }
   rpc get-rfc2544-summary-information {
     description "Show rfc2544 summary";
   }
   rpc get-secintel-category-feed {
     description "Show category detail information";
     input {
       uses command-forwarding;
       leaf category-name {
         description "Category name";
         type string;
         mandatory true;
       }
       leaf feed-name {
         description "Feed name";
         type string;
         mandatory true;
       }
       leaf start {
         description "Start number";
         type union {
           type uint32;
           type string {
             pattern "<.*>|$.*";
           }
         }
       }
       leaf count {
         description "Total number";
         type union {
           type uint32;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-secintel-category-summary {
     description "Show category summary";
     input {
       uses command-forwarding;
       leaf category-name {
         description "Show specified category summary";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-secintel-category-list {
     description "Show all category names";
     input {
       uses command-forwarding;
     }
   }
   rpc get-secintel-update-status {
     description "Show update status";
     input {
       uses command-forwarding;
     }
   }
   rpc get-secintel-recommended-action {
     description "Show security intelligence recommended action ";
     input {
       uses command-forwarding;
       leaf category-name {
         description "Show category recommended action";
         type string;
       }
     }
     output {
       container secintel-recommended-action {
         uses secintel-recommended-action-block;
       }
     }
   }
   rpc get-secintel-redirect-files {
     description "Show redirect files information";
     input {
       uses command-forwarding;
       leaf file-name {
         description "Show redirect-file content";
         type string {
         }
       }
     }
     output {
       container secintel-redirect-files {
         uses secintel-redirect-files-block;
       }
     }
   }
   rpc get-secintel-post-status {
     description "Show sec-profiling feed post status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-secintel-statistics {
     description "Show security intelligence statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container secintel-statistics {
         uses secintel-statistics-block;
       }
     }
   }
   rpc get-secintel-statistics-profile {
     description "Show security intelligence profile statistics";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-dns-statistics {
     description "Show security intelligence dns-statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container dns-statistics {
         uses dns-statistics-block;
       }
     }
   }
   rpc get-dns-statistics-profile {
     description "Show security intelligence dns-profile statistics";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-dns-filtering-cache {
     description "Show DNS-Filtering cache";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container dns-filtering-cache {
         uses dns-filtering-cache-block;
       }
     }
   }
   rpc get-dns-filtering-cache-summary {
     description "Show DNS-Filtering Cache Summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container dns-filtering-cache-summary {
         uses dns-filtering-cache-summary-block;
       }
     }
   }
   rpc get-dns-filtering-cache-c2 {
     description "Show DNS-Filtering Cache C2-Entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container dns-filtering-cache-c2 {
         uses dns-filtering-cache-c2-block;
       }
     }
   }
   rpc get-dns-filtering-cache-benign {
     description "Show DNS-Filtering Cache Benign-Entries";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container dns-filtering-cache-benign {
         uses dns-filtering-cache-benign-block;
       }
     }
   }
   rpc get-services-match-policies {
     description "Show match-policy information";
     input {
       leaf service-set {
         description "Name of service set";
         type string;
       }
       leaf source-ip {
         description "Source address";
         type jt:ipprefix;
       }
       leaf source-port {
         description "Source port to use as match";
         type union {
           type uint16;
           type string {
             pattern "<.*>|$.*";
           }
         }
       }
       leaf destination-ip {
         description "Destination address";
         type jt:ipprefix;
       }
       leaf destination-port {
         description "Destination port to use as match";
         type union {
           type uint16;
           type string {
             pattern "<.*>|$.*";
           }
         }
       }
       leaf protocol {
         description "IP protocol name or number";
         type string;
       }
       leaf result-count {
         description "The number of policy matches to display";
         type union {
           type uint16;
           type string {
             pattern "<.*>|$.*";
           }
         }
       }
       leaf match-direction {
         description "Match direction";
         type enumeration {
           enum "input" {
             description "Direction input";
           }
           enum "output" {
             description "Direction output";
           }
         }
       }
     }
     output {
       container services-match-policies-information {
         uses services-match-policies-information-block;
       }
     }
   }
   rpc get-service-cos-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       container service-cos-statistics-information {
         uses service-cos-statistics-information-block;
       }
     }
   }
   rpc get-service-cos-diffserv-statistics {
     description "Show Diffserv marking statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-cos-forwarding-class-statistics {
     description "Show forwarding Class statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
   }
   rpc get-service-hcm-statistics-information {
     description "Show hcm statistics";
     input {
       leaf rule {
         description "Name of HCM tag rule";
         type string;
       }
     }
     output {
       container service-hcm-statistics-information {
         uses service-hcm-statistics-information-block;
       }
     }
   }
   rpc get-service-hcm-pic-statistics-information {
     description "Show hcm pic statistics";
     input {
       leaf interface {
         description "Name of extension provider interface";
         type string;
       }
     }
     output {
       container service-hcm-pic-statistics-information {
         uses service-hcm-pic-statistics-information-block;
       }
     }
   }
   rpc get-service-mss-sessions-information {
     description "Show mobile subscriber data sessions";
     input {
       leaf imsi {
         description "IMSI of subscriber";
         type string {
           length "5 .. 15";
         }
       }
     }
   }
   rpc get-service-hcm-sessions-stats {
     description "Show hcm session statistics";
     input {
       leaf imsi {
         description "IMSI of subscriber";
         type string {
           length "5 .. 15";
         }
         mandatory true;
       }
     }
   }
   rpc get-service-tdf-sessions-information {
     description "Show traffic-detection-function subscriber data sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-tdf-hcm-sessions-stats {
     description "Show hcm session statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
   }
   rpc get-service-pgcp-flow-table-information {
     description "Show PGCP flow table entries";
     output {
       container service-pgcp-flow-table-information {
         uses service-pgcp-flow-table-information-block;
       }
     }
   }
   rpc get-service-pgcp-flow-table-information-gateway {
     description "Show packet-gateway-control-protocol information for gateway";
     input {
       leaf gateway-name {
         description "Gateway name";
         type string;
         mandatory true;
       }
       leaf gate-id {
         description "Gate id";
         type union {
           type uint64;
           type string {
             pattern "<.*>|$.*";
           }
         }
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf get-service-pgcp-flow-count-information {
         description "Show count of matching entries";
         type empty;
       }
       leaf level {
         default "brief";
         type enumeration {
           enum "brief" {
             description "Display brief output";
           }
           enum "extensive" {
             description "Display extensive output";
           }
         }
       }
       leaf backup-data-pic {
         description "Show flows table by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-service-pgcp-conversation-information {
     description "Show PGCP conversations";
     output {
       container service-pgcp-conversation-information {
         uses service-pgcp-conversation-information-block;
       }
     }
   }
   rpc get-service-pgcp-conversation-information-gateway {
     description "Show PGCP conversations for gateway";
     input {
       leaf gateway-name {
         description "Gateway name";
         type string;
         mandatory true;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf level {
         default "brief";
         type enumeration {
           enum "brief" {
             description "Display brief output";
           }
           enum "extensive" {
             description "Display extensive output";
           }
         }
       }
       leaf backup-data-pic {
         description "Show conversations information by querying the backup Data-PIC";
         type empty;
       }
       leaf redundancy-option {
         default "master";
         type enumeration {
           enum "master" {
             description "Query the master RE or ms-pic (default)";
           }
           enum "backup" {
             description "Query the backup ms-pic";
           }
         }
       }
     }
   }
   rpc get-pgcpd-active-configuration {
     description "Show pgcpd active-configuration";
     output {
       container pgcpd-active-configuration {
         uses pgcpd-active-configuration-block;
       }
     }
   }
   rpc get-service-pgcp-active-configuration-gateway {
     description "Show gateway active configuration";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-pgcp-statistics {
     description "Show pgcpd statistics";
   }
   rpc get-service-pgcp-statistics-gateway {
     description "Show gateway statistics";
     input {
       leaf gateway-name {
         description "Gateway name";
         type string;
         mandatory true;
       }
       leaf display {
         default "brief";
         type enumeration {
           enum "brief" {
             description "Display brief output (default)";
           }
           enum "extensive" {
             description "Display extensive output";
           }
         }
       }
       leaf redundancy-option {
         default "master";
         type enumeration {
           enum "master" {
             description "Query the master RE or ms-pic (default)";
           }
           enum "backup" {
             description "Query the backup ms-pic";
           }
         }
       }
     }
     output {
       container service-pgcp-statistics-gateway {
         uses service-pgcp-statistics-gateway-block;
       }
     }
   }
   rpc get-service-pgcp-terminations {
     description "Show list of terminations";
     output {
       container service-pgcp-terminations {
         uses service-pgcp-terminations-block;
       }
     }
   }
   rpc get-service-pgcp-terminations-gateway {
     description "Show list of terminations for gateway";
     input {
       leaf gateway-name {
         description "Gateway name";
         type string;
         mandatory true;
       }
       leaf termination-prefix {
         description "Termination-prefix to use as filter, default * (all)";
         type string;
       }
       leaf display {
         default "brief";
         type enumeration {
           enum "h248" {
             description "Display H248 output format";
           }
           enum "brief" {
             description "Display brief output (default)";
           }
           enum "count" {
             description "Show count of matching entries";
           }
         }
       }
       leaf redundancy-option {
         default "master";
         type enumeration {
           enum "master" {
             description "Query the master RE or ms-pic (default)";
           }
           enum "backup" {
             description "Query the backup ms-pic";
           }
         }
       }
     }
   }
   rpc get-service-pgcp-gates {
     description "Show list of gates";
     output {
       container service-pgcp-gates {
         uses service-pgcp-gates-block;
       }
     }
   }
   rpc get-service-pgcp-gates-gateway {
     description "Show all gates for gateway";
     input {
       leaf gateway-name {
         description "Gateway name";
         type string;
         mandatory true;
       }
       leaf display {
         default "brief";
         type enumeration {
           enum "extensive" {
             description "Display extensive output";
           }
           enum "brief" {
             description "Display brief output (default)";
           }
           enum "count" {
             description "Show count of matching entries";
           }
         }
       }
       leaf source-routing-instance {
         description "Source routing-instance";
         type string;
       }
       leaf destination-routing-instance {
         description "Destination routing-instance";
         type string;
       }
       leaf redundancy-option {
         default "master";
         type enumeration {
           enum "master" {
             description "Query the master RE or ms-pic (default)";
           }
           enum "backup" {
             description "Query the backup ms-pic";
           }
         }
       }
     }
   }
   rpc get-service-pgcp-gate {
     description "Show gate according to gate-id";
   }
   rpc get-service-pgcp-gate-gateway {
     description "Show gate for gateway";
     input {
       leaf gateway-name {
         description "Gateway name";
         type string;
         mandatory true;
       }
       leaf gate-id {
         description "Gate id";
         type union {
           type uint64;
           type string {
             pattern "<.*>|$.*";
           }
         }
         mandatory true;
       }
       leaf display {
         default "brief";
         type enumeration {
           enum "extensive" {
             description "Display extensive output";
           }
           enum "brief" {
             description "Display brief output (default)";
           }
           enum "statistics" {
             description "Display statistics for gate";
           }
           enum "session-mirroring" {
             description "Display session mirroring for gate";
           }
         }
       }
       leaf redundancy-option {
         default "master";
         type enumeration {
           enum "master" {
             description "Query the master RE or ms-pic (default)";
           }
           enum "backup" {
             description "Query the backup ms-pic";
           }
         }
       }
     }
   }
   rpc get-services-pgcpd-root-termination {
     description "Show root termination h248 information";
     output {
       container services-pgcpd-root-termination {
         uses services-pgcpd-root-termination-block;
       }
     }
   }
   rpc get-services-pgcpd-root-termination-gateway {
     description "Show root termination h248 information for gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
   }
   rpc get-service-border-signaling-gateway-statistics-calls {
     description "Show border signaling gateway calls statistics";
     output {
       container bsg-statistics-calls-details {
         uses bsg-statistics-calls-details-block;
       }
     }
   }
   rpc get-service-border-signaling-gateway-statistics-calls-by-sp {
     description "Show border signaling gateway calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-by-server {
     description "Show border signaling gateway calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-sp {
     description "Show border signaling gateway calls duration statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-calls-duration-by-server {
     description "Show border signaling gateway calls duration statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-statistics-failed-calls-by-sp {
     description "Show border signaling gateway failed calls statistics grouped by service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-calls-failed-details {
         uses bsg-statistics-calls-failed-details-block;
       }
     }
   }
   rpc get-service-border-signaling-gateway-statistics-failed-calls-by-server {
     description "Show border signaling gateway failed calls statistics grouped by server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-calls-failed-details {
         uses bsg-statistics-calls-failed-details-block;
       }
     }
   }
   rpc get-service-bsg-denied-messages {
     description "Show information about dropped messages";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-statistics-denied-messages-details {
         uses bsg-statistics-denied-messages-details-block;
       }
     }
   }
   rpc get-service-border-signaling-gateway-statistics-admission-control {
     description "Show border signaling gateway admission control profile statistics statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-border-signaling-gateway-information-by-request-uri {
     description "Show border signaling gateway information by request uri";
     input {
       leaf gateway {
         description "Name of border signaling gateway";
         type string;
         mandatory true;
       }
       leaf uri {
         description "URI";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-border-signaling-gateway-information-by-contact {
     description "Show border signaling gateway information by contact";
     input {
       leaf gateway {
         description "Name of border signaling gateway";
         type string;
         mandatory true;
       }
       leaf contact {
         description "Contact";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-information-by-call-context-id {
     description "Show border signaling gateway information by call context ID";
     input {
       leaf gateway {
         description "Name of border signaling gateway";
         type string;
         mandatory true;
       }
       leaf context-id {
         description "Call context ID";
         type union {
           type uint32;
           type string {
             pattern "<.*>|$.*";
           }
         }
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
   }
   rpc get-service-bsg-status-information {
     description "Show border signaling gateway status information";
     input {
       leaf gateway {
         description "Name of border signaling gateway";
         type string;
         mandatory true;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       container bsg-status-information {
         uses bsg-status-information-block;
       }
     }
   }
   rpc get-border-signaling-gateway-name-resolution-cache-by-fqdn {
     description "Show records for the Fully Qualified Domain Name";
     input {
       leaf fqdn {
         description "Fully Qualified Domain Name";
         type string;
         mandatory true;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-name-resolution-cache-information {
         uses bsg-name-resolution-cache-information-block;
       }
     }
   }
   rpc get-service-border-signaling-gateway-name-resolution-cache-all {
     description "Show contents of the cache";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-name-resolution-cache-information {
         uses bsg-name-resolution-cache-information-block;
       }
     }
   }
   rpc get-service-border-signaling-gateway-routing-blacklist {
     description "Show border signaling gateway servers blacklist content";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
   }
   rpc get-service-bsg-registrations {
     description "Show border signaling gateway registrations statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-registrations {
         uses bsg-registrations-block;
       }
     }
   }
   rpc get-service-bsg-registrations-statistics {
     description "Show registration statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-registrations {
         uses bsg-registrations-block;
       }
     }
   }
   rpc get-service-bsg-registrations-realm-statistics {
     description "Realm statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf realm-name {
         type string;
       }
     }
     output {
       container bsg-registrations-realm {
         uses bsg-registrations-realm-block;
       }
     }
   }
   rpc get-service-border-signaling-gateway-address-of-record {
     description "Show border signaling gateway address of record";
     output {
       container bsg-address-of-records {
         uses bsg-address-of-records-block;
       }
     }
   }
   rpc get-service-border-signaling-gateway-address-of-record-bindings {
     description "Show address of record bindings";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf address-of-record {
         description "Address of record name";
         type string;
       }
       leaf detail {
         description "Detail mode";
         type empty;
       }
     }
   }
   rpc get-service-border-signaling-gateway-charging-status {
     description "Show border signaling gateway accounting status";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-charging-status {
         uses bsg-charging-status-block;
       }
     }
   }
   rpc get-service-border-signaling-gateway-charging-statistics {
     description "Show border signaling gateway accounting statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       container bsg-charging-statistics {
         uses bsg-charging-statistics-block;
       }
     }
   }
   rpc get-service-msp-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf get-service-sfw-flow-count-information {
         description "Show count of matching entries";
         type empty;
       }
     }
     output {
       container service-sfw-flow-table-information {
         uses service-sfw-flow-table-information-block;
       }
     }
   }
   rpc get-msp-session-table {
     description "Show session table entries";
     input {
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf add-on {
         type enumeration {
           enum "nat" {
             description "Sessions with network address translation";
           }
         }
       }
       leaf source-nat-pool {
         description "Source NAT Pool name";
         type string;
       }
       leaf nat-port-overload-index {
         description "NAT port overloading index";
         type union {
           type string {
             pattern "<.*>|$.*";
           }
           type uint32 {
             range "0 .. 127";
           }
         }
       }
     }
   }
   rpc get-service-msp-sess-count-information {
     description "Show count of matching entries";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of extension provider interface";
         type string;
       }
       leaf add-on {
         type enumeration {
           enum "nat" {
             description "Sessions with network address translation";
           }
         }
       }
       leaf source-nat-pool {
         description "Source NAT Pool name";
         type string;
       }
       leaf nat-port-overload-index {
         description "NAT port overloading index";
         type union {
           type string {
             pattern "<.*>|$.*";
           }
           type uint32 {
             range "0 .. 127";
           }
         }
       }
     }
     output {
       container service-msp-sess-count-information {
         uses service-msp-sess-count-information-block;
       }
     }
   }
   rpc get-service-msp-sess-softwire {
     description "Show softwire session table entries";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
     }
   }
   rpc get-usf-service-softwire-table-information {
     description "Show softwire flow entries";
     output {
       container usf-service-softwire-table-information {
         uses usf-service-softwire-table-information-block;
       }
     }
   }
   rpc get-service-msp-sess-softwire-count-info {
     description "Show softwire count of matching entries";
     input {
       leaf source-prefix {
         description "Source prefix to use as filter";
         type string;
       }
       leaf destination-prefix {
         description "Destination prefix to use as filter";
         type string;
       }
       leaf service-set {
         description "Name of service set";
         type string;
       }
       leaf interface {
         description "Name of extension provider interface";
         type string;
       }
     }
   }
   rpc get-service-msp-sess-softwire-dslite-info {
     description "Show ds-lite related softwire sessions";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
       leaf get-service-msp-sess-softwire-dslite-count-info {
         description "Show count of matching entries";
         type empty;
       }
       leaf aftr {
         description "AFTR IPV6 Address";
         type jt:ipv6addr;
       }
       leaf b4 {
         description "B4 IPV6 Address";
         type jt:ipv6addr;
       }
     }
   }
   rpc get-service-msp-session-analysis-information {
     description "Show service sessions statistics";
     input {
       leaf interface {
         description "Name of extension provider interface";
         type string;
       }
     }
   }
   rpc get-services-sessions-utilization {
     description "Show session utilization statistics";
     input {
       leaf interface {
         description "Name of extension provider interface";
         type string;
       }
     }
     output {
       container services-sessions-utilization-information {
         uses services-sessions-utilization-information-block;
       }
     }
   }
   rpc get-services-sessions-tcp-log {
     description "Show services sessions tcp-log";
     input {
       leaf interface {
         description "Name of extension provider interface";
         type string;
       }
     }
   }
   rpc get-service-msp-alg-conversation-information {
     description "Show alg conversations";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf display {
         default "brief";
         type enumeration {
           enum "extensive" {
             description "Display extensive output";
           }
           enum "brief" {
             description "Display brief output (default)";
           }
         }
       }
     }
     output {
       container service-msp-alg-conversation-information {
         uses service-msp-alg-conversation-information-block;
       }
     }
   }
   rpc get-service-msp-alg-stats-information {
     description "Show ALG Statistics";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       container service-msp-alg-stats-information {
         uses service-msp-alg-stats-information-block;
       }
     }
   }
   rpc get-service-msp-alg-sip-globals-information {
     description "Show SIP ALG global configurations";
     input {
       leaf interface {
         description "Name of extension provider interface";
         type string;
       }
     }
     output {
       container service-msp-alg-sip-globals-information {
         uses service-msp-alg-sip-globals-information-block;
       }
     }
   }
   rpc get-service-ha-info {
     description "Show HA info and current status";
     input {
       leaf interface {
         description "Name of adaptive services interface";
         type string;
       }
       leaf level {
         default "brief";
         type enumeration {
           enum "brief" {
             description "Display brief output";
           }
           enum "detail" {
             description "Display detailed output";
           }
           enum "statistics" {
             description "Display statistics output";
           }
         }
       }
     }
     output {
       container service-ha-info {
         uses service-ha-info-block;
       }
     }
   }
   rpc get-service-flow-analysis-information {
     description "Show flow table entries";
     input {
       leaf interface {
         description "Name of adaptive services interface";
         type string;
       }
     }
     output {
       container service-flow-analysis-information {
         uses service-flow-analysis-information-block;
       }
     }
   }
   rpc get-service-subs-analysis-information {
     description "Show subscriber table entries";
     input {
       leaf interface {
         description "Name of adaptive services interface";
         type string;
       }
     }
     output {
       container service-subs-analysis-information {
         uses service-subs-analysis-information-block;
       }
     }
   }
   rpc get-service-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
       leaf get-service-sfw-flow-count-information {
         description "Show count of matching entries";
         type empty;
       }
     }
     output {
       container service-sfw-flow-table-information {
         uses service-sfw-flow-table-information-block;
       }
     }
   }
   rpc get-service-sfw-conversation-information {
     description "Show conversations";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
     }
     output {
       container service-sfw-conversation-information {
         uses service-sfw-conversation-information-block;
       }
     }
   }
   rpc get-service-sfw-sip-call-information {
     description "Show SIP call information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-call-count-information {
         description "Show count of matching entries";
         type empty;
       }
     }
     output {
       container service-sfw-sip-call-information {
         uses service-sfw-sip-call-information-block;
       }
     }
   }
   rpc get-service-sfw-sip-register-information {
     description "Show SIP register information";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-register-count-information {
         description "Show count of matching entries";
         type empty;
       }
     }
   }
   rpc get-service-sfw-statistics-information {
     description "Show statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       container service-sfw-statistics-information {
         uses service-sfw-statistics-information-block;
       }
     }
   }
   rpc get-sfw-application-protocol-statistics {
     description "Application protocol type to use as filter";
     input {
       leaf protocol {
         description "Application protocol type to use as filter";
         type enumeration {
           enum "sip" {
             description "Session Initiation Protocol";
           }
         }
       }
     }
     output {
       container service-sfw-statistics-information {
         uses service-sfw-statistics-information-block;
       }
     }
   }
   rpc get-service-sfw-redundancy-statistics {
     description "Show redundancy statistics";
     input {
       leaf backup-data-pic {
         description "Query the backup data PIC";
         type empty;
       }
       leaf display {
         default "brief";
         type enumeration {
           enum "extensive" {
             description "Display extensive output";
           }
           enum "brief" {
             description "Display brief output (default)";
           }
         }
       }
     }
   }
   rpc get-service-capture {
     description "Show Services PIC packet capture";
     input {
       leaf file {
         type string;
         mandatory true;
       }
       leaf level {
         default "brief";
         type enumeration {
           enum "brief" {
             description "Display brief output";
           }
           enum "detail" {
             description "Display detailed output";
           }
           enum "extensive" {
             description "Display extensive output";
           }
         }
       }
       leaf packet-id {
         description "Packet-id to be used as filter";
         type string;
       }
     }
   }
   rpc get-service-softwire-table-information {
     description "Show softwire information";
     input {
       leaf get-service-current-softwire-count-information {
         description "Show count of softwires created";
         type empty;
       }
     }
     output {
       container service-softwire-table-information {
         uses service-softwire-table-information-block;
       }
     }
   }
   rpc get-service-softwire-flow-table-information {
     description "Show flow table entries";
     input {
       leaf service-set {
         description "Name of service set";
         type string;
       }
       leaf interface {
         description "Name of adaptive services interface";
         type string;
       }
       leaf get-service-softwire-count-information {
         description "Show count of matching entries";
         type empty;
       }
     }
     output {
       container service-softwire-flow-table-information {
         uses service-softwire-flow-table-information-block;
       }
     }
   }
   rpc get-service-softwire-ds-lite-flow-table-information {
     description "Show ds-lite related softwire flows";
     input {
       leaf AFTR {
         description "AFTR IPV6 Address";
         type jt:ipv6addr;
       }
       leaf B4 {
         description "B4 IPV6 Address";
         type jt:ipv6addr;
       }
     }
     output {
       container service-softwire-flow-table-information {
         uses service-softwire-flow-table-information-block;
       }
     }
   }
   rpc get-service-softwire-v6rd-flow-table-information {
     description "Show v6rd related softwire flows";
     input {
       leaf concentrator {
         description "Softwire concentrator IPV4 Address";
         type jt:ipv4addr;
       }
       leaf initiator {
         description "Softwire initiator IPV4 Address";
         type jt:ipv4addr;
       }
     }
     output {
       container service-softwire-flow-table-information {
         uses service-softwire-flow-table-information-block;
       }
     }
   }
   rpc get-service-softwire-session-table-information {
     description "Show session table entries";
     input {
       leaf service-set {
         description "Name of service set";
         type string;
       }
       leaf interface {
         description "Name of adaptive services interface";
         type string;
       }
       leaf get-service-softwire-session-count-info {
         description "Show count of matching entries";
         type empty;
       }
     }
   }
   rpc get-service-softwire-session-dslite-table-info {
     description "Show ds-lite related softwire sessions";
     input {
       leaf service-set {
         description "Name of service set";
         type string;
       }
       leaf interface {
         description "Name of adaptive services interface";
         type string;
       }
       leaf get-service-softwire-session-count-info {
         description "Show count of matching entries";
         type empty;
       }
       leaf aftr {
         description "AFTR IPV6 Address";
         type jt:ipv6addr;
       }
       leaf b4 {
         description "B4 IPV6 Address";
         type jt:ipv6addr;
       }
     }
   }
   rpc get-service-softwire-statistics-information {
     description "Show global softwire statistics";
     input {
       leaf interface {
         description "Name of adaptive services interface";
         type string;
       }
       leaf display {
         type enumeration {
           enum "ds-lite" {
             description "Show softwire statistics for dslite";
           }
           enum "v6rd" {
             description "Show softwire statistics for v6rd";
           }
         }
       }
     }
     output {
       container service-softwire-statistics-information {
         uses service-softwire-statistics-information-block;
       }
     }
   }
   rpc get-inline-service-sw-statistics-information {
     description "Show global inline softwire statistics";
     input {
       leaf interface {
         description "Name of adaptive services interface";
         type string;
       }
       leaf display {
         type enumeration {
           enum "v6rd" {
             description "Softwire statistics for 6rd";
           }
           enum "mape" {
             description "Softwire statistics for MAPE";
           }
           enum "mapt" {
             description "Softwire statistics for MAPT";
           }
         }
       }
     }
     output {
       container inline-service-sw-statistics-information {
         uses inline-service-sw-statistics-information-block;
       }
     }
   }
   rpc get-inline-nat-statistics-information {
     description "Show global inline nat statistics";
     input {
       leaf interface {
         description "Name of adaptive services interface";
         type string;
       }
     }
     output {
       container inline-nat-statistics-information {
         uses inline-nat-statistics-information-block;
       }
     }
   }
   rpc get-inline-nat-pool-information {
     description "Show NAT pools information";
     input {
       leaf pool-name {
         description "Name of pool";
         type string;
       }
     }
   }
   rpc get-inline-nat-mapping-nptv6-information {
     description "Show nptv6 translated address";
     input {
       leaf address {
         description "IPV6 Address";
         type jt:ipv6addr;
         mandatory true;
       }
       leaf direction {
         type enumeration {
           enum "internal" {
             description "Internal-address";
           }
           enum "external" {
             description "External-address";
           }
         }
         mandatory true;
       }
     }
   }
   rpc get-inline-ip-reass-statistics {
     description "Show IP Reassembly statistics";
     input {
       uses command-forwarding;
     }
     output {
       container inline-ip-reass-statistics-information {
         uses inline-ip-reass-statistics-information-block;
       }
     }
   }
   rpc get-inline-ip-reass-si-statistics-information {
     description "Show inline ip-reassembly statistics on si-ifl";
     input {
       leaf interface-name {
         description "Name of adaptive services interface";
         type string;
         mandatory true;
       }
     }
     output {
       container inline-ip-reass-statistics-information {
         uses inline-ip-reass-statistics-information-block;
       }
     }
   }
   rpc get-inline-ip-reass-fpc-slot-information {
     description "FPC slot number";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
     output {
       container inline-ip-reass-statistics-information {
         uses inline-ip-reass-statistics-information-block;
       }
     }
   }
   rpc get-inline-ipv6-reass-statistics {
     description "Show IPv6 Reassembly statistics";
     input {
       uses command-forwarding;
     }
     output {
       container inline-ipv6-reass-statistics-information {
         uses inline-ipv6-reass-statistics-information-block;
       }
     }
   }
   rpc get-ipv6-reassembly-interface-information {
     description "Inline-service interface related statistics";
     input {
       leaf interface-name {
         description "Name of inline service interface";
         type string;
         mandatory true;
       }
     }
     output {
       container inline-ipv6-reass-statistics-information {
         uses inline-ipv6-reass-statistics-information-block;
       }
     }
   }
   rpc get-inline-ipv6-reass-fpc-slot-information {
     description "FPC slot number";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
     output {
       container inline-ipv6-reass-statistics-information {
         uses inline-ipv6-reass-statistics-information-block;
       }
     }
   }
   rpc get-inline-sfw-flow-table-information {
     description "Show flow table entries";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of adaptive services interface";
         type string;
       }
       leaf get-inline-sfw-flow-count-information {
         description "Show count of matching entries";
         type empty;
       }
     }
     output {
       container service-sfw-flow-table-information {
         uses service-sfw-flow-table-information-block;
       }
     }
   }
   rpc get-inline-sfw-statistics-information {
     description "Show statistics";
     input {
       leaf display {
         default "brief";
         type enumeration {
           enum "brief" {
             description "Display brief output (default)";
           }
           enum "summary" {
             description "Display summary output";
           }
         }
       }
       leaf service-set {
         description "Name of service set";
         type string;
       }
       leaf interface {
         description "Name of adaptive services interface";
         type string;
       }
     }
     output {
       container service-sfw-statistics-information {
         uses service-sfw-statistics-information-block;
       }
     }
   }
   rpc get-service-ids-source-table-information {
     description "Show attack source address table";
     input {
       leaf source-prefix {
         description "Source prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         uses service-ids-flow-table-information-block;
       }
     }
   }
   rpc get-service-ids-destination-table-information {
     description "Show attack destination address table";
     input {
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         uses service-ids-flow-table-information-block;
       }
     }
   }
   rpc get-service-ids-pair-table-information {
     description "Show attack source and destination address pair table";
     input {
       leaf source-prefix {
         description "Source prefix to use as filter";
         type string;
       }
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       container service-ids-flow-table-information {
         uses service-ids-flow-table-information-block;
       }
     }
   }
   rpc get-service-identification-statistics-information {
     description "Show service identification statistics";
     input {
       leaf detail {
         description "Display detailed statistics";
         type empty;
       }
     }
     output {
       container service-identification-statistics-information {
         uses service-identification-statistics-information-block;
       }
     }
   }
   rpc get-header-redirect-set-statistics-information {
     description "Show header redirect set statistics";
     input {
       leaf detail {
         description "Display detailed statistics";
         type empty;
       }
     }
     output {
       container header-redirect-set-statistics-information {
         uses header-redirect-set-statistics-information-block;
       }
     }
   }
   rpc get-uri-redirect-set-statistics-information {
     description "Show URI redirect set statistics";
     input {
       leaf detail {
         description "Display detailed statistics";
         type empty;
       }
     }
     output {
       container uri-redirect-set-statistics-information {
         uses uri-redirect-set-statistics-information-block;
       }
     }
   }
   rpc get-flow-table-statistics-information {
     description "Show flow table statistics";
     input {
       leaf detail {
         description "Show detailed statistics information";
         type empty;
       }
     }
     output {
       container flow-table-statistics-information {
         uses flow-table-statistics-information-block;
       }
     }
   }
   rpc get-soft-gre-tunnel-database {
     description "Show active soft gre active tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case interface {
           leaf interface {
             description "Interface name to use as filter";
             type string;
           }
         }
         case tunnel-group {
           leaf tunnel-group {
             description "Tunnel group to use as filter";
             type string;
           }
         }
         case local-ip {
           leaf local-ip {
             description "Local ip address to use as filter";
             type jt:ipv4addr;
           }
         }
         case remote-ip {
           leaf remote-ip {
             description "Remote ip address to use as filter";
             type jt:ipv4addr;
           }
         }
       }
     }
     output {
       container soft-gre-tunnel-database {
         uses soft-gre-tunnel-database-block;
       }
     }
   }
   rpc get-l2tp-destination-information {
     description "Show L2TP destination information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       container service-l2tp-destination-information {
         uses service-l2tp-destination-information-block;
       }
     }
   }
   rpc get-services-l2tp-destination-lockout {
     description "Display locked out destinations";
     output {
       container service-l2tp-destination-lockout-information {
         uses service-l2tp-destination-lockout-information-block;
       }
     }
   }
   rpc get-l2tp-tunnel-information {
     description "Show active L2TP tunnel list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       container service-l2tp-tunnel-information {
         uses service-l2tp-tunnel-information-block;
       }
     }
   }
   rpc get-l2tp-session-information {
     description "Show active L2TP session list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
     output {
       container service-l2tp-session-information {
         uses service-l2tp-session-information-block;
       }
     }
   }
   rpc get-l2tp-client-information {
     description "Show active L2TP clients list";
     input {
       leaf client-name {
         description "Client name";
         type string;
       }
     }
     output {
       container service-l2tp-client-information {
         uses service-l2tp-client-information-block;
       }
     }
   }
   rpc get-l2tp-tunnel-group-information {
     description "Show tunnel-group list";
     input {
       leaf tunnel-group-name {
         description "Tunnel group name";
         type string;
       }
     }
     output {
       container service-l2tp-tunnel-group-information {
         uses service-l2tp-tunnel-group-information-block;
       }
     }
   }
   rpc get-l2tp-session-limit-group-information {
     description "Show session-limit-group list";
     input {
       leaf session-limit-group-name {
         description "Session limit group name";
         type string;
       }
     }
     output {
       container service-l2tp-session-limit-group-information {
         uses service-l2tp-session-limit-group-information-block;
       }
     }
   }
   rpc get-l2tp-tunnel-switch-information {
     description "Show table of tunnel switched sessions";
     output {
       container service-l2tp-tunnel-switch-information {
         uses service-l2tp-tunnel-switch-information-block;
       }
     }
   }
   rpc get-l2tp-tunnel-switch-session-information {
     description "Show tunnel switched sessions";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
     output {
       container service-l2tp-session-information {
         uses service-l2tp-session-information-block;
       }
     }
   }
   rpc get-l2tp-tunnel-switch-tunnel-information {
     description "Show switched tunnels";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       container service-l2tp-tunnel-information {
         uses service-l2tp-tunnel-information-block;
       }
     }
   }
   rpc get-l2tp-tunnel-switch-destination-information {
     description "Show tunnel switched destinations";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       container service-l2tp-destination-information {
         uses service-l2tp-destination-information-block;
       }
     }
   }
   rpc get-l2tp-disconnect-cause-summary {
     description "Show L2TP disconnect cause summary";
     output {
       container service-l2tp-disconnect-cause-summary {
         uses service-l2tp-disconnect-cause-summary-block;
       }
     }
   }
   rpc get-l2tp-user-information {
     description "Show active L2TP user list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case user {
           leaf user {
             description "Filter by username";
             type string;
           }
         }
       }
     }
     output {
       container service-l2tp-session-information {
         uses service-l2tp-session-information-block;
       }
     }
   }
   rpc get-l2tp-multilink-information {
     description "Show active L2TP multilink list";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case bundle-id {
           leaf bundle-id {
             description "Filter by multilink bundle ID";
             type string;
           }
         }
       }
     }
     output {
       container services-l2tp-multilink-information {
         uses services-l2tp-multilink-information-block;
       }
     }
   }
   rpc get-l2tp-summary-information {
     description "Show L2TP summary information";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       leaf interface {
         description "Name of adaptive services interface";
         type string;
       }
     }
     output {
       container service-l2tp-summary-information {
         uses service-l2tp-summary-information-block;
       }
     }
   }
   rpc get-services-l2tp-radius-authentication-accounting-servers-information {
     description "Show RADIUS authentication and accounting servers information";
     output {
       container services-l2tp-radius-authentication-accounting-servers-information {
         uses services-l2tp-radius-authentication-accounting-servers-information-block;
       }
     }
   }
   rpc get-services-l2tp-radius-authentication-accounting-statistics-information {
     description "Show RADIUS authentication and accounting statistics information";
     output {
       container services-l2tp-radius-authentication-accounting-statistics-information {
         uses services-l2tp-radius-authentication-accounting-statistics-information-block;
       }
     }
   }
   rpc get-services-l2tp-radius-authentication-servers-information {
     description "Show RADIUS authentication servers information";
     output {
       container services-l2tp-radius-authentication-servers-information {
         uses services-l2tp-radius-authentication-servers-information-block;
       }
     }
   }
   rpc get-services-l2tp-radius-authentication-statistics-information {
     description "Show RADIUS authentication statistics information";
     output {
       container services-l2tp-radius-authentication-statistics-information {
         uses services-l2tp-radius-authentication-statistics-information-block;
       }
     }
   }
   rpc get-services-l2tp-radius-accounting-servers-information {
     description "Show RADIUS accounting servers information";
     output {
       container services-l2tp-radius-accounting-servers-information {
         uses services-l2tp-radius-accounting-servers-information-block;
       }
     }
   }
   rpc get-services-l2tp-radius-accounting-statistics-information {
     description "Show RADIUS accounting statistics information";
     output {
       container services-l2tp-radius-accounting-statistics-information {
         uses services-l2tp-radius-accounting-statistics-information-block;
       }
     }
   }
   rpc get-service-crtp-params-information {
     description "Show Compressed Real-Time Protocol information";
     input {
       leaf interface {
         description "Name of link services interface";
         type string;
       }
     }
   }
   rpc get-service-crtp-extensive-information {
     description "Show CRTP extensive output";
     input {
       leaf interface {
         description "Name of link services interface";
         type string;
       }
     }
   }
   rpc get-service-crtp-flow-table-information {
     description "Show CRTP flow table entries";
     input {
       leaf interface {
         description "Name of link services interface";
         type string;
       }
     }
     output {
       container service-crtp-flow-table-information {
         uses service-crtp-flow-table-information-block;
       }
     }
   }
   rpc get-link-services-cpu-usage {
     description "Show cpu usage as a percentage for the specified PIC";
     input {
       leaf interface {
         description "Name of link services interface";
         type string;
         mandatory true;
       }
       leaf level {
         default "brief";
         type enumeration {
           enum "brief" {
             description "Display brief output (1 and 5 second average)";
           }
           enum "detail" {
             description "Display detailed output (per cpu average)";
           }
         }
       }
     }
     output {
       container lsqinfo-cpu-usage-information {
         uses lsqinfo-cpu-usage-information-block;
       }
     }
   }
   rpc get-global-pcp-statistics-information {
     description "Show global PCP statistics";
     input {
       leaf interface {
         description "Name of adaptive services interface";
         type string;
       }
       leaf level {
         type enumeration {
           enum "protocol" {
             description "Display PCP protocol statistics";
           }
         }
       }
     }
   }
   rpc get-msp-ssubscriber-table {
     description "Show subscriber table entries";
   }
   rpc get-service-subscriber-analysis-information {
     description "Show service subscribers statistics";
     input {
       leaf interface {
         description "Name of extension provider interface";
         type string;
       }
     }
   }
   rpc get-tcp-log-connection-information {
     description "Show connections related to TCP logging";
     input {
       leaf interface {
         description "Name of extension provider interface";
         type string;
       }
     }
   }
   rpc get-services-redundancy-group-information {
     description "Show services redundancy-group information";
     input {
       leaf verbose {
         default "terse";
         type enumeration {
           enum "terse" {
             description "Display terse output(default)";
           }
           enum "brief" {
             description "Display brief output";
           }
           enum "extensive" {
             description "Display detailed output";
           }
         }
       }
     }
   }
   rpc get-services-redundancy-group-id-information {
     description "Show redundancy group-id information";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type union {
           type uint32;
           type string {
             pattern "<.*>|$.*";
           }
         }
         mandatory true;
       }
     }
   }
   rpc get-ip-monitoring-status {
     description "Ip monitoring status";
     input {
       leaf policy {
         description "Policy name";
         type string;
       }
     }
     output {
       container ip-monitoring {
         uses ip-monitoring-block;
       }
     }
   }
   rpc get-traffic-load-balance-statistics {
     description "Traffic load balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
   }
   rpc get-flb-statistics {
     description "FLB  statistics";
     input {
       leaf all {
         description "All flb instances";
         type empty;
       }
     }
   }
   rpc traffic-load-balance-commit-status {
     description "Display commit status";
     output {
       container tdir-commit-status {
         uses tdir-commit-status-block;
       }
     }
   }
   rpc get-url-filter-statistics {
     description "Show web filter statistics";
     input {
       leaf profile {
         description "Web filter profile specific statistics";
         type string;
         mandatory true;
       }
       leaf url-filter-template {
         description "Url filter template specific statistics";
         type string;
       }
       leaf dns-filter-template {
         description "DNS filter template specific statistics";
         type string;
       }
       leaf dns-filter-term {
         description "DNS filter term specific statistics";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf level {
         default "brief";
         type enumeration {
           enum "brief" {
             description "Brief Information";
           }
           enum "detail" {
             description "Detailed Information";
           }
           enum "extensive" {
             description "Extensive Information";
           }
         }
       }
     }
     output {
       container url-filter-statistics {
         uses url-filter-statistics-block;
       }
     }
   }
   rpc get-web-filter-dns-feed-statistics {
     description "Show web filter dns feed statistics";
     input {
       leaf feed-name {
         description "Web filter DNS feed  specific statistics";
         type string;
         mandatory true;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
   }
   rpc get-url-filter-dns-resolution {
     description "Show url-filter dns-resolution";
     input {
       leaf profile {
         description "Url-filter profile specific DNS resolution information";
         type string;
         mandatory true;
       }
       leaf url-filter-template {
         description "Url-filter template specific DNS resolution information";
         type string;
       }
     }
     output {
       container url-filter-dns-resolution {
         uses url-filter-dns-resolution-block;
       }
     }
   }
   rpc get-url-filter-dns-resolution-statistics {
     description "Show url-filter dns-resolution statistics";
     input {
       leaf profile {
         description "Url-filter profile specific DNS resolution information";
         type string;
         mandatory true;
       }
       leaf url-filter-template {
         description "Url-filter template specific DNS resolution information";
         type string;
         mandatory true;
       }
       leaf verbosity_level {
         type enumeration {
           enum "summary" {
             description "Display summary output";
           }
           enum "extensive" {
             description "Display extensive output";
           }
         }
         mandatory true;
       }
     }
     output {
       container url-filter-dns-resolution-statistics {
         uses url-filter-dns-resolution-statistics-block;
       }
     }
   }
   rpc get-url-filter-secintel-policy-status {
     description "Show secintel policy status";
     input {
       leaf profile {
         description "Url-filter profile specific secintel policy status";
         type string;
         mandatory true;
       }
       leaf url-filter-template {
         description "Url-filter template specific secintel policy status";
         type string;
       }
       leaf verbosity_level {
         type enumeration {
           enum "summary" {
             description "Display summary output";
           }
           enum "extensive" {
             description "Display extensive output";
           }
         }
       }
     }
     output {
       container url-filter-secintel-policy-status {
         uses url-filter-secintel-policy-status-block;
       }
     }
   }
   rpc get-url-filter-secintel-policy-db {
     description "Web filtering secintel policy db";
     input {
       leaf ip-prefix-information {
         description "Web filtering secintel IP prefix information";
         type string;
         mandatory true;
       }
       leaf profile {
         description "Web filtering secintel profile IP prefix information";
         type string;
         mandatory true;
       }
       leaf template {
         description "Web filtering secintel template IP prefix information";
         type string;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping fwa-statistics-block {
     container fwa-counters {
       description "Fixed wireless access statistics";
       leaf create-session-req-rcv {
         type int32;
         description "Create session requests received";
       }
       leaf create-session-resp-xmit {
         type int32;
         description "Create session responses transmitted";
       }
       leaf modify-bearer-req-rcv {
         type int32;
         description "Modify bearer requests received";
       }
       leaf modify-bearer-resp-xmit {
         type int32;
         description "Modify bearer response transmitted";
       }
       leaf delete-session-req-rcv {
         type int32;
         description "Delete session request received";
       }
       leaf delete-session-resp-xmit {
         type int32;
         description "Delete session response transmitted";
       }
       leaf delete-bearer-req-rcv {
         type int32;
         description "Delete bearer request received";
       }
       leaf delete-bearer-resp-xmit {
         type int32;
         description "Delete bearer request transmitted";
       }
       leaf error-indication-rcv {
         type int32;
         description "Error indication rcv";
       }
       leaf error-indication-xmit {
         type int32;
         description "Error indication transmitted";
       }
       leaf echo-req-rcv {
         type int32;
         description "Echo request received";
       }
       leaf echo-resp-xmit {
         type int32;
         description "Echo request transmitted";
       }
     }
   }
   grouping uac-debug-counters-block {
     leaf uac-debug-counters-title {
       type string;
       description "Uac debug counters";
     }
     list uac-debug-counter-info {
       description "Uac debug counter info";
       leaf uac-debug-counter-name {
         type string;
       }
       leaf uac-debug-counter-value {
         type uint32;
       }
     }
   }
   grouping uac-counters-block {
     list uac-counter {
       description "UAC counter for the PFE";
       leaf pfe-name {
         type string;
         description "PFE";
       }
       leaf allowed-policy-action {
         type uint32;
         description "Sessions allowed due to policy action";
       }
       leaf allowed-timeout-action {
         type uint32;
         description "Sessions allowed due to timeout action";
       }
       leaf denied-unauthenticated {
         type uint32;
         description "Sessions denied due to lack of authentication";
       }
       leaf denied-policy-action {
         type uint32;
         description "Sessions denied due to policy action";
       }
       leaf denied-policy-unmatched {
         type uint32;
         description "Sessions denied due to unmatched policy";
       }
       leaf denied-timeout-action {
         type uint32;
         description "Sessions denied due to timeout action";
       }
       leaf terminated-reevaluation {
         type uint32;
         description "Sessions terminated due to reevaluation";
       }
       leaf terminated-signout {
         type uint32;
         description "Sessions terminated due to user signout";
       }
       leaf auth-added {
         type uint32;
         description "Auth entry added to PFE";
       }
       leaf auth-deleted {
         type uint32;
         description "Auth entry deleted from PFE";
       }
       leaf current-auth-cnt {
         type uint32;
         description "UAC total auth count";
       }
     }
   }
   grouping ift-global-information-block {
     container ift-global {
       leaf device-id {
         type uint32;
         description "Unique device identifier";
       }
       leaf meta-data-stack-length {
         type uint32;
         description "Maximum length of the meta-data";
       }
       leaf hop-limit {
         type uint32;
         description "Maximum hop limit";
       }
       leaf flow-type {
         type string;
         description "Traffic flow type";
       }
       leaf no-ipv6-address-match {
         type uint32;
         description "IPV6 address match allowed or not";
       }
       leaf clock-source {
         type string;
         description "Clock source for timestamping";
       }
     }
   }
   grouping ift-profile-information-block {
     list ift-profile {
       leaf profile-name {
         type string;
         description "Profile name";
       }
       leaf sample-rate {
         type uint32;
         description "Ratio of packets to be sampled (1 out of N)";
       }
       container collector-info {
         leaf source-address {
           type string;
           description "Source address";
         }
         leaf destination-address {
           type string;
           description "Destination address";
         }
         leaf destination-port {
           type int32;
           description "Destination port";
         }
         leaf maximum-clip-length {
           type int32;
           description "Clip length of data packet";
         }
         leaf mtu {
           type int32;
           description "MTU of export packets";
         }
       }
     }
   }
   grouping ift-stats-information-block {
     container ift-stats {
       leaf init-packets {
         type uint64;
         description "IFA initator statistics";
       }
       leaf transit-packets {
         type uint64;
         description "IFA transit statistics";
       }
       leaf terminate-rx-packets {
         type uint64;
         description "IFA termination rx statistics";
       }
       leaf terminate-tx-packets {
         type uint64;
         description "IFA termination tx statistics";
       }
       leaf terminate-tx-records {
         type uint64;
         description "IFA termination tx records";
       }
     }
   }
   grouping services-flow-collector-information-block {
     leaf interface-name {
       type string;
       description "Physical interface name";
     }
     leaf pic-status {
       type string;
       description "Current interface state";
     }
     leaf flow-collector-destination-response {
       type string;
       description "Selected destination";
     }
     leaf test-file-transfer-response {
       type string;
     }
     leaf clear-flow-collector-statistics-response {
       type string;
     }
     container statistics-information {
       description "Service flow collector application information";
       leaf memory-used {
         type int32;
         description "Memory used, in bytes";
       }
       leaf memory-free {
         type int32;
         description "Memory free, in bytes";
       }
       leaf packets {
         type int32;
         description "Packets";
       }
       leaf packets-per-second {
         type int32;
         description "Packets per second";
       }
       leaf peak-packets-per-second {
         type int32;
         description "Peak packets per second";
       }
       leaf bytes {
         type int32;
         description "Bytes";
       }
       leaf bytes-per-second {
         type int32;
         description "Bytes per second";
       }
       leaf peak-bytes-per-second {
         type int32;
         description "Peak bytes per second";
       }
       leaf flow-record-processed {
         type int32;
         description "Flow records processed";
       }
       leaf flow-record-processed-per-second {
         type int32;
         description "Flow records processed per second";
       }
       leaf peak-flow-record-processed-per-second {
         type int32;
         description "Peak flow records processed per second";
       }
       leaf blocks-allocated {
         type int32;
         description "Blocks allocated";
       }
       leaf blocks-allocated-per-second {
         type int32;
         description "Blocks allocated per second";
       }
       leaf peak-blocks-allocated-per-second {
         type int32;
         description "Peak blocks allocated per second";
       }
       leaf blocks-freed {
         type int32;
         description "Blocks freed";
       }
       leaf blocks-freed-per-second {
         type int32;
         description "Blocks freed per second";
       }
       leaf peak-blocks-freed-per-second {
         type int32;
         description "Peak blocks freed per second";
       }
       leaf blocks-unavailable {
         type int32;
         description "Blocks unavailable";
       }
       leaf blocks-unavailable-per-second {
         type int32;
         description "Blocks unavailable per second";
       }
       leaf peak-blocks-unavailable-per-second {
         type int32;
         description "Peak blocks unavailable per second";
       }
       leaf files-created {
         type int32;
         description "Files created";
       }
       leaf files-created-per-second {
         type int32;
         description "Files created per second";
       }
       leaf peak-files-created-per-second {
         type int32;
         description "Peak files created per second";
       }
       leaf files-exported {
         type int32;
         description "Files exported";
       }
       leaf files-exported-per-second {
         type int32;
         description "Files exported per second";
       }
       leaf peak-files-exported-per-second {
         type int32;
         description "Peak files exported per second";
       }
       leaf files-destroyed {
         type int32;
         description "Files destroyed";
       }
       leaf files-destroyed-per-second {
         type int32;
         description "Files destroyed per second";
       }
       leaf peak-files-destroyed-per-second {
         type int32;
         description "Peak files destroyed per second";
       }
       leaf uncompressed-bytes {
         type int32;
         description "Uncompressed bytes";
       }
       leaf uncompressed-bytes-per-second {
         type int32;
         description "Uncompressed bytes per second";
       }
       leaf peak-uncompressed-bytes-per-second {
         type int32;
         description "Peak uncompressed bytes per second";
       }
       leaf compressed-bytes {
         type int32;
         description "Compressed bytes";
       }
       leaf compressed-bytes-per-second {
         type int32;
         description "Compressed bytes per second";
       }
       leaf peak-compressed-bytes-per-second {
         type int32;
         description "Peak compressed bytes per second";
       }
       leaf packet-no-memory-drops {
         type int32;
         description "Packets dropped because of insufficient memory";
       }
       leaf packet-not-ip-drops {
         type int32;
         description "Packets dropped because they were not IP packets";
       }
       leaf packet-not-ipv4-drops {
         type int32;
         description "Packets dropped because they were not IPv4 packets";
       }
       leaf packet-too-small-drops {
         type int32;
         description "Packets dropped because they were too small";
       }
       leaf packet-ip-fragment-drops {
         type int32;
         description "Packets dropped because they were fragments";
       }
       leaf packet-icmp-drops {
         type int32;
         description "Packets dropped because they were ICMP packets";
       }
       leaf packet-tcp-drops {
         type int32;
         description "Packets dropped because they were TCP packets";
       }
       leaf packet-unknown-drops {
         type int32;
         description "Packets dropped because they were an unknown type";
       }
       leaf packet-not-jflow-drops {
         type int32;
         description "Packets dropped because they were not JUNOS flow packets";
       }
       leaf ftp-bytes {
         type int32;
         description "FTP bytes";
       }
       leaf ftp-bytes-per-second {
         type int32;
         description "FTP bytes per second";
       }
       leaf peak-ftp-bytes-per-second {
         type int32;
         description "Peak FTP bytes per second";
       }
       leaf ftp-files {
         type int32;
         description "FTP files";
       }
       leaf ftp-files-per-second {
         type int32;
         description "FTP files per second";
       }
       leaf peak-ftp-files-per-second {
         type int32;
         description "Peak FTP files per second";
       }
       leaf ftp-failures {
         type int32;
         description "Number of ftp transfer failures";
       }
       container export-channel {
         leaf export-channel-index {
           type int32;
           description "Export channel index";
         }
         leaf current-server {
           type string;
           description "Currently used server";
         }
         leaf primary-server-state {
           type string;
           description "Primary server state";
         }
         leaf secondary-server-state {
           type string;
           description "Secondary server state";
         }
       }
     }
     container file-information {
       description "Service flow collector information about files";
       container file {
         leaf file-name {
           type string;
           description "Filename";
         }
         leaf flow-records {
           type int32;
           description "Flow records in file";
         }
         leaf flow-records-per-second {
           type int32;
           description "Flow records per second";
         }
         leaf peak-flow-records-per-second {
           type int32;
           description "Peak flow records per second";
         }
         leaf uncompressed-bytes {
           type int32;
           description "Uncompressed bytes";
         }
         leaf uncompressed-bytes-per-second {
           type int32;
           description "Uncompressed bytes per second";
         }
         leaf peak-uncompressed-bytes-per-second {
           type int32;
           description "Peak uncompressed bytes per second";
         }
         leaf compressed-bytes {
           type int32;
           description "Compressed bytes";
         }
         leaf compressed-bytes-per-second {
           type int32;
           description "Compressed bytes per second";
         }
         leaf peak-compressed-bytes-per-second {
           type int32;
           description "Peak compressed bytes per second";
         }
         leaf compressed-block-count {
           type int32;
           description "Number of compressed blocks";
         }
         leaf block-count {
           type int32;
           description "Number of blocks in file";
         }
         leaf state {
           type string;
           description "Current state of the file";
         }
         leaf transfer-attempts {
           type int32;
           description "Number of FTP transfer attempts";
         }
       }
     }
     container input-information {
       description "Service flow collector information for each input";
       container input {
         description "Input interface statistics";
         leaf input-interface {
           type string;
           description "Input interface";
         }
         leaf packets {
           type int32;
           description "Packets";
         }
         leaf bytes {
           type int32;
           description "Bytes";
         }
       }
     }
   }
   grouping cpcd-pic-statistics-block {
     container statistics-header {
       leaf service-set-interface {
         type string;
         description "PIC interface servicing the service-set";
       }
     }
     list statistics {
       description "Statistics";
       leaf packets-received {
         type uint64;
         description "Number of packets received";
       }
       leaf packets-altered {
         type uint64;
         description "Number of packets rewritten/redirected/tagged";
       }
     }
   }
   grouping cpcd-profile-block {
     container cpcd-profile-table {
       container cpcd-profile-table-entry {
         leaf profile-name {
           type string;
           description "Profile name";
         }
         leaf num-rules {
           type int32;
         }
       }
     }
   }
   grouping cpcd-rule-block {
     container cpcd-rule-table {
       container cpcd-rule-table-entry {
         leaf rule-name {
           type string;
           description "Rule name";
         }
         leaf term-name {
           type string;
           description "Term name";
         }
       }
     }
   }
   grouping cpcd-pic-information-block {
     container cpcd-pic-table {
       container cpcd-pic-table-entry {
         leaf pic-name {
           type string;
         }
         leaf pic-index {
           type int32;
         }
       }
     }
   }
   grouping dynamic-filtering-connection-status-block {
     leaf message {
       type string;
     }
     leaf url {
       type string;
     }
     leaf port {
       type int32;
     }
     leaf purl {
       type string;
     }
     leaf pport {
       type string;
     }
     container dynamic-filtering-connection-block {
       description "Display status for RE connections from dyn-filterd daemon";
       leaf conn-block-header {
         type string;
       }
       leaf conn-interface {
         type string;
       }
       leaf conn-count {
         type int32;
       }
       leaf conn-status {
         type string;
       }
       leaf conn-last-connect {
         type string;
       }
       leaf conn-last-failure {
         type string;
       }
       leaf conn-total-failure {
         type int32;
       }
       leaf conn-pkts-sent {
         type int32;
       }
       leaf conn-pkts-rcvd {
         type int32;
       }
     }
   }
   grouping aamw-statistics-block {
     leaf aamw-statistics-interested {
       type uint32;
     }
     leaf aamw-statistics-ignored {
       type uint32;
     }
     leaf aamw-statistics-blacklist-hit-counter {
       type uint32;
     }
     leaf aamw-statistics-whitelist-hit-counter {
       type uint32;
     }
     leaf aamw-statistics-total-session-actives {
       type uint32;
     }
     leaf aamw-statistics-http-session-actives {
       type uint32;
     }
     leaf aamw-statistics-https-session-actives {
       type uint32;
     }
     leaf aamw-statistics-smtp-session-actives {
       type uint32;
     }
     leaf aamw-statistics-smtps-session-actives {
       type uint32;
     }
     leaf aamw-statistics-imap-session-actives {
       type uint32;
     }
     leaf aamw-statistics-imaps-session-actives {
       type uint32;
     }
     leaf aamw-statistics-smb-session-actives {
       type uint32;
     }
     leaf aamw-statistics-total-session-blocked {
       type uint32;
     }
     leaf aamw-statistics-http-session-blocked {
       type uint32;
     }
     leaf aamw-statistics-https-session-blocked {
       type uint32;
     }
     leaf aamw-statistics-smtp-session-blocked {
       type uint32;
     }
     leaf aamw-statistics-smtps-session-blocked {
       type uint32;
     }
     leaf aamw-statistics-imap-session-blocked {
       type uint32;
     }
     leaf aamw-statistics-imaps-session-blocked {
       type uint32;
     }
     leaf aamw-statistics-smb-session-blocked {
       type uint32;
     }
     leaf aamw-statistics-total-session-permitted {
       type uint32;
     }
     leaf aamw-statistics-http-session-permitted {
       type uint32;
     }
     leaf aamw-statistics-https-session-permitted {
       type uint32;
     }
     leaf aamw-statistics-smtp-session-permitted {
       type uint32;
     }
     leaf aamw-statistics-smtps-session-permitted {
       type uint32;
     }
     leaf aamw-statistics-imap-session-permitted {
       type uint32;
     }
     leaf aamw-statistics-imaps-session-permitted {
       type uint32;
     }
     leaf aamw-statistics-smb-session-permitted {
       type uint32;
     }
     leaf aamw-statistics-total-file-submission-success {
       type uint32;
     }
     leaf aamw-statistics-http-file-submission-success {
       type uint32;
     }
     leaf aamw-statistics-https-file-submission-success {
       type uint32;
     }
     leaf aamw-statistics-smtp-file-submission-success {
       type uint32;
     }
     leaf aamw-statistics-smtps-file-submission-success {
       type uint32;
     }
     leaf aamw-statistics-imap-file-submission-success {
       type uint32;
     }
     leaf aamw-statistics-imaps-file-submission-success {
       type uint32;
     }
     leaf aamw-statistics-smb-file-submission-success {
       type uint32;
     }
     leaf aamw-statistics-total-file-submission-failure {
       type uint32;
     }
     leaf aamw-statistics-http-file-submission-failure {
       type uint32;
     }
     leaf aamw-statistics-https-file-submission-failure {
       type uint32;
     }
     leaf aamw-statistics-smtp-file-submission-failure {
       type uint32;
     }
     leaf aamw-statistics-smtps-file-submission-failure {
       type uint32;
     }
     leaf aamw-statistics-imap-file-submission-failure {
       type uint32;
     }
     leaf aamw-statistics-imaps-file-submission-failure {
       type uint32;
     }
     leaf aamw-statistics-smb-file-submission-failure {
       type uint32;
     }
     leaf aamw-statistics-total-file-submission-not-needed {
       type uint32;
     }
     leaf aamw-statistics-http-file-submission-not-needed {
       type uint32;
     }
     leaf aamw-statistics-https-file-submission-not-needed {
       type uint32;
     }
     leaf aamw-statistics-smtp-file-submission-not-needed {
       type uint32;
     }
     leaf aamw-statistics-smtps-file-submission-not-needed {
       type uint32;
     }
     leaf aamw-statistics-imap-file-submission-not-needed {
       type uint32;
     }
     leaf aamw-statistics-imaps-file-submission-not-needed {
       type uint32;
     }
     leaf aamw-statistics-smb-file-submission-not-needed {
       type uint32;
     }
     leaf aamw-statistics-total-file-verdict-meets_threshold {
       type uint32;
     }
     leaf aamw-statistics-http-file-verdict-meets_threshold {
       type uint32;
     }
     leaf aamw-statistics-https-file-verdict-meets_threshold {
       type uint32;
     }
     leaf aamw-statistics-smtp-file-verdict-meets_threshold {
       type uint32;
     }
     leaf aamw-statistics-smtps-file-verdict-meets_threshold {
       type uint32;
     }
     leaf aamw-statistics-imap-file-verdict-meets_threshold {
       type uint32;
     }
     leaf aamw-statistics-imaps-file-verdict-meets_threshold {
       type uint32;
     }
     leaf aamw-statistics-smb-file-verdict-meets_threshold {
       type uint32;
     }
     leaf aamw-statistics-total-file-verdict-under_threshold {
       type uint32;
     }
     leaf aamw-statistics-http-file-verdict-under_threshold {
       type uint32;
     }
     leaf aamw-statistics-https-file-verdict-under_threshold {
       type uint32;
     }
     leaf aamw-statistics-smtp-file-verdict-under_threshold {
       type uint32;
     }
     leaf aamw-statistics-smtps-file-verdict-under_threshold {
       type uint32;
     }
     leaf aamw-statistics-imap-file-verdict-under_threshold {
       type uint32;
     }
     leaf aamw-statistics-imaps-file-verdict-under_threshold {
       type uint32;
     }
     leaf aamw-statistics-smb-file-verdict-under_threshold {
       type uint32;
     }
     leaf aamw-statistics-total-file-fallback-blocked {
       type uint32;
     }
     leaf aamw-statistics-http-file-fallback-blocked {
       type uint32;
     }
     leaf aamw-statistics-https-file-fallback-blocked {
       type uint32;
     }
     leaf aamw-statistics-smtp-file-fallback-blocked {
       type uint32;
     }
     leaf aamw-statistics-smtps-file-fallback-blocked {
       type uint32;
     }
     leaf aamw-statistics-imap-file-fallback-blocked {
       type uint32;
     }
     leaf aamw-statistics-imaps-file-fallback-blocked {
       type uint32;
     }
     leaf aamw-statistics-smb-file-fallback-blocked {
       type uint32;
     }
     leaf aamw-statistics-total-fallback-block-service-not-ready {
       type uint32;
     }
     leaf aamw-statistics-http-fallback-block-service-not-ready {
       type uint32;
     }
     leaf aamw-statistics-https-fallback-block-service-not-ready {
       type uint32;
     }
     leaf aamw-statistics-smtp-fallback-block-service-not-ready {
       type uint32;
     }
     leaf aamw-statistics-smtps-fallback-block-service-not-ready {
       type uint32;
     }
     leaf aamw-statistics-imap-fallback-block-service-not-ready {
       type uint32;
     }
     leaf aamw-statistics-imaps-fallback-block-service-not-ready {
       type uint32;
     }
     leaf aamw-statistics-smb-fallback-block-service-not-ready {
       type uint32;
     }
     leaf aamw-statistics-total-fallback-block-out-of-resource {
       type uint32;
     }
     leaf aamw-statistics-http-fallback-block-out-of-resource {
       type uint32;
     }
     leaf aamw-statistics-https-fallback-block-out-of-resource {
       type uint32;
     }
     leaf aamw-statistics-smtp-fallback-block-out-of-resource {
       type uint32;
     }
     leaf aamw-statistics-smtps-fallback-block-out-of-resource {
       type uint32;
     }
     leaf aamw-statistics-imap-fallback-block-out-of-resource {
       type uint32;
     }
     leaf aamw-statistics-imaps-fallback-block-out-of-resource {
       type uint32;
     }
     leaf aamw-statistics-smb-fallback-block-out-of-resource {
       type uint32;
     }
     leaf aamw-statistics-total-fallback-block-content-size {
       type uint32;
     }
     leaf aamw-statistics-http-fallback-block-content-size {
       type uint32;
     }
     leaf aamw-statistics-https-fallback-block-content-size {
       type uint32;
     }
     leaf aamw-statistics-smtp-fallback-block-content-size {
       type uint32;
     }
     leaf aamw-statistics-smtps-fallback-block-content-size {
       type uint32;
     }
     leaf aamw-statistics-imap-fallback-block-content-size {
       type uint32;
     }
     leaf aamw-statistics-imaps-fallback-block-content-size {
       type uint32;
     }
     leaf aamw-statistics-smb-fallback-block-content-size {
       type uint32;
     }
     leaf aamw-statistics-total-fallback-block-timeout {
       type uint32;
     }
     leaf aamw-statistics-http-fallback-block-timeout {
       type uint32;
     }
     leaf aamw-statistics-https-fallback-block-timeout {
       type uint32;
     }
     leaf aamw-statistics-smtp-fallback-block-timeout {
       type uint32;
     }
     leaf aamw-statistics-smtps-fallback-block-timeout {
       type uint32;
     }
     leaf aamw-statistics-imap-fallback-block-timeout {
       type uint32;
     }
     leaf aamw-statistics-imaps-fallback-block-timeout {
       type uint32;
     }
     leaf aamw-statistics-smb-fallback-block-timeout {
       type uint32;
     }
     leaf aamw-statistics-total-fallback-block-unknown-file {
       type uint32;
     }
     leaf aamw-statistics-http-fallback-block-unknown-file {
       type uint32;
     }
     leaf aamw-statistics-https-fallback-block-unknown-file {
       type uint32;
     }
     leaf aamw-statistics-smtp-fallback-block-unknown-file {
       type uint32;
     }
     leaf aamw-statistics-smtps-fallback-block-unknown-file {
       type uint32;
     }
     leaf aamw-statistics-imap-fallback-block-unknown-file {
       type uint32;
     }
     leaf aamw-statistics-imaps-fallback-block-unknown-file {
       type uint32;
     }
     leaf aamw-statistics-smb-fallback-block-unknown-file {
       type uint32;
     }
     leaf aamw-statistics-total-file-fallback-permitted {
       type uint32;
     }
     leaf aamw-statistics-http-file-fallback-permitted {
       type uint32;
     }
     leaf aamw-statistics-https-file-fallback-permitted {
       type uint32;
     }
     leaf aamw-statistics-smtp-file-fallback-permitted {
       type uint32;
     }
     leaf aamw-statistics-smtps-file-fallback-permitted {
       type uint32;
     }
     leaf aamw-statistics-imap-file-fallback-permitted {
       type uint32;
     }
     leaf aamw-statistics-imaps-file-fallback-permitted {
       type uint32;
     }
     leaf aamw-statistics-smb-file-fallback-permitted {
       type uint32;
     }
     leaf aamw-statistics-total-fallback-permit-service-not-ready {
       type uint32;
     }
     leaf aamw-statistics-http-fallback-permit-service-not-ready {
       type uint32;
     }
     leaf aamw-statistics-https-fallback-permit-service-not-ready {
       type uint32;
     }
     leaf aamw-statistics-smtp-fallback-permit-service-not-ready {
       type uint32;
     }
     leaf aamw-statistics-smtps-fallback-permit-service-not-ready {
       type uint32;
     }
     leaf aamw-statistics-imap-fallback-permit-service-not-ready {
       type uint32;
     }
     leaf aamw-statistics-imaps-fallback-permit-service-not-ready {
       type uint32;
     }
     leaf aamw-statistics-smb-fallback-permit-service-not-ready {
       type uint32;
     }
     leaf aamw-statistics-total-fallback-permit-out-of-resource {
       type uint32;
     }
     leaf aamw-statistics-http-fallback-permit-out-of-resource {
       type uint32;
     }
     leaf aamw-statistics-https-fallback-permit-out-of-resource {
       type uint32;
     }
     leaf aamw-statistics-smtp-fallback-permit-out-of-resource {
       type uint32;
     }
     leaf aamw-statistics-smtps-fallback-permit-out-of-resource {
       type uint32;
     }
     leaf aamw-statistics-imap-fallback-permit-out-of-resource {
       type uint32;
     }
     leaf aamw-statistics-imaps-fallback-permit-out-of-resource {
       type uint32;
     }
     leaf aamw-statistics-smb-fallback-permit-out-of-resource {
       type uint32;
     }
     leaf aamw-statistics-total-fallback-permit-content-size {
       type uint32;
     }
     leaf aamw-statistics-http-fallback-permit-content-size {
       type uint32;
     }
     leaf aamw-statistics-https-fallback-permit-content-size {
       type uint32;
     }
     leaf aamw-statistics-smtp-fallback-permit-content-size {
       type uint32;
     }
     leaf aamw-statistics-smtps-fallback-permit-content-size {
       type uint32;
     }
     leaf aamw-statistics-imap-fallback-permit-content-size {
       type uint32;
     }
     leaf aamw-statistics-imaps-fallback-permit-content-size {
       type uint32;
     }
     leaf aamw-statistics-smb-fallback-permit-content-size {
       type uint32;
     }
     leaf aamw-statistics-total-fallback-permit-timeout {
       type uint32;
     }
     leaf aamw-statistics-http-fallback-permit-timeout {
       type uint32;
     }
     leaf aamw-statistics-https-fallback-permit-timeout {
       type uint32;
     }
     leaf aamw-statistics-smtp-fallback-permit-timeout {
       type uint32;
     }
     leaf aamw-statistics-smtps-fallback-permit-timeout {
       type uint32;
     }
     leaf aamw-statistics-imap-fallback-permit-timeout {
       type uint32;
     }
     leaf aamw-statistics-imaps-fallback-permit-timeout {
       type uint32;
     }
     leaf aamw-statistics-smb-fallback-permit-timeout {
       type uint32;
     }
     leaf aamw-statistics-total-fallback-permit-unknown-file {
       type uint32;
     }
     leaf aamw-statistics-http-fallback-permit-unknown-file {
       type uint32;
     }
     leaf aamw-statistics-https-fallback-permit-unknown-file {
       type uint32;
     }
     leaf aamw-statistics-smtp-fallback-permit-unknown-file {
       type uint32;
     }
     leaf aamw-statistics-smtps-fallback-permit-unknown-file {
       type uint32;
     }
     leaf aamw-statistics-imap-fallback-permit-unknown-file {
       type uint32;
     }
     leaf aamw-statistics-imaps-fallback-permit-unknown-file {
       type uint32;
     }
     leaf aamw-statistics-smb-fallback-permit-unknown-file {
       type uint32;
     }
     leaf aamw-statistics-total-file-ignored_by_sample_rate {
       type uint32;
     }
     leaf aamw-statistics-http-file-ignored_by_sample_rate {
       type uint32;
     }
     leaf aamw-statistics-https-file-ignored_by_sample_rate {
       type uint32;
     }
     leaf aamw-statistics-smtp-file-ignored_by_sample_rate {
       type uint32;
     }
     leaf aamw-statistics-smtps-file-ignored_by_sample_rate {
       type uint32;
     }
     leaf aamw-statistics-imap-file-ignored_by_sample_rate {
       type uint32;
     }
     leaf aamw-statistics-imaps-file-ignored_by_sample_rate {
       type uint32;
     }
     leaf aamw-statistics-smb-file-ignored_by_sample_rate {
       type uint32;
     }
     leaf aamw-statistics-total-email-scanned {
       type uint32;
     }
     leaf aamw-statistics-smtp-email-scanned {
       type uint32;
     }
     leaf aamw-statistics-smtps-email-scanned {
       type uint32;
     }
     leaf aamw-statistics-imap-email-scanned {
       type uint32;
     }
     leaf aamw-statistics-imaps-email-scanned {
       type uint32;
     }
     leaf aamw-statistics-total-email-permitted {
       type uint32;
     }
     leaf aamw-statistics-smtp-email-permitted {
       type uint32;
     }
     leaf aamw-statistics-smtps-email-permitted {
       type uint32;
     }
     leaf aamw-statistics-imap-email-permitted {
       type uint32;
     }
     leaf aamw-statistics-imaps-email-permitted {
       type uint32;
     }
     leaf aamw-statistics-total-email-blocked {
       type uint32;
     }
     leaf aamw-statistics-smtp-email-blocked {
       type uint32;
     }
     leaf aamw-statistics-smtps-email-blocked {
       type uint32;
     }
     leaf aamw-statistics-imap-email-blocked {
       type uint32;
     }
     leaf aamw-statistics-imaps-email-blocked {
       type uint32;
     }
     leaf aamw-statistics-total-email-tag-and-delivered {
       type uint32;
     }
     leaf aamw-statistics-smtp-email-tag-and-delivered {
       type uint32;
     }
     leaf aamw-statistics-smtps-email-tag-and-delivered {
       type uint32;
     }
     leaf aamw-statistics-imap-email-tag-and-delivered {
       type uint32;
     }
     leaf aamw-statistics-imaps-email-tag-and-delivered {
       type uint32;
     }
     leaf aamw-statistics-total-email-quarantined {
       type uint32;
     }
     leaf aamw-statistics-smtp-email-quarantined {
       type uint32;
     }
     leaf aamw-statistics-smtps-email-quarantined {
       type uint32;
     }
     leaf aamw-statistics-imap-email-quarantined {
       type uint32;
     }
     leaf aamw-statistics-imaps-email-quarantined {
       type uint32;
     }
     leaf aamw-statistics-total-email-fallback-blocked {
       type uint32;
     }
     leaf aamw-statistics-smtp-email-fallback-blocked {
       type uint32;
     }
     leaf aamw-statistics-smtps-email-fallback-blocked {
       type uint32;
     }
     leaf aamw-statistics-imap-email-fallback-blocked {
       type uint32;
     }
     leaf aamw-statistics-imaps-email-fallback-blocked {
       type uint32;
     }
     leaf aamw-statistics-total-email-fallback-block-service-not-ready {
       type uint32;
     }
     leaf aamw-statistics-smtp-email-fallback-block-service-not-ready {
       type uint32;
     }
     leaf aamw-statistics-smtps-email-fallback-block-service-not-ready {
       type uint32;
     }
     leaf aamw-statistics-imap-email-fallback-block-service-not-ready {
       type uint32;
     }
     leaf aamw-statistics-imaps-email-fallback-block-service-not-ready {
       type uint32;
     }
     leaf aamw-statistics-total-email-fallback-block-out-of-resource {
       type uint32;
     }
     leaf aamw-statistics-smtp-email-fallback-block-out-of-resource {
       type uint32;
     }
     leaf aamw-statistics-smtps-email-fallback-block-out-of-resource {
       type uint32;
     }
     leaf aamw-statistics-imap-email-fallback-block-out-of-resource {
       type uint32;
     }
     leaf aamw-statistics-imaps-email-fallback-block-out-of-resource {
       type uint32;
     }
     leaf aamw-statistics-total-email-fallback-block-content-size {
       type uint32;
     }
     leaf aamw-statistics-smtp-email-fallback-block-content-size {
       type uint32;
     }
     leaf aamw-statistics-smtps-email-fallback-block-content-size {
       type uint32;
     }
     leaf aamw-statistics-imap-email-fallback-block-content-size {
       type uint32;
     }
     leaf aamw-statistics-imaps-email-fallback-block-content-size {
       type uint32;
     }
     leaf aamw-statistics-total-email-fallback-block-timeout {
       type uint32;
     }
     leaf aamw-statistics-smtp-email-fallback-block-timeout {
       type uint32;
     }
     leaf aamw-statistics-smtps-email-fallback-block-timeout {
       type uint32;
     }
     leaf aamw-statistics-imap-email-fallback-block-timeout {
       type uint32;
     }
     leaf aamw-statistics-imaps-email-fallback-block-timeout {
       type uint32;
     }
     leaf aamw-statistics-total-email-fallback-block-unknown-file {
       type uint32;
     }
     leaf aamw-statistics-smtp-email-fallback-block-unknown-file {
       type uint32;
     }
     leaf aamw-statistics-smtps-email-fallback-block-unknown-file {
       type uint32;
     }
     leaf aamw-statistics-imap-email-fallback-block-unknown-file {
       type uint32;
     }
     leaf aamw-statistics-imaps-email-fallback-block-unknown-file {
       type uint32;
     }
     leaf aamw-statistics-total-email-fallback-permitted {
       type uint32;
     }
     leaf aamw-statistics-smtp-email-fallback-permitted {
       type uint32;
     }
     leaf aamw-statistics-smtps-email-fallback-permitted {
       type uint32;
     }
     leaf aamw-statistics-imap-email-fallback-permitted {
       type uint32;
     }
     leaf aamw-statistics-imaps-email-fallback-permitted {
       type uint32;
     }
     leaf aamw-statistics-total-email-fallback-permit-service-not-ready {
       type uint32;
     }
     leaf aamw-statistics-smtp-email-fallback-permit-service-not-ready {
       type uint32;
     }
     leaf aamw-statistics-smtps-email-fallback-permit-service-not-ready {
       type uint32;
     }
     leaf aamw-statistics-imap-email-fallback-permit-service-not-ready {
       type uint32;
     }
     leaf aamw-statistics-imaps-email-fallback-permit-service-not-ready {
       type uint32;
     }
     leaf aamw-statistics-total-email-fallback-permit-out-of-resource {
       type uint32;
     }
     leaf aamw-statistics-smtp-email-fallback-permit-out-of-resource {
       type uint32;
     }
     leaf aamw-statistics-smtps-email-fallback-permit-out-of-resource {
       type uint32;
     }
     leaf aamw-statistics-imap-email-fallback-permit-out-of-resource {
       type uint32;
     }
     leaf aamw-statistics-imaps-email-fallback-permit-out-of-resource {
       type uint32;
     }
     leaf aamw-statistics-total-email-fallback-permit-content-size {
       type uint32;
     }
     leaf aamw-statistics-smtp-email-fallback-permit-content-size {
       type uint32;
     }
     leaf aamw-statistics-smtps-email-fallback-permit-content-size {
       type uint32;
     }
     leaf aamw-statistics-imap-email-fallback-permit-content-size {
       type uint32;
     }
     leaf aamw-statistics-imaps-email-fallback-permit-content-size {
       type uint32;
     }
     leaf aamw-statistics-total-email-fallback-permit-timeout {
       type uint32;
     }
     leaf aamw-statistics-smtp-email-fallback-permit-timeout {
       type uint32;
     }
     leaf aamw-statistics-smtps-email-fallback-permit-timeout {
       type uint32;
     }
     leaf aamw-statistics-imap-email-fallback-permit-timeout {
       type uint32;
     }
     leaf aamw-statistics-imaps-email-fallback-permit-timeout {
       type uint32;
     }
     leaf aamw-statistics-total-email-fallback-permit-unknown-file {
       type uint32;
     }
     leaf aamw-statistics-smtp-email-fallback-permit-unknown-file {
       type uint32;
     }
     leaf aamw-statistics-smtps-email-fallback-permit-unknown-file {
       type uint32;
     }
     leaf aamw-statistics-imap-email-fallback-permit-unknown-file {
       type uint32;
     }
     leaf aamw-statistics-imaps-email-fallback-permit-unknown-file {
       type uint32;
     }
     leaf aamw-statistics-total-email-hit-whitelist {
       type uint32;
     }
     leaf aamw-statistics-smtp-email-hit-whitelist {
       type uint32;
     }
     leaf aamw-statistics-smtps-email-hit-whitelist {
       type uint32;
     }
     leaf aamw-statistics-imap-email-hit-whitelist {
       type uint32;
     }
     leaf aamw-statistics-imaps-email-hit-whitelist {
       type uint32;
     }
     leaf aamw-statistics-total-email-hit-blacklist {
       type uint32;
     }
     leaf aamw-statistics-smtp-email-blacklist {
       type uint32;
     }
     leaf aamw-statistics-smtps-email-blacklist {
       type uint32;
     }
     leaf aamw-statistics-imap-email-blacklist {
       type uint32;
     }
     leaf aamw-statistics-imaps-email-blacklist {
       type uint32;
     }
     leaf aamw-statistics-total-hash-eligible {
       type uint32;
     }
     leaf aamw-statistics-http-hash-eligible {
       type uint32;
     }
     leaf aamw-statistics-https-hash-eligible {
       type uint32;
     }
     leaf aamw-statistics-total-hash-selected {
       type uint32;
     }
     leaf aamw-statistics-http-hash-selected {
       type uint32;
     }
     leaf aamw-statistics-https-hash-selected {
       type uint32;
     }
     leaf aamw-statistics-total-hash-submitted {
       type uint32;
     }
     leaf aamw-statistics-http-hash-submitted {
       type uint32;
     }
     leaf aamw-statistics-https-hash-submitted {
       type uint32;
     }
     leaf aamw-statistics-total-hash-fail {
       type uint32;
     }
     leaf aamw-statistics-http-hash-fail {
       type uint32;
     }
     leaf aamw-statistics-https-hash-fail {
       type uint32;
     }
     leaf aamw-statistics-total-hash-known {
       type uint32;
     }
     leaf aamw-statistics-http-hash-known {
       type uint32;
     }
     leaf aamw-statistics-https-hash-known {
       type uint32;
     }
     leaf aamw-statistics-total-hash-unknown {
       type uint32;
     }
     leaf aamw-statistics-http-hash-unknown {
       type uint32;
     }
     leaf aamw-statistics-https-hash-unknown {
       type uint32;
     }
     leaf aamw-statistics-total-hash-verdict-timeout {
       type uint32;
     }
     leaf aamw-statistics-http-hash-verdict-timeout {
       type uint32;
     }
     leaf aamw-statistics-https-hash-verdict-timeout {
       type uint32;
     }
   }
   grouping aamw-redirect-files-block {
     leaf aamw-redirect-files-name {
       type string;
     }
     leaf aamw-redirect-files-size {
       type uint64;
     }
     leaf aamw-redirect-files-time {
       type string;
     }
     leaf aamw-redirect-file-content {
       type string;
     }
   }
   grouping aamw-policy-block {
     leaf aamw-policy-name {
       type string;
     }
     leaf aamw-used-profile-name {
       type string;
     }
     leaf aamw-applications {
       type string;
     }
     leaf aamw-verdict-number {
       type string;
     }
     leaf aamw-verdict-action {
       type string;
     }
     leaf aamw-verdict-notification {
       type string;
     }
     leaf aamw-default-notification {
       type string;
     }
     leaf aamw-whitelist-notification {
       type string;
     }
     leaf aamw-blacklist-notification {
       type string;
     }
     leaf aamw-policy-header {
       type string;
     }
     leaf aamw-fallback-action {
       type string;
     }
     leaf aamw-fallback-notification {
       type string;
     }
     leaf aamw-ml-scan-header {
       type string;
     }
     leaf aamw-ml-scan-action {
       type string;
     }
     leaf aamw-ml-scan-notification {
       type string;
     }
     leaf aamw-ml-default-notification {
       type string;
     }
     leaf aamw-protocol-name {
       type string;
     }
     leaf aamw-protocol-profile-name {
       type string;
     }
     leaf aamw-protocol-verdict-number {
       type string;
     }
     leaf aamw-protocol-verdict-action {
       type string;
     }
     leaf aamw-protocol-verdict-notification {
       type string;
     }
   }
   grouping aamw-profile-block {
     leaf aamw-profile-name {
       type string;
     }
     leaf aamw-profile-version {
       type uint32;
     }
     leaf aamw-profile-desc {
       type string;
     }
     leaf aamw-profile-disable_ftype {
       type string;
     }
     leaf aamw-profile-disable-category {
       type string;
     }
     leaf aamw-profile-category-sample {
       type string;
     }
   }
   grouping aamw-status-block {
     leaf aamw-server-hostname {
       type string;
     }
     leaf aamw-server-realm {
       type string;
     }
     leaf aamw-server-port {
       type uint32;
     }
     leaf aamw-proxy-hostname {
       type string;
     }
     leaf aamw-proxy-port {
       type string;
     }
     leaf aamw-detail-header1 {
       type string;
     }
     leaf aamw-connection-time {
       type string;
     }
     leaf aamw-connection-status {
       type string;
     }
     leaf aamw-detail-header2 {
       type string;
     }
     leaf aamw-card-info {
       type string;
     }
     leaf aamw-connection-active-number {
       type uint32;
     }
     leaf aamw-connection-failures {
       type uint32;
     }
   }
   grouping aamw-version-block {
     leaf aamw-version-email-config {
       type uint32;
     }
     leaf aamw-version-global-whitelist {
       type uint32;
     }
     leaf aamw-version-global-blacklist {
       type uint32;
     }
     leaf aamw-version-custom-whitelist {
       type uint32;
     }
     leaf aamw-version-custom-blacklist {
       type uint32;
     }
     leaf aamw-version-category-mapping {
       type uint32;
     }
     leaf aamw-version-ideneification-signature {
       type uint32;
     }
   }
   grouping appid-application-system-cache-information-block {
     leaf message {
       type string;
       description "CLI ouput message";
     }
     container appid-cache-configuration-usp {
       leaf appid-asc-usp-enable {
         type string;
         description "Show application cache (on|off)";
       }
       leaf appid-asc-security-services-enable {
         type string;
         description "Show security services application cache (on|off)";
       }
       leaf appid-asc-miscellaneous-services-enable {
         type string;
         description "Show miscellaneous services application cache (on|off)";
       }
       leaf appid-asc-cache-timeout {
         type uint32;
         description "Show cache entry timeout (seconds)";
       }
     }
     container appid-cache-configuration {
       leaf appid-asc-enable {
         type string;
         description "Show application cache (on|off)";
       }
       leaf appid-cache-timeout {
         type uint32;
         description "Show cache entry timeout (seconds)";
       }
       leaf appid-nested-asc-enable {
         type string;
         description "Show nested application cache (on|off)";
       }
       leaf appid-cache-unknown {
         type string;
         description "Show cache unknown result (on|off)";
       }
     }
     list appid-application-system-cache {
       leaf pic {
         type string;
         description "FPC index/PIC index";
       }
       leaf message {
         type string;
         description "CLI ouput message";
       }
       container asc-entry {
         leaf application-groups {
           type string;
           description "Application groups";
         }
         leaf virtual-system-identifier {
           type string;
           description "Virtual system identifier";
         }
         leaf ip-address {
           type jt:ipaddr;
           description "IP address in application system cache";
         }
         leaf port {
           type int32;
           description "Port number";
         }
         leaf protocol {
           type string;
         }
         leaf appid-application {
           type string;
           description "Application type";
         }
         leaf classification-path {
           type string;
           description "Application classification path";
         }
         leaf ipv6-address {
           type jt:ipv6addr;
           description "IPV6 address in application system cache";
         }
         leaf index {
           type int32;
           description "Index";
         }
       }
     }
     container appid-application-system-cache-pic {
       leaf pic {
         type string;
         description "FPC index/PIC index";
       }
       list appid-application-system-cache-usp {
         leaf application-groups {
           type string;
           description "Application groups";
         }
         leaf virtual-system-identifier {
           type string;
           description "Virtual system identifier";
         }
         leaf ipv6-address {
           type jt:ipv6addr;
           description "IPV6 address in application system cache";
         }
         leaf port {
           type int32;
           description "Port number";
         }
         leaf protocol {
           type string;
         }
         leaf appid-application {
           type string;
           description "Application type";
         }
         leaf is_encrypted {
           type string;
           description "Is Encrypted";
         }
         leaf classification-path {
           type string;
           description "Application classification path";
         }
         leaf ip-address {
           type jt:ipaddr;
           description "IP address in application system cache";
         }
         leaf index {
           type int32;
           description "Index";
         }
       }
     }
   }
   grouping appid-counter-information-block {
     leaf message {
       type string;
       description "CLI ouput message";
     }
     container logical-system-counters {
       container logical-system-counter {
         leaf logical-system {
           type uint32;
           description "Logical system name";
         }
         leaf tenant {
           type uint32;
           description "Tenant name";
         }
       }
       list appid-counter-usp {
         leaf counter-name {
           type string;
           description "Counter name";
         }
         leaf counter-value {
           type uint32;
           description "Counter value";
         }
         leaf pic {
           type string;
           description "FPC index/PIC index";
         }
       }
     }
     list appid-counter {
       leaf pic {
         type string;
         description "FPC index/PIC index";
       }
       leaf message {
         type string;
         description "CLI ouput message";
       }
       container counter {
         leaf counter-name {
           type string;
           description "Counter name";
         }
         leaf counter-value {
           type uint32;
           description "Counter value";
         }
       }
     }
   }
   grouping appid-commit-status-block {
     leaf appid-commit-status-detail {
       type string;
       description "Custom signatures commit status";
     }
   }
   grouping appid-application-statistics-information-block {
     container logical-system-app-stats {
       container logical-system-app {
         leaf logical-system {
           type uint32;
           description "Logical system name";
         }
         leaf tenant {
           type uint32;
           description "Tenant name";
         }
       }
       container last-reset-stats {
         leaf last-reset {
           type string;
           description "Last reset timestamp";
         }
         leaf elapsed-time {
           type string;
           description "Elapsed time";
         }
       }
       list appid-application-statistics-usp {
         leaf application-name {
           type string;
           description "Name of an application or nested application";
         }
         leaf sessions {
           type uint32;
           description "Sessions per application";
         }
         leaf bytes {
           type uint32;
           description "Byte count";
         }
         leaf is_encrypted {
           type string;
           description "Is Encrypted";
         }
         leaf sessions-final-match {
           type uint32;
           description "Final matched sessions per application";
         }
         leaf sessions-pre-match {
           type uint32;
           description "Pre matched sessions per application";
         }
         leaf sessions-limits-terminated {
           type uint32;
           description "Limits terminated sessions per application";
         }
       }
       list appid-application-statistics-detail-usp {
         leaf application-name {
           type string;
           description "Name of an application or nested application";
         }
         leaf is_encrypted {
           type string;
           description "Is Encrypted";
         }
         leaf sessions-final-match {
           type uint32;
           description "Final matched sessions per application";
         }
         leaf sessions-pre-match {
           type uint32;
           description "Pre matched sessions per application";
         }
         leaf sessions-limits-terminated {
           type uint32;
           description "Limits terminated sessions per application";
         }
       }
       list appid-application-statistics {
         leaf application-name {
           type string;
           description "Name of an application or nested application";
         }
         leaf sessions {
           type uint32;
           description "Sessions per application";
         }
         leaf bytes {
           type uint32;
           description "Byte count";
         }
       }
     }
   }
   grouping appid-application-group-statistics-information-block {
     container logical-system-group-stats {
       container logical-system-group {
         leaf logical-system {
           type uint32;
           description "Logical system name";
         }
         leaf tenant {
           type uint32;
           description "Tenant name";
         }
       }
       container last-reset-group-stats {
         leaf last-reset {
           type string;
           description "Last reset timestamp";
         }
         leaf elapsed-time {
           type string;
           description "Elapsed time";
         }
       }
       list appid-application-group-statistics {
         leaf application-name {
           type string;
           description "Name of an application or nested application";
         }
         leaf sessions {
           type uint32;
           description "Sessions per application";
         }
         leaf bytes {
           type uint32;
           description "Byte count";
         }
       }
     }
   }
   grouping appid-status-information-block {
     container appid-pic-status {
       description "Application identification status for PIC";
       leaf pic {
         type string;
         description "FPC index/PIC index";
       }
       leaf status-name {
         type string;
         description "Status name";
       }
       leaf status-value {
         type string;
         description "Status value";
       }
       list appid-module-status {
         container status {
           leaf status-name {
             type string;
             description "Status name";
           }
           leaf status-value {
             type string;
             description "Status value";
           }
         }
       }
       list appid-asc-status {
         container status {
           leaf status-name {
             type string;
             description "Status name";
           }
           leaf status-value {
             type string;
             description "Status value";
           }
         }
       }
       list appid-protobundle-status {
         container status {
           leaf status-name {
             type string;
             description "Status name";
           }
           leaf status-value {
             type string;
             description "Status value";
           }
         }
       }
       list appid-proxy-profile-status {
         container status {
           leaf status-name {
             type string;
             description "Status name";
           }
           leaf status-value {
             type string;
             description "Status value";
           }
         }
       }
       list appid-protobundle-slot1-status {
         container status {
           leaf status-name {
             type string;
             description "Status name";
           }
           leaf status-value {
             type string;
             description "Status value";
           }
         }
       }
       list appid-protobundle-slot2-status {
         container status {
           leaf status-name {
             type string;
             description "Status name";
           }
           leaf status-value {
             type string;
             description "Status value";
           }
         }
       }
       list appid-rollback-status {
         container status {
           leaf status-name {
             type string;
             description "Status name";
           }
           leaf status-value {
             type string;
             description "Status value";
           }
         }
       }
     }
   }
   grouping appid-package-version-block {
     leaf version-detail {
       type int32;
       description "Application package version";
     }
     leaf release-date {
       type string;
       description "Application package release date";
     }
     leaf version-name {
       type string;
       description "Version name";
     }
     leaf version-value {
       type string;
       description "Version value";
     }
     list appid-failed-version {
       container failed-version {
         leaf version-name {
           type string;
           description "Version name";
         }
         leaf version-value {
           type string;
           description "Version value";
         }
       }
     }
   }
   grouping appid-pkt-capture-counter-information-block {
     list pkt-capture-counter-pic {
       leaf pic {
         type string;
         description "FPC index/PIC index";
       }
       list pkt-capture-counter {
         leaf pkt-capture-counter-name {
           type string;
           description "Counter name ";
         }
         leaf pkt-capture-counter-value {
           type uint32;
           description "Counter value ";
         }
       }
     }
   }
   grouping recent-appid-sigpack-information-block {
     leaf-list recent-appid-sigpack-versions {
       type string;
       description "Appid Sigpack last-known-good versions";
     }
   }
   grouping ssl-statistics-block {
     container ssl-statistics-pic {
       leaf ssl-statistics-pic-info {
         type string;
       }
       leaf ssl-statistics-sessions-matched {
         type uint32;
       }
       leaf ssl-statistics-sessions-bypassed-non-ssl {
         type uint32;
       }
       leaf ssl-statistics-sessions-bypassed-mem-overflow {
         type uint32;
       }
       leaf ssl-statistics-sessions-bypassed-low-memory {
         type uint32;
       }
       leaf ssl-statistics-sessions-created {
         type uint32;
       }
       leaf ssl-statistics-sessions-ignored {
         type uint32;
       }
       leaf ssl-statistics-sessions-active {
         type uint32;
       }
       leaf ssl-statistics-sessions-dropped {
         type uint32;
       }
       leaf ssl-statistics-sessions-whitelisted {
         type uint32;
       }
       leaf ssl-statistics-whitelisted-url-category-match {
         type uint32;
       }
       leaf ssl-statistics-sessions-default-profile-hit {
         type uint32;
       }
       leaf ssl-statistics-sessions-dropped-no-default-profile {
         type uint32;
       }
       leaf ssl-statistics-sessions-potential-policy-conflict {
         type uint32;
       }
     }
   }
   grouping ssl-status-block {
     container ssl-status-pic {
       leaf ssl-status-pic-info {
         type string;
       }
       leaf ssl-status-one-crypto {
         type string;
       }
       leaf ssl-status-async-crypto {
         type string;
       }
       leaf ssl-status-proxy-activation {
         type string;
       }
       leaf ssl-status-force-enable-jdpi-service {
         type string;
       }
       leaf ssl-status-local-logging {
         type string;
       }
       leaf ssl-status-sslfp-pkid-link-status {
         type string;
       }
       leaf ssl-status-deferred-profile-selection {
         type string;
       }
       leaf ssl-status-cert-cache-activated {
         type string;
       }
       leaf ssl-status-invalidate-cert-cache-on-crl-update {
         type string;
       }
       leaf ssl-status-max-cert-cache-nodes {
         type uint32;
       }
       leaf ssl-status-cert-nodes-in-use {
         type uint32;
       }
       leaf ssl-status-sess-cache-activated {
         type string;
       }
       leaf ssl-status-max-sess-cache-nodes {
         type uint32;
       }
       leaf ssl-status-sess-nodes-in-use {
         type uint32;
       }
     }
   }
   grouping ssl-counters-block {
     leaf ssl-counters-lsys-name {
       type string;
     }
     list ssl-counters-pic {
       leaf ssl-counters-pic-info {
         type string;
       }
       container ssl-counters-info {
         leaf ssl-counters-name {
           type string;
         }
         leaf ssl-counters-value {
           type uint32;
         }
       }
     }
   }
   grouping ssl-profile-list-block {
     leaf ssl-profile-list-lsys-name {
       type string;
     }
     container ssl-profile-list-pic {
       leaf ssl-profile-list-pic-info {
         type string;
       }
       leaf ssl-profile-id {
         type uint32;
       }
       leaf ssl-profile-name {
         type string;
       }
     }
   }
   grouping ssl-profile-detail-block {
     leaf ssl-profile-detail-lsys-name {
       type string;
     }
     container ssl-profile-detail-pic {
       leaf ssl-profile-detail-pic-info {
         type string;
       }
       leaf ssl-profile-profile {
         type string;
       }
       leaf ssl-profile-trace {
         type string;
       }
       leaf ssl-profile-root-ca {
         type string;
       }
       leaf ssl-profile-allow-non-ssl-session {
         type string;
       }
       leaf ssl-profile-termination-profile-id {
         type uint32;
       }
       leaf ssl-profile-initiation-profile-id {
         type uint32;
       }
       leaf ssl-profile-nof-whitelist-entries {
         type uint32;
       }
       leaf ssl-profile-supported-protocol-version {
         type string;
       }
     }
   }
   grouping ssl-proxy-sess-cache-entries-block {
     leaf ssl-proxy-sess-cache-entries-lsys-name {
       type string;
     }
     container ssl-proxy-sess-cache-entries-pic {
       leaf ssl-proxy-sess-cache-entries-pic-info {
         type string;
       }
       leaf ssl-proxy-sess-cache-hash-entry {
         type uint32;
       }
       leaf ssl-proxy-sess-cache-status {
         type string;
       }
       leaf ssl-proxy-sess-cache-key {
         type string;
       }
       leaf ssl-proxy-sess-cache-sess-id-len {
         type uint32;
       }
       leaf ssl-proxy-sess-cache-sess-id {
         type string;
       }
       leaf ssl-proxy-sess-cache-dest-ip {
         type string;
       }
       leaf ssl-proxy-sess-cache-dest-port {
         type uint32;
       }
       leaf ssl-proxy-sess-cache-term-profile-id {
         type uint32;
       }
       leaf ssl-proxy-sess-cache-init-profile-id {
         type uint32;
       }
       leaf ssl-proxy-ssl-t-resumption-type {
         type string;
       }
       leaf ssl-proxy-ssl-i-resumption-type {
         type string;
       }
       leaf ssl-proxy-sess-cache-interdicted-cert-type {
         type string;
       }
       leaf ssl-proxy-sess-cache-server-cert-verification-result {
         type string;
       }
       leaf ssl-proxy-sess-cache-server-name-extn-len {
         type uint32;
       }
       leaf ssl-proxy-sess-cache-server-name-extn-name {
         type string;
       }
       leaf ssl-proxy-sess-cache-server-cert-chain-hash {
         type string;
       }
       leaf ssl-proxy-sess-cache-term-ssl-version {
         type uint32;
       }
       leaf ssl-proxy-sess-cache-term-compression-method {
         type int32;
       }
       leaf ssl-proxy-sess-cache-term-cipher-id {
         type uint32;
       }
       leaf ssl-proxy-sess-cache-term-master-key-len {
         type uint32;
       }
       leaf ssl-proxy-sess-cache-init-ssl-version {
         type uint32;
       }
       leaf ssl-proxy-sess-cache-init-compression-method {
         type uint32;
       }
       leaf ssl-proxy-sess-cache-init-cipher-id {
         type uint32;
       }
       leaf ssl-proxy-sess-cache-init-master-key-len {
         type uint32;
       }
       leaf ssl-proxy-ssli-tick-validity {
         type string;
       }
       leaf ssl-proxy-ssli-tick-lifetime-hint {
         type uint32;
       }
       leaf ssl-proxy-ssli-tick-age-add {
         type uint32;
       }
       leaf ssl-proxy-ssli-tick-len {
         type uint32;
       }
       leaf ssl-proxy-sess-cache-stale-entries {
         type uint32;
       }
     }
   }
   grouping ssl-proxy-sess-cache-statistics-block {
     leaf ssl-proxy-sess-cache-statistics-lsys-name {
       type string;
     }
     container ssl-proxy-sess-cache-statistics-pic {
       leaf ssl-proxy-sess-cache-statistics-pic-info {
         type string;
       }
       leaf ssl-proxy-sess-cache-statistics-sess-cache-hit {
         type uint32;
       }
       leaf ssl-proxy-sess-cache-statistics-sess-cache-miss {
         type uint32;
       }
       leaf ssl-proxy-sess-cache-statistics-sess-cache-activation-flr {
         type uint32;
       }
       leaf ssl-proxy-sess-cache-statistics-sess-cache-full {
         type uint32;
       }
     }
   }
   grouping ssl-proxy-cert-cache-entries-block {
     leaf ssl-proxy-cert-cache-entries-lsys-name {
       type string;
     }
     container ssl-proxy-cert-cache-entries-pic {
       leaf ssl-proxy-cert-cache-entries-pic-info {
         type string;
       }
       leaf ssl-proxy-cert-cache-entry {
         type uint32;
       }
       leaf ssl-proxy-cert-cache-key {
         type string;
       }
       leaf ssl-proxy-cert-cache-serial-number {
         type string;
       }
       leaf ssl-proxy-cert-cache-init-profile-id {
         type uint32;
       }
       leaf ssl-proxy-cert-cache-num-of-crl-update {
         type uint32;
       }
       leaf ssl-proxy-cert-cache-status {
         type string;
       }
       leaf ssl-proxy-cert-cache-interdicted-cert-type {
         type string;
       }
       leaf ssl-proxy-cert-cache-server-cert-verification-result {
         type string;
       }
       leaf ssl-proxy-cert-cache-cert-ref-count {
         type uint32;
       }
       leaf ssl-proxy-cert-cache-subject {
         type string;
       }
       leaf ssl-proxy-cert-cache-issuer {
         type string;
       }
     }
   }
   grouping ssl-proxy-cert-cache-statistics-block {
     leaf ssl-proxy-cert-cache-statistics-lsys-name {
       type string;
     }
     container ssl-proxy-cert-cache-statistics-pic {
       leaf ssl-proxy-cert-cache-statistics-pic-info {
         type string;
       }
       leaf ssl-proxy-cert-cache-statistics-sess-cache-hit {
         type uint32;
       }
       leaf ssl-proxy-cert-cache-statistics-sess-cache-miss {
         type uint32;
       }
       leaf ssl-proxy-cert-cache-statistics-sess-cache-activation-flr {
         type uint32;
       }
       leaf ssl-proxy-cert-cache-statistics-sess-cache-full {
         type uint32;
       }
     }
   }
   grouping ssl-certificate-block {
     leaf ssl-certificate-lsys-name {
       type string;
     }
     container ssl-certificate-pic {
       leaf ssl-certificate-pic-info {
         type string;
       }
       leaf ssl-cert-id {
         type uint32;
       }
     }
   }
   grouping ssl-certificate-id-detail-block {
     leaf ssl-certificate-id-detail-lsys-name {
       type string;
     }
     container ssl-certificate-id-detail-pic {
       leaf ssl-certificate-id-detail-pic-info {
         type string;
       }
       container ssl-certificate-id-detail-info {
         leaf ssl-certificate-id {
           type string;
         }
         leaf ssl-cert-type {
           type string;
         }
         leaf ssl-issuer {
           type string;
         }
         leaf ssl-subject {
           type string;
         }
         leaf ssl-validity {
           type string;
         }
         leaf ssl-validity-not-before {
           type string;
         }
         leaf ssl-validity-not-after {
           type string;
         }
         leaf ssl-public-key-algorithm {
           type string;
         }
         leaf ssl-cert-modify-time {
           type string;
         }
         leaf ssl-key-modify-time {
           type string;
         }
         leaf ssl-certificate-version {
           type uint32;
         }
         leaf ssl-serial-number {
           type string;
         }
         leaf ssl-signature-algorithm {
           type string;
         }
         leaf ssl-crl {
           type string;
         }
         leaf ssl-crl-present {
           type string;
         }
         leaf ssl-crl-check {
           type string;
         }
         leaf ssl-crl-download-failed {
           type string;
         }
         leaf ssl-crl-check-on-download-failed {
           type string;
         }
       }
     }
   }
   grouping ssl-term-profile-detail-block {
     leaf ssl-term-profile-detail-lsys-name {
       type string;
     }
     container ssl-term-profile-detail-pic {
       leaf ssl-term-profile-detail-pic-info {
         type string;
       }
       leaf ssl-term-profile-detail-profile {
         type string;
       }
       leaf ssl-term-profile-detail-allow-non-ssl-sess {
         type string;
       }
       leaf ssl-term-profile-detail-preferred-ciphers {
         type string;
       }
       leaf ssl-term-profile-detail-nof-url-categories-conf {
         type uint32;
       }
       leaf ssl-term-profile-detail-protocol-version {
         type string;
       }
       leaf ssl-term-profile-detail-client-auth {
         type string;
       }
       leaf ssl-term-profile-detail-server-auth {
         type string;
       }
       leaf ssl-term-profile-detail-crypto-mode {
         type string;
       }
       leaf ssl-term-profile-detail-sess-resumption {
         type string;
       }
       leaf ssl-term-profile-detail-crl-check {
         type string;
       }
       leaf ssl-term-profile-detail-cert-rsa {
         type string;
       }
       leaf ssl-term-profile-detail-cert-ecdsa {
         type string;
       }
       leaf ssl-term-profile-detail-renegotiation {
         type string;
       }
       leaf ssl-term-profile-detail-custom-ciphers {
         type string;
       }
       leaf ssl-term-profile-detail-server-cert {
         type string;
       }
       leaf ssl-term-profile-detail-decrypt-mirror {
         type string;
       }
       leaf ssl-term-profile-detail-trusted-ca {
         type string;
       }
       leaf ssl-term-profile-detail-cert-chain-rsa-cert {
         type string;
       }
       leaf ssl-term-profile-detail-chain-ca-of-rsa-cert {
         type uint32;
       }
       leaf ssl-term-profile-detail-cert-chain-ecc-cert {
         type string;
       }
       leaf ssl-term-profile-detail-chain-ca-of-ecc-cert {
         type uint32;
       }
       list ssl-term-profile-detail-status {
         leaf ssl-term-profile-detail-status-counter-name {
           type string;
         }
         leaf ssl-term-profile-detail-status-counter-value {
           type uint32;
         }
       }
     }
   }
   grouping ssl-session-block {
     leaf ssl-session-lsys-name {
       type string;
     }
     leaf ssl-session-pic-info {
       type string;
     }
     leaf ssl-session-session-id {
       type uint32;
     }
     leaf ssl-session-connection-type {
       type string;
     }
     leaf ssl-session-ssl-profile {
       type string;
     }
     leaf ssl-session-early-dynapp-profile {
       type string;
     }
     leaf ssl-session-http-proxy-session {
       type string;
     }
     leaf ssl-session-swg-session {
       type string;
     }
     leaf ssl-session-init-sni {
       type string;
     }
     leaf ssl-session-resumed-session {
       type string;
     }
     leaf ssl-session-one-crypto {
       type string;
     }
     leaf ssl-session-async-crypto {
       type string;
     }
     leaf ssl-session-reneg-count {
       type uint32;
     }
     leaf ssl-session-cert {
       type string;
     }
     leaf ssl-session-cert-status {
       type string;
     }
     leaf ssl-session-cert-crl-check {
       type string;
     }
     leaf ssl-session-cert-action {
       type string;
     }
     leaf ssl-session-authentication {
       type string;
     }
     leaf ssl-session-term-key-size {
       type uint32;
     }
     leaf ssl-session-term-cipher {
       type string;
     }
     leaf ssl-session-term-tls-version {
       type uint32;
     }
     leaf ssl-session-init-key-size {
       type uint32;
     }
     leaf ssl-session-init-cipher {
       type string;
     }
     leaf ssl-session-init-tls-version {
       type uint32;
     }
   }
   grouping ssl-droplog-block {
     leaf ssl-droplog-lsys-name {
       type string;
     }
     container ssl-droplog-pic {
       leaf ssl-droplog-pic-info {
         type string;
       }
       leaf ssl-droplog-msg {
         type string;
       }
     }
   }
   grouping icap-redir-statistics-block {
     list icap-redir-statistics-ldom {
       description "Show ICAP redirect statistics of a logical-system or tenant";
       leaf icap-redir-statistics-msg-redirected {
         type uint64;
       }
       leaf icap-redir-statistics-msg-reqmod-redirected {
         type uint64;
       }
       leaf icap-redir-statistics-msg-respmod-redirected {
         type uint64;
       }
       leaf icap-redir-statistics-msg-received {
         type uint64;
       }
       leaf icap-redir-statistics-msg-reqmod-received {
         type uint64;
       }
       leaf icap-redir-statistics-msg-respmod-received {
         type uint64;
       }
       leaf icap-redir-statistics-fb-tmo-permit {
         type uint64;
       }
       leaf icap-redir-statistics-fb-tmo-log-permit {
         type uint64;
       }
       leaf icap-redir-statistics-fb-tmo-reject {
         type uint64;
       }
       leaf icap-redir-statistics-fb-conn-permit {
         type uint64;
       }
       leaf icap-redir-statistics-fb-conn-log-permit {
         type uint64;
       }
       leaf icap-redir-statistics-fb-conn-reject {
         type uint64;
       }
       leaf icap-redir-statistics-fb-deft-permit {
         type uint64;
       }
       leaf icap-redir-statistics-fb-deft-log-permit {
         type uint64;
       }
       leaf icap-redir-statistics-fb-deft-reject {
         type uint64;
       }
       leaf icap-redir-statistics-clear {
         type string;
         description "Clear ICAP redirect statistics";
       }
       leaf icap-redir-logical-system {
         type string;
         description "Logical system name";
       }
       leaf icap-redir-tenant {
         type string;
         description "Tenant name";
       }
     }
   }
   grouping icap-redir-status-block {
     list icap-redir-status-ldom {
       description "Show ICAP redirect profile status of a logical-system or tenant";
       leaf icap-redir-profile-status {
         type string;
       }
       leaf icap-redir-logical-system {
         type string;
         description "Logical system name";
       }
       leaf icap-redir-tenant {
         type string;
         description "Tenant name";
       }
     }
   }
   grouping show-ids-whitelist-block {
     list ids-logical-system {
       description "Logical system";
       leaf name {
         type string;
         description "Logical system name";
       }
     }
     list ids-wlist-status {
       leaf ids-wlist-addr {
         type jt:ipprefix;
         description "IP address";
       }
     }
   }
   grouping show-ids-status-block {
     leaf ids-description {
       type string;
       description "Description of screen";
     }
     list ids-logical-system {
       description "Logical system";
       leaf name {
         type string;
         description "Logical system name";
       }
     }
     container ids-status-header {
       leaf ids-status-header-name {
         type string;
         description "Name of header";
       }
       leaf ids-status-header-value {
         type string;
         description "Name of value";
       }
     }
     list ids-status {
       leaf ids-status-name {
         type string;
         description "Name of IDS configure";
       }
       leaf ids-status-value {
         type uint32;
         description "Configure value";
       }
     }
     list ids-white-list {
       leaf white-list-name {
         type string;
         description "Name of white list";
       }
       leaf ids-address {
         type jt:ipprefix;
         description "IP address";
       }
     }
     list ids-udp-wlist {
       leaf udp-wlist-string-name {
         type string;
         description "Name of white list string";
       }
       leaf udp-wlist-name {
         type string;
         description "Name of white list";
       }
     }
     list ids-ipblockfrag-wlist {
       leaf ipblockfrag-wlist-string-name {
         type string;
         description "Name of white list string";
       }
       leaf ipblockfrag-wlist-name {
         type string;
         description "Name of white list";
       }
     }
   }
   grouping service-set-packet-drop-statistics-block {
     container service-set-packet-drops {
       leaf interface-name {
         type string;
         description "Name of the adaptive services interface";
       }
       leaf service-set-name {
         type string;
         description "Name of the service set";
       }
       leaf cpulimit-drops {
         type uint32;
         description "Drops because CPU usage limit is reached";
       }
       leaf memlimit-drops {
         type uint32;
         description "Drops because Memory usage limit is reached";
       }
       leaf flowlimit-drops {
         type uint32;
         description "Drops because Flow limit is reached";
       }
       leaf tcpalg-drops {
         type uint32;
         description "Drops because tcp alg control packet is too big";
       }
     }
   }
   grouping service-set-drop-flow-statistics-block {
     container service-set-drop-flows {
       leaf interface-name {
         type string;
         description "Name of the adaptive services interface";
       }
       leaf service-set-name {
         type string;
         description "Name of the service set";
       }
       leaf current-ingress-drop-flow {
         type uint32;
         description "Current number of ingress drop flows";
       }
       leaf current-egress-drop-flow {
         type uint32;
         description "Current number of egress drop flows";
       }
       leaf pkt-drop-exceed-ingress-drop-flow-limit {
         type uint32;
         description "Number of packets dropped due to ingress drop flow limit";
       }
       leaf pkt-drop-exceed-egress-drop-flow-limit {
         type uint32;
         description "Number of packets dropped due to egress drop flow limit";
       }
     }
   }
   grouping service-set-integrity-drops-statistics-block {
     container service-set-integrity-drops-entry {
       leaf interface-name {
         type string;
         description "Name of the adaptive services interface";
       }
       list sset-integrity-drops-service-set-entry {
         leaf service-set-name {
           type string;
           description "Name of the service set";
         }
         container error-counters {
           leaf ip-errors {
             type uint32;
             description "IP processing errors";
           }
           leaf tcp-errors {
             type uint32;
             description "TCP processing errors";
           }
           leaf udp-errors {
             type uint32;
             description "UDP processing errors";
           }
           leaf icmp-errors {
             type uint32;
             description "ICMP processing errors";
           }
           leaf non-ip-packets {
             type uint32;
             description "Non-IP packets";
           }
           leaf alg-errors {
             type uint32;
             description "ALG processing errors";
           }
         }
         container ip-error-counters {
           leaf ip-length-error {
             type uint32;
             description "IP packet length inconsistencies";
           }
           leaf ip-header-length-error {
             type uint32;
             description "Minimum IP header length check failures";
           }
           leaf long-packet {
             type uint32;
             description "Reassembled packet exceeds maximum IP length (65,535 bytes)";
           }
           leaf illegal-destination-address {
             type uint32;
             description "Illegal destination address";
           }
           leaf illegal-source-address {
             type uint32;
             description "Illegal source address";
           }
           leaf ttl-zero {
             type uint32;
             description "IP packets received with a TTL value of 0";
           }
           leaf illegal-ip-protocol {
             type uint32;
             description "Illegal IP protocol number ";
           }
           leaf non-ipv6 {
             type uint32;
             description "Non-IPv6 packets";
           }
           leaf land-attack {
             type uint32;
             description "IP source address same as destination address";
           }
           leaf not-ip-packet {
             type uint32;
             description "Not IP Packet";
           }
           leaf non-ipv4 {
             type uint32;
             description "Non-IPv4 packets";
           }
           leaf bad-checksum {
             type uint32;
             description "Bad checksum";
           }
           leaf illegal-fragment-length {
             type uint32;
             description "Illegal IP fragment length";
           }
           leaf fragment-overlap {
             type uint32;
             description "IP fragment overlap";
           }
           leaf fragment-reassembly-timeout {
             type uint32;
             description "IP fragment reassembly timeout";
           }
           leaf fragment-limit-exceeded {
             type uint32;
             description "IP fragment limit exceeded";
           }
           leaf unknown {
             type uint32;
             description "Unknown errors";
           }
         }
         container tcp-error-counters {
           leaf tcp-header-length-error {
             type uint32;
             description "TCP header length inconsistencies";
           }
           leaf tcp-zero-port {
             type uint32;
             description "Source or destination port number is zero";
           }
           leaf illegal-sequence-number-flags {
             type uint32;
             description "Illegal sequence number and flags combinations";
           }
           leaf syn-attack {
             type uint32;
             description "SYN attack";
           }
           leaf non-syn-first-packet {
             type uint32;
             description "First packet not a SYN message";
           }
           leaf tcp-port-scan {
             type uint32;
             description "TCP port scan";
           }
           leaf bad-syn-cookie-response {
             type uint32;
             description "Bad SYN cookie response";
           }
           leaf tcp-recon-sequence-number-error {
             type uint32;
             description "TCP reconstructor sequence number error";
           }
           leaf tcp-recon-retransmits {
             type uint32;
             description "TCP reconstructor retransmissions";
           }
           leaf tcp-partially-opened-connection-timeout-syn-rcvd {
             type uint32;
             description "TCP partially opened connection timeout";
           }
           leaf tcp-partially-opened-connection-timeout-syn-ack-rcvd {
             type uint32;
             description "TCP partially opened connection timeout";
           }
           leaf tcp-partially-closed-connection-reuse {
             type uint32;
             description "TCP partially closed connection reuse";
           }
           leaf tcp-3way-error-client-sent-syn-ack {
             type uint32;
             description "TCP 3-way error - client sent SYN+ACK";
           }
           leaf tcp-3way-error-server-sent-ack {
             type uint32;
             description "TCP 3-way error - server sent ACK";
           }
           leaf tcp-3way-error-syn-seq-num-retrans-mismatch {
             type uint32;
             description "TCP 3-way error - SYN seq number retransmission mismatch";
           }
           leaf tcp-3way-error-rst-seq-num-mismatch {
             type uint32;
             description "TCP 3-way error - RST seq number mismatch";
           }
           leaf tcp-3way-error-fin-received {
             type uint32;
             description "TCP 3-way error - FIN received";
           }
           leaf tcp-3way-error-invalid-flags {
             type uint32;
             description "TCP 3-way error - invalid TCP flag combination";
           }
           leaf tcp-3way-error-syn-no-flow-initiator {
             type uint32;
             description "TCP 3-way error - SYN recvd but no client flows";
           }
           leaf tcp-3way-error-first-packet-syn-ack {
             type uint32;
             description "TCP 3-way error - first packet SYN+ACK";
           }
           leaf tcp-3way-error-first-packet-fin-ack {
             type uint32;
             description "TCP 3-way error - first packet FIN+ACK";
           }
           leaf tcp-3way-error-first-packet-fin {
             type uint32;
             description "TCP 3-way error - first packet FIN";
           }
           leaf tcp-3way-error-first-packet-rst {
             type uint32;
             description "TCP 3-way error - first packet RST";
           }
           leaf tcp-3way-error-first-packet-ack {
             type uint32;
             description "TCP 3-way error - first packet ack";
           }
           leaf tcp-3way-error-first-packet-invalid-flags {
             type uint32;
             description "TCP 3-way error - first packet ack";
           }
           leaf tcp-close-error-no-final-ack {
             type uint32;
             description "TCP close error - no final ack";
           }
           leaf tcp-resumed-flow {
             type uint32;
             description "TCP Resumed Flow";
           }
         }
         container udp-error-counters {
           leaf udp-header-length-error {
             type uint32;
             description "IP data length is less than minimum UDP header length (8 bytes)";
           }
           leaf udp-zero-port {
             type uint32;
             description "Source or destination port number is zero";
           }
           leaf udp-port-scan {
             type uint32;
             description "UDP port scan (ICMP error seen for UDP flow)";
           }
         }
         container icmp-error-counters {
           leaf icmp-length-error {
             type uint32;
             description "IP data length less than minimum ICMP header length (8 bytes)";
           }
           leaf icmp-error-length-error {
             type uint32;
             description "ICMP error length inconsistencies";
           }
           leaf ping-duplicate-sequence-number {
             type uint32;
             description "Duplicate ping sequence number";
           }
           leaf ping-mismatched-sequence-number {
             type uint32;
             description "Mismatched ping sequence number";
           }
           leaf icmp-error-no-matching-flow {
             type uint32;
             description "No matching flow for ICMP error packet";
           }
         }
       }
     }
   }
   grouping msp-service-set-tcp-statistics-block {
     container msp-service-set-tcp-statistics-entry {
       leaf interface-name {
         type string;
         description "Name of the adaptive services interface";
       }
       list msp-sset-tcp-statistics-service-set-entry {
         leaf service-set-name {
           type string;
           description "Name of the service set";
         }
         container tcp-open-close-counters {
           leaf tcp-first-pkt-not-syn {
             type uint32;
             description "TCP first packet non-syn";
           }
           leaf tcp-first-pkt-rst {
             type uint32;
             description "TCP first packet reset";
           }
           leaf tcp-first-pkt-fin {
             type uint32;
             description "TCP first packet FIN";
           }
           leaf tcp-non-syn-discard {
             type uint32;
             description "TCP non syn discard";
           }
           leaf tcp-ext-alloc-fail {
             type uint32;
             description "TCP extension alloc fail";
           }
           leaf tfo-syn-with-cookie-req {
             type uint32;
             description "TFO SYN with cookie request";
           }
           leaf tfo-syn-with-cookie {
             type uint32;
             description "TFO SYN with cookie";
           }
           leaf tfo-syn-ack-with-cookie {
             type uint32;
             description "TFO SYN ACK with cookie";
           }
           leaf tfo-packets-forwarded {
             type uint32;
             description "TFO packets forwarded";
           }
           leaf tfo-packets-dropped {
             type uint32;
             description "TFO packets dropped";
           }
           leaf tfo-packets-stripped {
             type uint32;
             description "TFO packets stripped";
           }
         }
         container tcp-sequence-error-counters {
           leaf tcp-invalid-syn-ack {
             type uint32;
             description "TCP invalid syn ack";
           }
           leaf tcp-invalid-ack-win-check {
             type uint32;
             description "TCP invalid ack window check";
           }
           leaf tcp-invalid-xmit-syn {
             type uint32;
             description "TCP invalid syn transmit";
           }
           leaf tcp-invalid-rst-in-listen {
             type uint32;
             description "TCP invalid reset in listen";
           }
           leaf tcp-invalid-rst-in-syn-recv {
             type uint32;
             description "TCP invalid reset in syn received";
           }
           leaf tcp-invalid-rst-in-syn-sent {
             type uint32;
             description "TCP invalid reset in syn sent";
           }
           leaf tcp-invalid-flags-handshake {
             type uint32;
             description "TCP invalid flags handshake";
           }
           leaf tcp-reverse-flow-null-first-pkt-non-syn {
             type uint32;
             description "TCP reverse flow is null and first packet is not syn";
           }
           leaf tcp-reverse-flow-null {
             type uint32;
             description "TCP reverse flow null";
           }
         }
       }
     }
   }
   grouping service-set-tcp-mss-statistics-block {
     list service-set-tcp-mss {
       description "TCP MSS statistics";
       leaf interface-name {
         type string;
         description "Name of the adaptive services interface";
       }
       leaf service-set-name {
         type string;
         description "Name of the service set";
       }
       leaf syn-received {
         type uint32;
         description "Number of SYN packets received for the service set";
       }
       leaf syn-modified {
         type uint32;
         description "Number of SYN packets whose MSS setting was modified";
       }
     }
   }
   grouping syslog-stats-interface-block {
     leaf syslog-stats-interface-name {
       type string;
       description "Interface name";
     }
     leaf syslog-stats-interface-rate-limit {
       type uint32;
       description "Maximum syslog messages per seconds allowed";
     }
   }
   grouping jflow-log-stats-interface-block {
     leaf jflow-log-stats-interface-name {
       type string;
       description "Interface name";
     }
   }
   grouping security-log-profile-template-block {
     leaf-list entry {
       type string;
     }
   }
   grouping security-log-profile-config-block {
     leaf-list entry {
       type string;
     }
   }
   grouping service-set-memory-statistics-information-block {
     list service-set-memory-statistics {
       description "Memory usage statistics";
       leaf interface-name {
         type string;
         description "Name of the adaptive services interface";
       }
       leaf service-set-name {
         type string;
         description "Name of the service set";
       }
       leaf bytes-used {
         type uint64;
         description "Memory used (bytes)";
       }
     }
   }
   grouping service-set-cpu-statistics-information-block {
     list service-set-cpu-statistics {
       description "CPU usage statistics";
       leaf interface-name {
         type string;
         description "Name of the adaptive services interface";
       }
       leaf service-set-name {
         type string;
         description "Name of the service set";
       }
       leaf cpu-utilization-percent {
         type uint32;
         description "CPU utilization (percent)";
       }
     }
   }
   grouping service-set-summary-information-block {
     container service-set-summary-information-entry {
       leaf interface-name {
         type string;
         description "Name of the adaptive services interface";
       }
       list service-set-service-type-entry {
         leaf service-sets-configured {
           type uint32;
           description "Number of service sets configured";
         }
         leaf service-set-bytes-used {
           type uint64;
           description "Memory used (bytes)";
         }
         leaf service-set-memory-alarm {
           type string;
           description "Memory Alarm (zone)";
         }
         leaf service-set-percent-bytes-used {
           type uint32;
           description "Memory used (percent)";
         }
         leaf service-set-policy-bytes-used {
           type uint64;
           description "Policy memory used (bytes)";
         }
         leaf service-set-percent-policy-bytes-used {
           type uint32;
           description "Policy memory used (percent)";
         }
         leaf service-set-cpu-utilization {
           type uint32;
           description "CPU utilization (percent)";
         }
         leaf service-set-cpu-alarm {
           type string;
           description "CPU Alarm (zone)";
         }
         leaf service-type {
           type string;
           description "Service type";
         }
         leaf service-set-session-bytes-used {
           type uint64;
           description "Session memory used (bytes)";
         }
         leaf service-set-percent-session-bytes-used {
           type uint32;
           description "Session memory used (percent)";
         }
       }
     }
   }
   grouping service-set-plugin-summary-block {
     leaf interface-name {
       type string;
       description "Name of the adaptive services interface";
     }
     list service-set-plugin-information {
       description "Service set plugin information";
       leaf service-set-name {
         type string;
         description "Name of the service set";
       }
       leaf service-set-state {
         type string;
         description "Service set state";
       }
       leaf plugins-configured {
         type uint32;
         description "Plugins configured";
       }
       list service-set-plugin-entry {
         description "Service set plugin details";
         leaf plugin-name {
           type string;
           description "Name of the plugin";
         }
         leaf plugin-id {
           type uint32;
           description "Plugin ID";
         }
       }
     }
   }
   grouping source-nat-pool-information-block {
     list source-nat-pool-entry {
       leaf pool-name {
         type string;
         description "Name of the source NAT pool";
       }
       leaf address {
         type jt:ipaddr;
         description "IP address";
       }
       leaf pool-status {
         type string;
         description "Pool status";
       }
       leaf single-ports {
         type uint32;
         description "Number of allocated single ports";
       }
       leaf twin-ports {
         type uint32;
         description "Number of allocated twin ports";
       }
       leaf port-address-translation {
         type string;
         description "Support port address translation";
       }
       leaf host-address {
         type jt:ipaddr;
         description "Host IP address";
       }
       leaf references {
         type uint32;
         description "Reference count";
       }
     }
   }
   grouping source-nat-rule-application-information-block {
     leaf-list logical-system-name {
       type string;
       description "Name of the logical system";
     }
     list source-nat-rule-app-entry {
       description "Information on the source NAT rule";
       leaf rule-name {
         type string;
         description "The name of the rule";
       }
       leaf rule-set-name {
         type string;
         description "The name of the rule-set";
       }
       leaf rule-id {
         type uint32;
         description "The rule identifier";
       }
       list applications {
         list application {
           leaf application-name {
             type string;
             description "Name of the application";
           }
           list application-term {
             leaf protocol {
               type string;
               description "IP protocol";
             }
             list source-port-range {
               leaf low {
                 type int32;
                 description "The lower limit in the range of ports";
               }
               leaf high {
                 type int32;
                 description "The higher limit in the range of the ports";
               }
             }
             list destination-port-range {
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
           }
         }
       }
     }
   }
   grouping source-nat-summary-block {
     list source-nat-entry {
       leaf pool-name {
         type string;
         description "Name of the source NAT pool";
       }
       leaf address-low {
         type jt:ipaddr;
         description "Start of the address range";
       }
       leaf address-high {
         type jt:ipaddr;
         description "End of the address range";
       }
       leaf interface {
         type string;
         description "Name of the interface";
       }
       leaf port-address-translation {
         type string;
         description "Support port address translation";
       }
       leaf service-set-name {
         type string;
         description "Name of the service set";
       }
       leaf interface-name {
         type string;
         description "Name of the services interface";
       }
     }
   }
   grouping destination-nat-pool-information-block {
     leaf-list logical-system-name {
       type string;
       description "Name of the logical system";
     }
     container total-destination-nat-pool-number {
       description "Total number of destination-nat pools";
       leaf total-pools {
         type uint32;
         description "Total number of destination-nat pool";
       }
     }
     list destination-nat-pool-entry {
       description "Information on the destination-nat pool";
       leaf interface-name {
         type string;
         description "Name of the services interface";
       }
       leaf service-set-name {
         type string;
         description "Name of the service set";
       }
       leaf pool-name {
         type string;
         description "Name of the source NAT pool";
       }
       leaf pool-description {
         type string;
         description "The description of the pool";
       }
       leaf pool-id {
         type uint32;
         description "The numerical pool number";
       }
       leaf routing-instance-name {
         type string;
         description "The name of the routing instance";
       }
       leaf total-pool-address {
         type uint32;
         description "The total number of address pools";
       }
       leaf address-pool-hits {
         type uint32;
         description "The number of translation hits on this pool address";
       }
       list pool-address-range {
         description "Information on address range";
         leaf address-range-low {
           type string;
           description "The low range of the address";
         }
         leaf address-range-high {
           type string;
           description "The high range of the address";
         }
         leaf address-port {
           type uint32;
           description "The port number used";
         }
       }
     }
   }
   grouping destination-nat-rule-application-information-block {
     leaf-list logical-system-name {
       type string;
       description "Name of the logical system";
     }
     list destination-nat-rule-app-entry {
       description "Application configured on the destination NAT rule";
       leaf rule-name {
         type string;
         description "The name of the rule";
       }
       leaf rule-set-name {
         type string;
         description "The name of the rule-set";
       }
       leaf rule-id {
         type uint32;
         description "The rule identifier";
       }
       list applications {
         list application {
           leaf application-name {
             type string;
             description "Name of the application";
           }
           list application-term {
             leaf protocol {
               type string;
               description "IP protocol";
             }
             list source-port-range {
               leaf low {
                 type int32;
                 description "The lower limit in the range of ports";
               }
               leaf high {
                 type int32;
                 description "The higher limit in the range of the ports";
               }
             }
             list destination-port-range {
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
           }
         }
       }
     }
   }
   grouping destination-nat-summary-information-block {
     list destination-nat-entry {
       description "Information about a destination NAT entry";
       leaf destination-nat-pool-name {
         type string;
       }
       leaf destination-address-range {
         type string;
       }
       leaf destination-port-number {
         type int32;
       }
     }
   }
   grouping static-nat-rule-information-block {
     leaf-list logical-system-name {
       type string;
       description "Name of the logical system";
     }
     container total-static-nat-rules {
       description "Total number of static-nat rules";
       leaf total-rules {
         type uint32;
         description "Total number of destination-nat rules";
       }
     }
     container total-static-nat-rule-ref-addr-num {
       description "Total referenced IPv4/IPv6 ip-prefixes in static NAT rule";
       leaf total-static-nat-rule-ref-addr-num-v4 {
         type uint32;
         description "Total referenced IPv4 ip-prefixes in static NAT rule";
       }
       leaf total-static-nat-rule-ref-addr-num-v6 {
         type uint32;
         description "Total referenced IPv6 ip-prefixes in static NAT rule";
       }
     }
     list static-nat-rule-entry {
       description "Information on the static-nat rule";
       leaf interface-name {
         type string;
         description "Name of the services interface";
       }
       leaf service-set-name {
         type string;
         description "Name of the service set";
       }
       leaf rule-name {
         type string;
         description "The name of the rule";
       }
       leaf rule-set-name {
         type string;
         description "The name of the rule-set";
       }
       leaf rule-description {
         type string;
         description "The description of the rule";
       }
       leaf rule-id {
         type uint32;
         description "The rule identifier";
       }
       leaf rule-matching-position {
         type uint32;
         description "The matching criteria or position of the rule";
       }
       leaf rule-from-context {
         type string;
         description "The from context based on the rule definition";
       }
       leaf rule-from-context-name {
         type string;
         description "The name of the zone, routing instance, interface, or rouing group";
       }
       leaf rule-destination-address-prefix {
         type string;
         description "The destination address prefix";
       }
       leaf rule-host-address-prefix {
         type string;
         description "The host address prefix";
       }
       leaf rule-address-netmask {
         type string;
         description "The netmask of address";
       }
       leaf rule-host-routing-instance {
         type string;
         description "The host routing-instance of the rule";
       }
       leaf clear-alarm {
         type uint32;
         description "Clear alarm threshold of the rule";
       }
       leaf raise-alarm {
         type uint32;
         description "Raise alarm threshold of the rule";
       }
       leaf rule-translation-hits {
         type uint32;
         description "Number of rule translation hits on the specified object";
       }
       leaf succ-hits {
         type uint32;
         description "Number of succ translation hits on the specified object";
       }
       leaf failed-hits {
         type uint32;
         description "Number of failed translation hits on the specified object";
       }
       leaf concurrent-hits {
         type uint32;
         description "Number of concurrent translation hits on the specified object";
       }
       list static-source-address-range-entry {
         leaf rule-source-address {
           type string;
           description "The source address";
         }
         leaf rule-source-address-low-range {
           type string;
           description "The low range of the source address";
         }
         leaf rule-source-address-high-range {
           type string;
           description "The high range of the source address";
         }
       }
       list static-source-port-entry {
         leaf static-rule-source-port-low {
           type uint32;
           description "The low source port";
         }
         leaf static-rule-source-port-high {
           type uint32;
           description "The high source port";
         }
       }
       leaf rule-destination-port-low {
         type uint32;
         description "The low destination port";
       }
       leaf rule-destination-port-high {
         type uint32;
         description "The high destination port";
       }
       leaf rule-host-port-low {
         type uint32;
         description "The low host port";
       }
       leaf rule-host-port-high {
         type uint32;
         description "The high host port";
       }
       leaf rule-destination-nptv6-address-prefix {
         type string;
         description "The destination NPTv6 address prefix";
       }
       leaf rule-destination-nptv6-netmask {
         type string;
         description "The netmask of destination NPTv6 address";
       }
     }
   }
   grouping service-nat-pool-information-block {
     list sfw-per-service-set-nat-pool {
       description "NAT pool information for one service set";
       leaf interface-name {
         type string;
         description "Name of the adaptive services interface";
       }
       leaf service-set-name {
         type string;
         description "Name of the service set";
       }
       list service-nat-pool {
         leaf pool-name {
           type string;
           description "Name of the NAT pool";
         }
         leaf translation-type {
           type string;
           description "Type of Network Address Translation";
         }
         leaf pool-address-range {
           type string;
           description "Range of port addresses";
         }
         leaf pool-port-range {
           type string;
           description "Range of port numbers";
         }
         leaf pool-ports-in-use {
           type int32;
           description "Number of ports in use";
         }
         leaf port-block-type {
           type string;
           description "Type of port block";
         }
         leaf port-block-size {
           type uint32;
           description "Number of ports in a port block";
         }
         leaf max-blocks-per-address {
           type uint32;
           description "Max number of port blocks per private address";
         }
         leaf active-block-timeout {
           type uint32;
           description "Activity timeout of port block";
         }
         leaf effective-pba-port-range {
           type string;
           description "Effective range of port numbers";
         }
         leaf effective-port-blocks {
           type uint32;
           description "Effective number of port blocks";
         }
         leaf effective-ports {
           type uint32;
           description "Effective number of ports";
         }
         leaf port-block-efficiency {
           type string;
           description "Port block efficiency";
         }
         leaf pool-address-start {
           type string;
           description "Start of address range";
         }
         leaf pool-address-end {
           type string;
           description "End of address range";
         }
         leaf pool-port-low {
           type int32;
           description "Start of port range";
         }
         leaf pool-port-high {
           type int32;
           description "End of port range";
         }
         leaf pool-avail-addresses {
           type uint32;
           description "Total number of free addresses in the nat pool";
         }
         leaf pool-configured-port-range {
           type string;
           description "Range of port numbers configured";
         }
         leaf pool-preserve-range-enabled {
           type string;
           description "Preserve well known ports has been enabled";
         }
         leaf pool-out-of-port-errors {
           type int32;
           description "Number of port allocation failures";
         }
         leaf pool-out-of-address-errors {
           type int32;
           description "Number of address allocation failures";
         }
         leaf pool-max-ports-in-use {
           type int32;
           description "Maximum number of ports ever used in this pool so far";
         }
         leaf pool-addresses-in-use {
           type int32;
           description "Number of Addresses in use";
         }
         leaf pool-parity-port-errors {
           type int32;
           description "Number of port allocation failures due to parity";
         }
         leaf pool-preserve-range-errors {
           type int32;
           description "Number of port allocation failures due to preserve range";
         }
         leaf pool-app-port-errors {
           type int32;
           description "Number of APP port allocation failures";
         }
         leaf pool-app-exceed-port-limit-errors {
           type int32;
           description "Number of APP port allocation failures due to port limit";
         }
         leaf pool-mem-alloc-errors {
           type int32;
           description "Number of memory allocation failures";
         }
         leaf eif-inbound-session-count {
           type int32;
           description "Current number of eif inbound session ";
         }
         leaf eif-inbound-session-limit-exceed-drop {
           type int32;
           description "Current number of session drop due to exceeded eif limit ";
         }
         leaf pool-eif-current-inbound-flows-count {
           type uint32;
           description "Current eif inbound flows count";
         }
         leaf pool-eif-flow-limit-exceeded-drops {
           type uint32;
           description "Total eif flow limit exceeded drops";
         }
         leaf max-port-blocks-used {
           type uint32;
           description "Max number of port blocks used";
         }
         leaf port-blocks-in-use {
           type uint32;
           description "Current number of port blocks in use";
         }
         leaf port-block-allocation-errors {
           type uint32;
           description "Total port block allocation errors";
         }
         leaf port-block-out-of-port-errors {
           type uint32;
           description "Total port block out of port errors";
         }
         leaf port-block-mem-alloc-failure-errors {
           type uint32;
           description "Total port block memory allocation errors";
         }
         leaf pool-users {
           type int32;
           description "Number of subscribers using this pool";
         }
         leaf port-blocks-limit-exceeded-errors {
           type uint32;
           description "Total port blocks allocation limit exceeded errors";
         }
         leaf detnat-subscriber-exceeded-port-limits {
           type uint32;
           description "Subscriber port limit exceeded errors";
         }
       }
     }
   }
   grouping service-detnat-information-block {
     leaf service-set-name {
       type string;
       description "Name of the service set";
     }
     leaf interface-name {
       type string;
       description "Name of the adaptive services interface";
     }
     leaf pool-name {
       type string;
       description "Name of the NAT pool";
     }
     leaf detnat-internal-host {
       type string;
       description "Internal/Subscriber IP address";
     }
     leaf detnat-nat-ip {
       type string;
       description "NAT IP Address";
     }
     leaf detnat-nat-port-low {
       type string;
       description "NAT Port Start";
     }
     leaf detnat-nat-port-high {
       type string;
       description "NAT Port End";
     }
   }
   grouping service-nat-ipv6-multicast-interfaces-information-block {
     list service-nat-ipv6-multicast-interfaces {
       leaf v6-multicast-interface-name {
         type string;
         description "Name of interface for IPv6 multicast";
       }
       leaf v6-multicast-configured-status {
         type string;
         description "IPv6 multicast configuration";
       }
       leaf v6-multicast-operation-status {
         type string;
         description "IPv6 multicast status";
       }
       leaf v6-multicast-by-all {
         type string;
         description "IPv6 multicast configured by all keyword";
       }
     }
   }
   grouping service-nat-mapping-nptv6-information-block {
     leaf nptv6-interface-name {
       type string;
       description "Interface Name";
     }
     leaf nptv6-service-set {
       type string;
       description "Service Set Name";
     }
     leaf nptv6-pool-name {
       type string;
       description "Name of the NAT pool";
     }
     leaf nptv6-internal-ip {
       type string;
       description "Internal IPV6 address";
     }
     leaf nptv6-external-ip {
       type string;
       description "Translated IPV6 address";
     }
   }
   grouping service-nat-statistics-information-block {
     leaf interface-name {
       type string;
       description "Name of the services interface";
     }
     leaf query-unsupported-msg {
       type string;
       description "Query not supported on interface";
     }
     leaf nat-pkt-dst-in-nat-route {
       type int32;
       description "Sessions discarded due to packet destination in NAT route";
     }
     leaf nat-filtering-session {
       type int32;
       description "Session Created for EIF";
     }
     leaf nat-mapping-session {
       type int32;
       description "Session Created for EIM";
     }
     leaf nat-rule-lookup-failures {
       type int32;
       description "NAT rule lookup failures";
     }
     leaf nat-map-allocation-successes {
       type int32;
       description "NAT map allocation success count";
     }
     leaf nat-map-allocation-failures {
       type int32;
       description "NAT map allocation failure count";
     }
     leaf nat-map-free-success {
       type int32;
       description "NAT Free Successes";
     }
     leaf nat-map-free-failures {
       type int32;
       description "NAT Free Failures";
     }
     leaf nat-eim-mapping-create-failed {
       type int32;
       description "NAT EIM mapping create failed";
     }
     leaf nat-eim-mapping-created {
       type int32;
       description "NAT EIM mapping Created";
     }
     leaf nat-eim-mapping-updated {
       type int32;
       description "NAT EIM mapping Updated";
     }
     leaf nat-eif-mapping-free {
       type int32;
       description "NAT EIF mapping Free";
     }
     leaf nat-eim-mapping-free {
       type int32;
       description "NAT EIM mapping Free";
     }
     leaf nat-total-pkts-processed {
       type int32;
       description "Total packets processed";
     }
     leaf nat-total-pkts-forwarded {
       type int32;
       description "Total packets forwarded";
     }
     leaf nat-total-pkts-translated {
       type int32;
       description "Total packets translated";
     }
     leaf nat64-mtu-exceed {
       type uint32;
       description "NAT64 - MTU exceeded";
     }
     leaf nat64-dfbit-set {
       type uint32;
       description "NAT64 - dfbit set";
     }
     leaf nat64-err-mtu-exceed-build {
       type uint32;
       description "NAT64 error - MTU exceed build";
     }
     leaf nat64-err-mtu-exceed-send {
       type uint32;
       description "NAT64 error - MTU exceed send";
     }
     leaf session-xlate464-clat-prefix-not-found {
       type int32;
       description "Session xlate464 clat prefix not found";
     }
     leaf session-xlate464-embeded-ipv4-not-found {
       type int32;
       description "Session xlate464 embedded ipv4 not found";
     }
     leaf nat-jflow-log-alloc-fail {
       type uint32;
       description "NAT jflow-log error - memory allocation fail";
     }
     leaf nat-jflow-log-alloc-success {
       type uint32;
       description "NAT jflow-log - memory allocation success";
     }
     leaf nat-jflow-log-free-success {
       type uint32;
       description "NAT jflow-log - memory free success";
     }
     leaf nat-jflow-log-free-fail-record {
       type uint32;
       description "NAT jflow-log error - memory free fail null record";
     }
     leaf nat-jflow-log-free-fail-data {
       type uint32;
       description "NAT jflow-log error - memory free fail null data";
     }
     leaf nat-jflow_log-invalid-trans-type {
       type uint32;
       description "NAT jflow-log error - invalid nat translation type";
     }
     leaf nat-jflow-log-free-success-fail-queuing {
       type uint32;
       description "NAT jflow-log - memory free success";
     }
     leaf nat-jflow-log-invalid-input-args {
       type uint32;
       description "NAT jflow-log - invalid input arguments";
     }
     leaf nat-jflow-log-invalid-alloc-err {
       type uint32;
       description "NAT jflow-log - invalid allocation error type";
     }
     leaf nat-jflow-log-rate-limit-fail-get-pool {
       type uint32;
       description "NAT jflow-log - rate limit fail to get pool";
     }
     leaf nat-jflow-log-rate-limit-fail-get-service-set {
       type uint32;
       description "NAT jflow-log - rate limit fail get service set";
     }
     leaf nat-jflow-log-rate-limit-fail-invalid-current-time {
       type uint32;
       description "NAT jflow-log - rate limit fail invalid current time";
     }
     leaf nat-total-session-interest {
       type int32;
       description "Total Session Interest events";
     }
     leaf nat-total-session-create {
       type int32;
       description "Total Session Create events";
     }
     leaf nat-total-session-destroy {
       type int32;
       description "Total Session Destroy events";
     }
     leaf nat-total-session-pub-req {
       type int32;
       description "Total Session Pub Req events";
     }
     leaf nat-total-session-accepts {
       type int32;
       description "Total sessions accepted";
     }
     leaf nat-total-session-discards {
       type int32;
       description "Total sessions discarded";
     }
     leaf nat-total-session-ignores {
       type int32;
       description "Total sessions ignored";
     }
     leaf nat-ctrl-sess-not-xltd-chld-sess-ignd {
       type int32;
       description "Control Session not xlated and child session ignored";
     }
     leaf nat-total-session-time-event {
       type int32;
       description "Total Session Time events";
     }
     leaf nat-session-interest-pub-req {
       type int32;
       description "Session interest thru pub event";
     }
     leaf nat-alg-data-session-interest {
       type int32;
       description "ALG Session interest";
     }
     leaf nat-alg-data-session-created {
       type int32;
       description "ALG Session Create";
     }
     leaf total-session-close {
       type int32;
       description "Total Session Close";
     }
     leaf nat-pkt-drop-in-backup-state {
       type int32;
       description "Sessions discarded due to NAT in backup state";
     }
     leaf nat-session-ext-alloc-failures {
       type int32;
       description "Session extension allocation failures";
     }
     leaf nat-session-ext-set-failures {
       type int32;
       description "Session extension set failures";
     }
     leaf no-sext-in-xlate-pkt {
       type int32;
       description "No NAT Session Ext in Xlate Packet";
     }
     leaf pool-session-cnt-update-fail-on-create {
       type int32;
       description "Pool session count update on create";
     }
     leaf pool-session-cnt-update-fail-on-close {
       type int32;
       description "Pool session count update on close";
     }
     leaf session-xlate464-clat-prefix-found {
       type int32;
       description "Session xlate464 clat prefix found";
     }
     leaf session-xlate464-embeded-ipv4-found {
       type int32;
       description "Session xlate464 embeded ipv4 found for clat prefix length";
     }
     leaf session-xlate464-embeded-ipv4-invalid {
       type int32;
       description "Session xlate464 embeded ipv4 address not valid";
     }
     leaf nat_free_fail_on_inactive_sset {
       type uint32;
       description "NAT Free failures while service set is not active";
     }
     leaf nat-eim-mapping-reused {
       type int32;
       description "NAT EIM mapping reused";
     }
     leaf nat-eim-mapping-alloc-failures {
       type int32;
       description "NAT EIM mapping allocation failures";
     }
     leaf nat-eim-mismatched-mapping {
       type int32;
       description "NAT EIM mapping mismatched entry";
     }
     leaf nat-eim-duplicate-mapping {
       type int32;
       description "NAT EIM mapping duplicate entry";
     }
     leaf nat-eim-waiting-for-init {
       type int32;
       description "NAT EIM waiting for init";
     }
     leaf nat-eim-waiting-for-init-failed {
       type int32;
       description "NAT EIM waiting for init failed";
     }
     leaf nat-eim-lookup-hold-success {
       type int32;
       description "NAT EIM lookup and hold success";
     }
     leaf nat-eim-lookup-timeout {
       type int32;
       description "NAT EIM lookup entry in timeout";
     }
     leaf nat-eim-lookup-clear-timer {
       type int32;
       description "NAT EIM lookup timer cleared for timeout entry";
     }
     leaf nat-eim-lookup-entry-without-timer {
       type int32;
       description "NAT EIM lookup timeout entry without timer";
     }
     leaf nat-eim-release-without-entry {
       type int32;
       description "NAT EIM release without entry";
     }
     leaf nat-eim-release-in-timeout {
       type int32;
       description "NAT EIM release entry in timeout";
     }
     leaf nat-eim-release-race {
       type int32;
       description "NAT EIM release race";
     }
     leaf nat-eim-release-set-timeout {
       type int32;
       description "NAT EIM release set entry for timeout";
     }
     leaf nat-eim-timer-entry-refreshed {
       type int32;
       description "NAT EIM timer entry refreshed";
     }
     leaf nat-eim-timer-start-invalid {
       type int32;
       description "NAT EIM timer invalid timer started";
     }
     leaf nat-eim-timer-start-invalid-fail {
       type int32;
       description "NAT EIM timer invalid timer start failed";
     }
     leaf nat-eim-timer-free-mapping {
       type int32;
       description "NAT EIM timer entry freed";
     }
     leaf nat-eim-timer-update-timeout {
       type int32;
       description "NAT EIM timer entry updated";
     }
     leaf nat-eim-entry-drained {
       type int32;
       description "NAT EIM entry drained";
     }
     leaf nat_eim_mapping_eif_curr_sess_update_invalid {
       type uint32;
       description "NAT EIM - mapping eif curr sess update invalid";
     }
     leaf nat_eim_mapping_created_without_eif_sess_limit {
       type uint32;
       description "NAT EIM - mapping created without eif sess_limit set";
     }
     leaf nat-total-bytes-processed {
       type int32;
       description "Total bytes processed";
     }
     leaf nat-total-pkts-discarded {
       type int32;
       description "Total packets discarded";
     }
     leaf nat-total-pkts-restored {
       type int32;
       description "Total packets restored";
     }
     leaf nat-cm-sess-lnode-created {
       type int32;
       description "Total session list nodes created";
     }
     leaf nat-cm-sess-lnode-deleted {
       type int32;
       description "Total session list nodes deleted";
     }
     leaf nat-cm-eim-lnode-created {
       type int32;
       description "Total mapping list nodes created";
     }
     leaf nat-cm-eim-lnode-deleted {
       type int32;
       description "Total mapping list nodes deleted";
     }
     leaf nat-src-ipv4-translations {
       type int32;
       description "Source ipv4 translation count";
     }
     leaf nat-src-ipv4-restorations {
       type int32;
       description "Source ipv4 restoration count";
     }
     leaf nat-dst-ipv4-translations {
       type int32;
       description "Destination ipv4 translation count";
     }
     leaf nat-dst-ipv4-restorations {
       type int32;
       description "Destination ipv4 restoration count";
     }
     leaf nat-src-ipv6-translations {
       type uint32;
       description "Source ipv6 translation count";
     }
     leaf nat-src-ipv6-restorations {
       type uint32;
       description "Source ipv6 restoration count";
     }
     leaf nat-dst-ipv6-translations {
       type uint32;
       description "Destination ipv6 translation count";
     }
     leaf nat-dst-ipv6-restorations {
       type uint32;
       description "Destination ipv6 restoration count";
     }
     leaf nat-src-port-translations {
       type int32;
       description "Source port translation count";
     }
     leaf nat-src-port-restorations {
       type int32;
       description "Source port restoration count";
     }
     leaf nat-dst-port-translations {
       type int32;
       description "Destination port translation count";
     }
     leaf nat-dst-port-restorations {
       type int32;
       description "Destination port restoration count";
     }
     leaf nat-icmp-id-translations {
       type int32;
       description "ICMP ID translation count";
     }
     leaf nat-icmp-id-restorations {
       type int32;
       description "ICMP ID restoration count";
     }
     leaf nat-icmp-error-translations {
       type int32;
       description "ICMP error packets after translation";
     }
     leaf nat-icmp-drop {
       type int32;
       description "ICMP drops";
     }
     leaf nat-icmp-allocation-failure {
       type int32;
       description "ICMP allocation failure";
     }
     leaf nat-rule-lookup-for-icmp-err-fail {
       type int32;
       description "ICMP error NAT rule lookup failed";
     }
     leaf nat-tcp-port-translations {
       type int32;
       description "Tcp port translations count";
     }
     leaf nat-tcp-port-restorations {
       type int32;
       description "Tcp port restorations count";
     }
     leaf nat-udp-port-translations {
       type int32;
       description "Udp port translation count";
     }
     leaf nat-udp-port-restorations {
       type int32;
       description "Udp port restoration count";
     }
     leaf nat-unexpected-proto-with-port-xlation {
       type int32;
       description "Unexpected Protocol With Port Translation";
     }
     leaf nat-gre-call-id-translations {
       type int32;
       description "GRE call id translation count";
     }
     leaf nat-gre-call-id-restorations {
       type int32;
       description "GRE call id restoration count";
     }
     leaf nat-unsupported-gre-proto {
       type int32;
       description "GRE unsupported protocol value";
     }
     leaf nat-icmp-error-src-restored {
       type int32;
       description "SRC IP restored in ICMP Error";
     }
     leaf nat-icmp-error-dst-restored {
       type int32;
       description "DST IP restored in ICMP Error";
     }
     leaf nat-icmp-error-src-xlated {
       type int32;
       description "SRC IP translated in ICMP Error";
     }
     leaf nat-icmp-error-dst-xlated {
       type int32;
       description "DST IP translated in ICMP Error";
     }
     leaf nat-icmp-error-new-src-xlated {
       type int32;
       description "New SRC IP translated in ICMP Error";
     }
     leaf nat-icmp-error-org-ip-src-restored {
       type int32;
       description "Inner SRC IP restored in ICMP Error";
     }
     leaf nat-icmp-error-org-ip-src-port-restored {
       type int32;
       description "Inner SRC port restored in ICMP Error";
     }
     leaf nat-icmp-error-org-ip-dst-port-restored {
       type uint32;
       description "Inner DST port restored in ICMP Error";
     }
     leaf nat-icmp-error-org-ip-dst-restored {
       type int32;
       description "Inner DST IP restored in ICMP Error";
     }
     leaf nat-icmp-error-org-ip-src-xlated {
       type int32;
       description "Inner SRC IP Translated in ICMP Error";
     }
     leaf nat-icmp-error-org-ip-src-port-xlated {
       type int32;
       description "Inner SRC port Translated in ICMP Error";
     }
     leaf nat-icmp-error-org-ip-dst-port-xlated {
       type uint32;
       description "Inner DST port Translated in ICMP Error";
     }
     leaf nat-icmp-error-org-ip-dst-xlated {
       type int32;
       description "Inner DST IP Translated in ICMP Error";
     }
     leaf nat-error-no-policy {
       type int32;
       description "NAT error - no policy";
     }
     leaf nat-error-ip-version {
       type uint32;
       description "NAT error - IP version";
     }
     leaf nat-xlate-free-null-ext {
       type int32;
       description "NAT error - xlate free called with null ext";
     }
     leaf nat-session-ext-free-failed {
       type int32;
       description "NAT error - ext free failed";
     }
     leaf nat-policy-add-failed {
       type int32;
       description "NAT error - policy add failed";
     }
     leaf nat-policy-delete-failed {
       type int32;
       description "NAT error - policy delete failed";
     }
     leaf nat-prefix-filter-alloc-failed {
       type uint32;
       description "NAT error - prefix filter allocation failed";
     }
     leaf nat-prefix-filter-name-failed {
       type uint32;
       description "NAT error - prefix filter name failed";
     }
     leaf nat-prefix-list-create-failed {
       type uint32;
       description "NAT error - prefix list create failed";
     }
     leaf nat-prefix-filter-tree-add-failed {
       type uint32;
       description "NAT error - prefix filter tree add failed";
     }
     leaf nat-prefix-filter-created {
       type uint32;
       description "NAT - prefix filter created";
     }
     leaf nat-prefix-filter-changed {
       type uint32;
       description "NAT - prefix filter changed";
     }
     leaf nat-prefix-filter-ctrl-free {
       type uint32;
       description "NAT - prefix filter control free";
     }
     leaf nat-prefix-filter-match {
       type uint32;
       description "NAT - prefix filter match";
     }
     leaf nat-prefix-filter-no-match {
       type uint32;
       description "NAT - prefix filter No match";
     }
     leaf nat-prefix-filter-mapping-add {
       type uint32;
       description "NAT - prefix filter mapping add";
     }
     leaf nat-prefix-filter-mapping-remove {
       type uint32;
       description "NAT - prefix filter mapping remove";
     }
     leaf nat-prefix-filter-mapping-free {
       type uint32;
       description "NAT - prefix filter mapping free";
     }
     leaf nat-prefix-filter-unsupp-ip-version {
       type uint32;
       description "NAT - prefix filter Unsupported IP version";
     }
     leaf nat-unsupported-layer-4-napt {
       type uint32;
       description "NAT - Unsupported layer 4 protocol";
     }
     leaf nat-unsupported-icmp-type-napt {
       type uint32;
       description "NAT - Unsupported ICMP type";
     }
     leaf nat64-ipoptions-drop {
       type uint32;
       description "NAT64 - IP options drop";
     }
     leaf nat64-udp-cksum-zero-drop {
       type uint32;
       description "NAT64 - UDP checksum zero drop";
     }
     leaf nat64-unsupp-icmp-type-drop {
       type uint32;
       description "NAT64 - Unsupported ICMP type drop";
     }
     leaf nat64-unsupp-icmp-code-drop {
       type uint32;
       description "NAT64 - Unsupported ICMP code drop";
     }
     leaf nat64-unsupp-hdr-drop {
       type uint32;
       description "NAT64 - Unsupported Header drop";
     }
     leaf nat64-unsupp-l4-drop {
       type uint32;
       description "NAT64 - Unsupported L4 drop";
     }
     leaf nat64-ttl-exceed {
       type uint32;
       description "NAT64 - TTL exceeded";
     }
     leaf nat64-unsupp-icmp-error {
       type uint32;
       description "NAT64 - Unsupported ICMP error";
     }
     leaf nat64-err-map-src {
       type uint32;
       description "NAT64 error - mapping ipv4 source";
     }
     leaf nat64-err-map-dst {
       type uint32;
       description "NAT64 error - mapping ipv6 destination";
     }
     leaf nat64-err-ttl-exceed-build {
       type uint32;
       description "NAT64 error - TTL exceed build";
     }
     leaf nat64-err-ttl-exceed-send {
       type uint32;
       description "NAT64 error - TTL exceed send";
     }
     leaf nat-subs-ext-alloc {
       type uint32;
       description "NAT subscriber extension - allocated";
     }
     leaf nat-subs-ext-invalid-param {
       type uint32;
       description "NAT subscriber extension - invalid parameters";
     }
     leaf nat-subs-ext-no-mem {
       type uint32;
       description "NAT subscriber extension - no memory";
     }
     leaf nat-subs-ext-free {
       type uint32;
       description "NAT subscriber extension - freed";
     }
     leaf nat-subs-ext-is-null {
       type uint32;
       description "NAT subscriber extension - is NULL";
     }
     leaf nat-subs-ext-is-invalid {
       type uint32;
       description "NAT subscriber extension - is invalid";
     }
     leaf nat-subs-ext-link-success {
       type uint32;
       description "NAT subscriber extension - link is successful";
     }
     leaf nat-subs-ext-link-exist {
       type uint32;
       description "NAT subscriber extension - link already exists";
     }
     leaf nat-subs-ext-link-fail {
       type uint32;
       description "NAT subscriber extension - link failed";
     }
     leaf nat-subs-ext-link-unknown-ret {
       type uint32;
       description "NAT subscriber extension - unknown return value";
     }
     leaf nat-subs-ext-unlink-success {
       type uint32;
       description "NAT subscriber extension - unlink is successful";
     }
     leaf nat-subs-ext-unlink-fail {
       type uint32;
       description "NAT subscriber extension - unlink failed";
     }
     leaf nat-subs-ext-unlink-busy {
       type uint32;
       description "NAT subscriber extension - unlink on busy";
     }
     leaf nat-subs-ext-resource-in-use {
       type uint32;
       description "NAT subscriber extension - resource in use";
     }
     leaf nat-subs-ext-svc-set-not-active {
       type uint32;
       description "NAT subscriber extension - svc set is not active";
     }
     leaf nat-subs-ext-svc-set-is-null {
       type uint32;
       description "NAT subscriber extension - svc set is null";
     }
     leaf nat-subs-ext-timer-start-success {
       type uint32;
       description "NAT subscriber extension - timer start successful";
     }
     leaf nat-subs-ext-timer-start-fail {
       type uint32;
       description "NAT subscriber extension - timer start failed";
     }
     leaf nat-subs-ext-delay-timer-success {
       type uint32;
       description "NAT subscriber extension - delay timer start success";
     }
     leaf nat-subs-ext-delay-timer-fail {
       type uint32;
       description "NAT subscriber extension - delay timer start failed";
     }
     leaf nat-subs-ext-reuse-from-timer {
       type uint32;
       description "NAT subscriber extension - reuse from timer";
     }
     leaf nat-subs-ext-timer-cb {
       type uint32;
       description "NAT subscriber extension - timer callback called";
     }
     leaf nat-subs-ext-refcount-dec-fail {
       type uint32;
       description "NAT subscriber extension - plugin refcount decrement failed";
     }
     leaf nat-subs-ext-subs-reset-fail {
       type uint32;
       description "NAT subscriber extension - subscriber reset failed";
     }
     leaf nat-subs-ext-subs-session-count-update-ignore {
       type uint32;
       description "NAT subscriber extension - session count update ignored";
     }
     leaf nat-subs-ext-incorrect-state {
       type uint32;
       description "NAT subscriber extension - Incorrect state";
     }
     leaf nat-subs-ext-unlink-unk-err {
       type uint32;
       description "NAT subscriber extension - Unlink unknown error";
     }
     leaf nat-subs-ext-queue-inconsistent {
       type uint32;
       description "NAT subscriber extension - Queue inconsistent state";
     }
     leaf nat-subs-ext-return-to-prealloc-err {
       type uint32;
       description "NAT subscriber extension - Return to prealloc queue err";
     }
     leaf nat-subs-ext-dec-inval-sess-cnt {
       type uint32;
       description "NAT subscriber extension - Decrement invalid session count";
     }
     leaf nat-subs-ext-dec-inval-eim-cnt {
       type uint32;
       description "NAT subscriber extension - Decrement invalid EIM count";
     }
     leaf nat-subs-ext-ports-in-use-err {
       type uint32;
       description "NAT subscriber extension - Ports in use error";
     }
     leaf nat-subs-ext-err-set-state {
       type uint32;
       description "NAT subscriber extension - Set state error";
     }
     leaf nat-subs-ext-missing-ext {
       type uint32;
       description "NAT subscriber extension - Nat subscriber extension is missing";
     }
     leaf nat-subs-ext-invalid-eimrefcnt {
       type uint32;
       description "NAT subscriber extension - unexpected eim refcnt";
     }
     leaf nat-subs-ext-is-invalid-subs-in-tw {
       type uint32;
       description "NAT subscriber extension - invalid subs in timer wheel";
     }
     leaf nat-subs-ext-in-tw-during-free {
       type uint32;
       description "NAT subscriber extension - subs in timer wheel during free";
     }
     leaf nat_jflow_log_nat_sext_null {
       type uint32;
       description "NAT jflow-log error - session extension get fail";
     }
     leaf nat_jflow_log_alloc_fail {
       type uint32;
       description "NAT jflow-log error - memory allocation fail";
     }
     leaf nat_jflow_log_alloc_success {
       type uint32;
       description "NAT jflow-log - memory allocation success";
     }
     leaf nat_jflow_log_free_success {
       type uint32;
       description "NAT jflow-log - memory free success";
     }
     leaf nat_jflow_log_free_fail_record {
       type uint32;
       description "NAT jflow-log error - memory free fail null record";
     }
     leaf nat_jflow_log_free_fail_data {
       type uint32;
       description "NAT jflow-log error - memory free fail null data";
     }
     leaf nat_jflow_log_invalid_trans_type {
       type uint32;
       description "NAT jflow-log error - invalid nat translation type";
     }
     leaf nat_jflow_log_free_success_fail_queuing {
       type uint32;
       description "NAT jflow-log - memory free success";
     }
     leaf nat_jflow_log_invalid_input_args {
       type uint32;
       description "NAT jflow-log - invalid input arguments";
     }
     leaf nat_jflow_log_invalid_alloc_err {
       type uint32;
       description "NAT jflow-log - invalid allocation error type";
     }
     leaf nat_jflow_log_rate_limit_fail_get_pool_name {
       type uint32;
       description "NAT jflow-log - rate limit fail get pool name";
     }
     leaf nat_jflow_log_rate_limit_fail_get_natpool {
       type uint32;
       description "NAT jflow-log - rate limit fail get natpool";
     }
     leaf nat_jflow_log_rate_limit_fail_get_natpool_given_id {
       type uint32;
       description "NAT jflow-log - rate limit fail get natpool for given id";
     }
     leaf nat_jflow_log_rate_limit_fail_get_service_set {
       type uint32;
       description "NAT jflow-log - rate limit fail get service set";
     }
     leaf nat_jflow_log_rate_limit_fail_invalid_current_time {
       type uint32;
       description "NAT jflow-log - rate limit fail invalid current time";
     }
     leaf nat-eim-drain-in-lookup {
       type int32;
       description "NAT EIM entry found in drain state in lookup";
     }
   }
   grouping policy-hit-count-service-router-block {
     leaf-list policy-hit-count-num {
       type uint32;
       description "Number of policy";
     }
     list policy-hit-count-service-router-entry {
       description "Information about policy hit-count";
       leaf policy-hit-count-service-router-index {
         type uint32;
         description "Index";
       }
       leaf policy-hit-count-service-router-service-set {
         type string;
         description "Service set";
       }
       leaf policy-hit-count-service-router-interface {
         type string;
         description "Service set interface";
       }
       leaf policy-hit-count-service-router-policy-name {
         type string;
         description "Policy name";
       }
       leaf policy-hit-count-service-router-sfw-rule-name {
         type string;
         description "Sfw-rule name";
       }
       leaf policy-hit-count-service-router-direction {
         type string;
         description "Direction";
       }
       leaf policy-hit-count-service-router-count {
         type uint32;
         description "Policy hit-count ";
       }
     }
   }
   grouping sm-dns-statistics-block {
     leaf sm-dns-statistics-cache-hits {
       type uint64;
     }
     leaf sm-dns-statistics-cache-misses {
       type uint64;
     }
     leaf sm-dns-statistics-c2-sessions-permitted {
       type uint64;
     }
     leaf sm-dns-statistics-c2-sessions-dropped {
       type uint64;
     }
     leaf sm-dns-statistics-c2-sessions-sinkholed {
       type uint64;
     }
     leaf sm-dns-statistics-domain-submission-success {
       type uint64;
     }
     leaf sm-dns-statistics-domain-submission-failures {
       type uint64;
     }
     leaf sm-dns-statistics-safe-verdicts-received {
       type uint64;
     }
     leaf sm-dns-statistics-c2-verdicts-received {
       type uint64;
     }
     leaf sm-dns-statistics-dns-tunnels-detected {
       type uint64;
     }
     leaf sm-dns-statistics-latency-fallback-triggered {
       type uint64;
     }
     leaf sm-dns-statistics-average-latency {
       type uint32;
     }
     leaf sm-dns-statistics-maximum-latency {
       type uint32;
     }
     leaf sm-dns-statistics-minimum-latency {
       type uint32;
     }
     leaf sm-dns-statistics-sub50ms-response {
       type uint32;
     }
     leaf sm-dns-statistics-sub50ms-response-percent {
       type uint32;
     }
     leaf sm-dns-statistics-sub100ms-response {
       type uint32;
     }
     leaf sm-dns-statistics-sub100ms-response-percent {
       type uint32;
     }
     leaf sm-dns-statistics-sub250ms-response {
       type uint32;
     }
     leaf sm-dns-statistics-sub250ms-response-percent {
       type uint32;
     }
     leaf sm-dns-statistics-sub500ms-response {
       type uint32;
     }
     leaf sm-dns-statistics-sub500ms-response-percent {
       type uint32;
     }
     leaf-list logical-system-name {
       type string;
       description "Name of the logical system";
     }
     leaf-list dns-logical-system {
       type string;
       description "Logical system name";
     }
     leaf-list sm-dns-logical-system {
       type string;
       description "Logical system name";
     }
     leaf-list sm-dns-wl-logical-system {
       type string;
       description "Logical system name";
     }
   }
   grouping security-dynamic-address-block {
     leaf da-ipc-entry-add {
       type int32;
       description "Num of entry add IPC message object created";
     }
     leaf da-ipc-entry-del {
       type int32;
       description "Num of entry del IPC message object created";
     }
     leaf da-ipc-entry-trace-option {
       type int32;
       description "Num of trace option IPC message object created";
     }
     leaf da-ipc-batch-sent {
       type int32;
       description "Num of IPC message batches have been sent";
     }
     leaf da-malloc-failure {
       type int32;
       description "Counter of malloc failure";
     }
     leaf da-ipc-init {
       type string;
       description "Timestamp for IPC initialization";
     }
     leaf da-pfe-conn-first {
       type string;
       description "Timestamp for first PFE connection";
     }
     leaf da-pfe-conn-last {
       type string;
       description "Timestamp for last PFE connection";
     }
     leaf da-pfe-conn-failure {
       type string;
       description "Timestamp for last PFE connection failure";
     }
     leaf da-instance-name {
       type string;
       description "Name of dynamic address instance";
     }
     leaf da-ip-entry-idx {
       type int32;
       description "Position in found IP entries";
     }
     leaf da-ip-start {
       type string;
       description "Numerically minimal IP address within the range";
     }
     leaf da-ip-end {
       type string;
       description "Numerically maximal IP address within the range";
     }
     leaf da-name {
       type string;
       description "Dynamic address name";
     }
     leaf da-country-code {
       type string;
       description "Country code";
     }
     leaf da-lsys-name {
       type string;
       description "Logical system name";
     }
     leaf da-lsysinfo {
       type string;
       description "Dynamic address logical-system tenant name";
     }
     leaf feed-ref-da-name {
       type string;
       description "Dynamic address name";
     }
     leaf da-id {
       type int32;
       description "Dynamic address ID";
     }
     leaf da-sscan-status {
       type string;
       description "Dynamic address session scan module status";
     }
     leaf da-sscan-hold-interval {
       type string;
       description "Dynamic address session scan hold interval";
     }
     leaf da-sscan-entry-status {
       type string;
       description "Dynamic address session scan entry status";
     }
     leaf da-feed-server-name {
       type string;
       description "Feed server name";
     }
     leaf da-feed-server-lsysinfo {
       type string;
       description "Feed server logical-system tenant name";
     }
     leaf da-feed-name {
       type string;
       description "Feed source name";
     }
     leaf da-feed-lsysinfo {
       type string;
       description "Feed logical-system tenant name";
     }
     leaf da-category-name {
       type string;
       description "Category name";
     }
     leaf da-category-feed {
       type string;
       description "Category feed";
     }
     leaf da-property-name {
       type string;
       description "Property name";
     }
     leaf da-property-value {
       type string;
       description "Property value";
     }
     leaf da-property-value-start {
       type string;
       description "Property start value inclusive";
     }
     leaf da-property-value-end {
       type string;
       description "Property nd value inclusive";
     }
     leaf da-inst-name {
       type string;
       description "Dynamic address instance name";
     }
     leaf da-total-count {
       type int32;
       description "Number of entries";
     }
     leaf da-entry-cnt-v4 {
       type int32;
       description "IPv4 entry count";
     }
     leaf da-entry-cnt-v6 {
       type int32;
       description "IPv6 entry count";
     }
     leaf da-entry-cnt-mapping-feed {
       type int32;
       description "Mapping feed count";
     }
     leaf da-config-flags {
       type string;
       description "Configuration flags";
     }
     leaf da-feed-server-cnt {
       type int32;
       description "Number of feed server";
     }
     leaf da-feed-cnt {
       type int32;
       description "Number of feed";
     }
     leaf da-cnt {
       type int32;
       description "Number of dynamic address entry";
     }
     leaf da-cnt-total-v4 {
       type int32;
       description "IPv4 entry count";
     }
     leaf da-cnt-total-feed-v4 {
       type int32;
       description "IPv4 entry count from feed";
     }
     leaf da-cnt-total-v6 {
       type int32;
       description "IPv6 entry count";
     }
     leaf da-cnt-total-feed-v6 {
       type int32;
       description "IPv6 entry count from feed";
     }
     leaf da-feed-server-ca-profile-name {
       type string;
       description "Certificate profile name";
     }
     leaf da-feed-server-tls-profile-name {
       type string;
       description "TLS profile name";
     }
     leaf da-feed-server-user-name {
       type string;
       description "User name";
     }
     leaf da-feed-server-url {
       type string;
       description "Common url for feeds under same server";
     }
     leaf da-feed-server-routing-table {
       type string;
       description "Preferred routing table";
     }
     leaf da-feed-server-update-interval {
       type int32;
       description "The interval between end of last retrieval and start of next retrieval when feed does not configure it";
     }
     leaf da-feed-server-hold-interval {
       type int32;
       description "The time to hold data when feed update failed";
     }
     leaf da-feed-update-interval {
       type int32;
       description "The interval between end of last retrieval and start of next retrieval when feed does not configure it";
     }
     leaf da-feed-hold-interval {
       type int32;
       description "The time to hold data when feed update failed";
     }
     leaf da-feed-url {
       type int32;
       description "The URL to retreive dynamic address feed";
     }
     leaf da-feed-routing-table {
       type string;
       description "Preferred routing table";
     }
     leaf da-feed-ca-profile-name {
       type string;
       description "Certificate profile name";
     }
     leaf da-feed-stat-hist-total-update {
       type int32;
       description "Total number of updates on this feed";
     }
     leaf da-feed-stat-db-total-v4 {
       type int32;
       description "Total number of IPv4 entries in db from this feed";
     }
     leaf da-feed-stat-db-total-v6 {
       type int32;
       description "Total number of IPv6 entries in db from this feed";
     }
     leaf da-feed-stat-hist-total-err-download {
       type int32;
       description "Total number of download error on this feed";
     }
     leaf da-feed-stat-hist-total-err-db {
       type int32;
       description "Total number of db error on this feed";
     }
     leaf da-feed-stat-hist-total-err-other {
       type int32;
       description "Total number of other error on this feed";
     }
     leaf da-feed-stat-hist-total-ageout {
       type int32;
       description "Total number of ageout this feed";
     }
     leaf da-feed-stat-last-update-file-size {
       type int32;
       description "File size of last update";
     }
     leaf da-feed-stat-last-update-ipv4 {
       type int32;
       description "Total number of IPv4 entries contained in last update";
     }
     leaf da-feed-stat-last-update-ipv6 {
       type int32;
       description "Total number of IPv6 entries contained in last update";
     }
     leaf da-feed-stat-last-update-time-cost {
       type string;
       description "Seconds it took for last update parsing";
     }
     leaf da-feed-stat-last-download-time-cost {
       type string;
       description "Seconds it took for last downloading";
     }
     leaf da-feed-stat-last-update-begin-timestamp {
       type string;
       description "The time when last update began";
     }
     leaf da-feed-stat-last-update-end-timestamp {
       type string;
       description "The time when last update finished";
     }
     leaf da-feed-stat-last-update-status {
       type string;
       description "Last update status";
     }
     leaf da-feed-stat-last-download-begin-timestamp {
       type string;
       description "The time when last download began";
     }
     leaf da-feed-stat-last-download-end-timestamp {
       type string;
       description "The time when last download finished";
     }
     leaf da-feed-stat-last-err-download-timestamp {
       type string;
       description "The time when last download error happened";
     }
     leaf da-feed-stat-last-err-db-timestamp {
       type string;
       description "The time when last db error happened";
     }
     leaf da-feed-stat-last-err-other-timestamp {
       type string;
       description "The time when last other error happened";
     }
     leaf da-feed-stat-last-ageout-timestamp {
       type string;
       description "The time when last ageout happened";
     }
     leaf da-feed-stat-wakeup-update-time {
       type string;
       description "The time when next update happened";
     }
     leaf da-feed-stat-wakeup-expire-time {
       type string;
       description "The time when next expire happened";
     }
     leaf da-feed-stat-flag {
       type int32;
       description "Flags for feed";
     }
     container da-ip-entry {
       leaf da-ip-entry-idx {
         type int32;
         description "Position in found IP entries";
       }
       leaf da-ip-start {
         type string;
         description "Numerically minimal IP address within the range";
       }
       leaf da-ip-end {
         type string;
         description "Numerically maximal IP address within the range";
       }
       leaf da-feed-name {
         type string;
         description "Feed source name";
       }
       leaf da-name {
         type string;
         description "Dynamic address name";
       }
       leaf da-country-code {
         type string;
         description "Country code";
       }
     }
     container da-ip-entry-lsys {
       leaf da-ip-entry-idx {
         type int32;
         description "Position in found IP entries";
       }
       leaf da-ip-start {
         type string;
         description "Numerically minimal IP address within the range";
       }
       leaf da-ip-end {
         type string;
         description "Numerically maximal IP address within the range";
       }
       leaf da-feed-name {
         type string;
         description "Feed source name";
       }
       leaf da-name {
         type string;
         description "Dynamic address name";
       }
       leaf da-country-code {
         type string;
         description "Country code";
       }
       leaf da-lsys-name {
         type string;
         description "Logical system name";
       }
     }
     container da-ip-entry-foot {
       leaf da-inst-name {
         type string;
         description "Dynamic address instance name";
       }
       leaf da-total-count {
         type int32;
         description "Number of entries";
       }
     }
     container da-summary-brief {
       leaf da-feed-server-cnt {
         type int32;
         description "Number of feed server";
       }
       leaf da-feed-cnt {
         type int32;
         description "Number of feed";
       }
       leaf da-cnt {
         type int32;
         description "Number of dynamic address entry";
       }
     }
     container da-summary-server {
       leaf da-feed-server-name {
         type string;
         description "Feed server name";
       }
       leaf da-feed-server-lsysinfo {
         type string;
         description "Feed server logical-system tenant name";
       }
       leaf da-feed-server-ca-profile-name {
         type string;
         description "Certificate profile name";
       }
       leaf da-feed-server-tls-profile-name {
         type string;
         description "TLS profile name";
       }
       leaf da-feed-server-user-name {
         type string;
         description "User name";
       }
       leaf da-feed-server-url {
         type string;
         description "Common url for feeds under same server";
       }
       leaf da-feed-server-routing-table {
         type string;
         description "Preferred routing table";
       }
       leaf da-feed-server-update-interval {
         type int32;
         description "The interval between end of last retrieval and start of next retrieval when feed does not configure it";
       }
       leaf da-feed-server-hold-interval {
         type int32;
         description "The time to hold data when feed update failed";
       }
       container da-summary-feed {
         leaf da-feed-name {
           type string;
           description "Feed source name";
         }
         leaf da-feed-lsysinfo {
           type string;
           description "Feed logical-system tenant name";
         }
         leaf feed-ref-da-name {
           type string;
           description "Dynamic address name";
         }
         leaf da-feed-ca-profile-name {
           type string;
           description "Certificate profile name";
         }
         leaf da-feed-url {
           type int32;
           description "The URL to retreive dynamic address feed";
         }
         leaf da-feed-routing-table {
           type string;
           description "Preferred routing table";
         }
         leaf da-feed-update-interval {
           type int32;
           description "The interval between end of last retrieval and start of next retrieval when feed does not configure it";
         }
         leaf da-feed-hold-interval {
           type int32;
           description "The time to hold data when feed update failed";
         }
         leaf da-feed-stat-hist-total-update {
           type int32;
           description "Total number of updates on this feed";
         }
         leaf da-feed-stat-db-total-v4 {
           type int32;
           description "Total number of IPv4 entries in db from this feed";
         }
         leaf da-feed-stat-db-total-v6 {
           type int32;
           description "Total number of IPv6 entries in db from this feed";
         }
         leaf da-feed-stat-hist-total-err-download {
           type int32;
           description "Total number of download error on this feed";
         }
         leaf da-feed-stat-last-err-download-timestamp {
           type string;
           description "The time when last download error happened";
         }
         leaf da-feed-stat-hist-total-err-db {
           type int32;
           description "Total number of db error on this feed";
         }
         leaf da-feed-stat-last-err-db-timestamp {
           type string;
           description "The time when last db error happened";
         }
         leaf da-feed-stat-hist-total-err-other {
           type int32;
           description "Total number of other error on this feed";
         }
         leaf da-feed-stat-last-err-other-timestamp {
           type string;
           description "The time when last other error happened";
         }
         leaf da-feed-stat-hist-total-ageout {
           type int32;
           description "Total number of ageout this feed";
         }
         leaf da-feed-stat-last-ageout-timestamp {
           type string;
           description "The time when last ageout happened";
         }
         leaf da-feed-stat-wakeup-update-time {
           type string;
           description "The time when next update happened";
         }
         leaf da-feed-stat-wakeup-expire-time {
           type string;
           description "The time when next expire happened";
         }
         leaf da-feed-stat-flag {
           type int32;
           description "Flags for feed";
         }
         leaf da-feed-stat-last-update-file-size {
           type int32;
           description "File size of last update";
         }
         leaf da-feed-stat-last-update-ipv4 {
           type int32;
           description "Total number of IPv4 entries contained in last update";
         }
         leaf da-feed-stat-last-update-ipv6 {
           type int32;
           description "Total number of IPv6 entries contained in last update";
         }
         leaf da-feed-stat-last-update-begin-timestamp {
           type string;
           description "The time when last update began";
         }
         leaf da-feed-stat-last-update-end-timestamp {
           type string;
           description "The time when last update finished";
         }
         leaf da-feed-stat-last-update-time-cost {
           type string;
           description "Seconds it took for last update parsing";
         }
         leaf da-feed-stat-last-update-status {
           type string;
           description "Last update status";
         }
         leaf da-feed-stat-last-download-begin-timestamp {
           type string;
           description "The time when last download began";
         }
         leaf da-feed-stat-last-download-end-timestamp {
           type string;
           description "The time when last download finished";
         }
         leaf da-feed-stat-last-download-time-cost {
           type string;
           description "Seconds it took for last downloading";
         }
       }
     }
   }
   grouping av-policy-block {
     leaf av-policy-name {
       type string;
     }
     leaf av-policy-action {
       type string;
     }
     leaf av-policy-verdict-number {
       type string;
     }
     leaf av-policy-notification {
       type string;
     }
     leaf av-policy-default-notification {
       type string;
     }
     leaf av-policy-header {
       type string;
     }
     leaf av-policy-fallback-action {
       type string;
     }
     leaf av-policy-fallback-notification {
       type string;
     }
     leaf av-ml-scan-header {
       type string;
     }
     leaf av-ml-scan-action {
       type string;
     }
     leaf av-ml-scan-notification {
       type string;
     }
     leaf av-ml-default-notification {
       type string;
     }
   }
   grouping av-statistics-block {
     leaf av-statistics-db-type {
       type string;
     }
     leaf av-statistics-total-sigs {
       type uint32;
     }
     leaf av-statistics-db-version {
       type string;
     }
     leaf av-statistics-db-update-time {
       type string;
     }
     leaf av-statistics-total-files-scanned {
       type uint32;
     }
     leaf av-statistics-http-files-scanned {
       type uint32;
     }
     leaf av-statistics-https-files-scanned {
       type uint32;
     }
     leaf av-statistics-smtp-files-scanned {
       type uint32;
     }
     leaf av-statistics-smtps-files-scanned {
       type uint32;
     }
     leaf av-statistics-imap-files-scanned {
       type uint32;
     }
     leaf av-statistics-imaps-files-scanned {
       type uint32;
     }
     leaf av-statistics-smb-files-scanned {
       type uint32;
     }
     leaf av-statistics-total-files-found {
       type uint32;
     }
     leaf av-statistics-http-files-found {
       type uint32;
     }
     leaf av-statistics-https-files-found {
       type uint32;
     }
     leaf av-statistics-smtp-files-found {
       type uint32;
     }
     leaf av-statistics-smtps-files-found {
       type uint32;
     }
     leaf av-statistics-imap-files-found {
       type uint32;
     }
     leaf av-statistics-imaps-files-found {
       type uint32;
     }
     leaf av-statistics-smb-files-found {
       type uint32;
     }
     leaf av-statistics-total-files-blocked {
       type uint32;
     }
     leaf av-statistics-http-files-blocked {
       type uint32;
     }
     leaf av-statistics-https-files-blocked {
       type uint32;
     }
     leaf av-statistics-smtp-files-blocked {
       type uint32;
     }
     leaf av-statistics-smtps-files-blocked {
       type uint32;
     }
     leaf av-statistics-imap-files-blocked {
       type uint32;
     }
     leaf av-statistics-imaps-files-blocked {
       type uint32;
     }
     leaf av-statistics-smb-files-blocked {
       type uint32;
     }
     leaf av-statistics-total-files-permitted {
       type uint32;
     }
     leaf av-statistics-http-files-permitted {
       type uint32;
     }
     leaf av-statistics-https-files-permitted {
       type uint32;
     }
     leaf av-statistics-smtp-files-permitted {
       type uint32;
     }
     leaf av-statistics-smtps-files-permitted {
       type uint32;
     }
     leaf av-statistics-imap-files-permitted {
       type uint32;
     }
     leaf av-statistics-imaps-files-permitted {
       type uint32;
     }
     leaf av-statistics-smb-files-permitted {
       type uint32;
     }
   }
   grouping av-ml-statistics-block {
     leaf av-ml-scan-engine-version {
       type string;
     }
     leaf av-ml-scan-engine-update-time {
       type string;
     }
     leaf av-ml-statistics-total-files-scanned {
       type uint32;
     }
     leaf av-ml-statistics-http-files-scanned {
       type uint32;
     }
     leaf av-ml-statistics-https-files-scanned {
       type uint32;
     }
     leaf av-ml-statistics-smtp-files-scanned {
       type uint32;
     }
     leaf av-ml-statistics-smtps-files-scanned {
       type uint32;
     }
     leaf av-ml-statistics-imap-files-scanned {
       type uint32;
     }
     leaf av-ml-statistics-imaps-files-scanned {
       type uint32;
     }
     leaf av-ml-statistics-smb-files-scanned {
       type uint32;
     }
     leaf av-ml-statistics-total-files-found {
       type uint32;
     }
     leaf av-ml-statistics-http-files-found {
       type uint32;
     }
     leaf av-ml-statistics-https-files-found {
       type uint32;
     }
     leaf av-ml-statistics-smtp-files-found {
       type uint32;
     }
     leaf av-ml-statistics-smtps-files-found {
       type uint32;
     }
     leaf av-ml-statistics-imap-files-found {
       type uint32;
     }
     leaf av-ml-statistics-imaps-files-found {
       type uint32;
     }
     leaf av-ml-statistics-smb-files-found {
       type uint32;
     }
     leaf av-ml-statistics-total-files-blocked {
       type uint32;
     }
     leaf av-ml-statistics-http-files-blocked {
       type uint32;
     }
     leaf av-ml-statistics-https-files-blocked {
       type uint32;
     }
     leaf av-ml-statistics-smtp-files-blocked {
       type uint32;
     }
     leaf av-ml-statistics-smtps-files-blocked {
       type uint32;
     }
     leaf av-ml-statistics-imap-files-blocked {
       type uint32;
     }
     leaf av-ml-statistics-imaps-files-blocked {
       type uint32;
     }
     leaf av-ml-statistics-smb-files-blocked {
       type uint32;
     }
     leaf av-ml-statistics-total-files-permitted {
       type uint32;
     }
     leaf av-ml-statistics-http-files-permitted {
       type uint32;
     }
     leaf av-ml-statistics-https-files-permitted {
       type uint32;
     }
     leaf av-ml-statistics-smtp-files-permitted {
       type uint32;
     }
     leaf av-ml-statistics-smtps-files-permitted {
       type uint32;
     }
     leaf av-ml-statistics-imap-files-permitted {
       type uint32;
     }
     leaf av-ml-statistics-imaps-files-permitted {
       type uint32;
     }
     leaf av-ml-statistics-smb-files-permitted {
       type uint32;
     }
   }
   grouping user-group-debug-counters-block {
     leaf user-group-debug-counters-title {
       type string;
       description "User group debug counters";
     }
     list user-group-debug-counters-list {
       description "User group debug counters list";
       leaf user-group-debug-counter-name {
         type string;
       }
       leaf user-group-debug-counter-value {
         type uint32;
       }
     }
   }
   grouping authentication-table-counter-block {
     leaf total-auth-count {
       type uint32;
       description "Total count of authentication table records";
     }
     list domain_counter {
       leaf logical-domain {
         type string;
         description "Logical System";
       }
       leaf total-lsys-auth-count {
         type uint32;
         description "Total count of authentication table records in lsys";
       }
       leaf domain-name {
         type string;
         description "Domain name of auth entry";
       }
       leaf total-domain-count {
         type uint32;
         description "Num of auth entry for some domain";
       }
       leaf ad-count {
         type uint32;
         description "Num of ad auth entry for some domain";
       }
       leaf cp-count {
         type uint32;
         description "Num of cp auth entry for some domain";
       }
       leaf jims-count {
         type uint32;
         description "Num of jims auth entry for some domain";
       }
       leaf valid-count {
         type uint32;
         description "Num of valid state auth entry for some domain";
       }
       leaf pending-count {
         type uint32;
         description "Num of pending state auth entry for some domain";
       }
       leaf invalid-count {
         type uint32;
         description "Num of invalid state auth entry for some domain";
       }
       leaf init-count {
         type uint32;
         description "Num of init staste auth entry for some domain";
       }
     }
   }
   grouping authentication-table-by-address-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-all-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-all-by-group-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-all-by-user-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-cp-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-cp-by-group-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-cp-by-user-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ad-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ad-by-group-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ad-by-user-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ims-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ims-by-group-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping authentication-table-ims-by-user-block {
     list ad-auth-table {
       description "Information of the ad authentication table";
       leaf logical-domain {
         type string;
         description "Logical System";
       }
       leaf domain {
         type string;
         description "Domain name";
       }
       leaf total-count {
         type uint32;
         description "Total count of ad authentication table records";
       }
       list ad-authentication-info {
         leaf source-ip {
           type jt:ipaddr;
           description "Source address";
         }
         leaf-list user-name {
           type string;
           description "Name of the user";
         }
         leaf state {
           type string;
           description "State";
         }
         container ref-group-name-list {
           leaf-list ref-group-name {
             type string;
             description "Name of the interested group";
           }
         }
         leaf src-type {
           type string;
           description "Source";
         }
         leaf start-date {
           type string;
           description "Date user gained access";
         }
         leaf start-time {
           type string;
           description "Time user gained access";
         }
         leaf last-time {
           type string;
           description "Last updated timestamp(local display)";
         }
         leaf age-time {
           type string;
           description "Age time of user's access";
         }
         leaf forced-age-time {
           type string;
           description "Forced Age time of user's access";
         }
         container group-name-list {
           leaf-list group-name {
             type string;
             description "Name of the group";
           }
         }
       }
     }
   }
   grouping domain-controller-status-block {
     list domain-controller-info {
       description "Domain controller info";
       leaf domain {
         type string;
         description "Domain name";
       }
       list domain-controller {
         description "Domain-controller information";
         leaf dc-name {
           type string;
         }
         leaf address {
           type jt:ipaddr;
           description "Name of the address";
         }
         leaf status {
           type string;
           description "Status";
         }
         leaf reason {
           type string;
           description "Reason";
         }
       }
     }
   }
   grouping ip-user-mapping-statistics-block {
     list ip-user-mapping-statistics-per-domain {
       description "Ip-user-mapping statistics per domain";
       leaf domain {
         type string;
         description "Domain name";
       }
       list ip-user-mapping-statistics-per-dc {
         description "Ip-user-mapping statistics per domain controller";
         leaf host {
           type jt:ipaddr;
           description "Address of host";
         }
         leaf initial-eventlog-timespan {
           type uint32;
           description "Event log timespan";
         }
         leaf eventlog-scan-interval {
           type uint32;
           description "Event log scan interval";
         }
         leaf total-log-query-number {
           type uint32;
           description "Total log query number";
         }
         leaf failed-log-query-number {
           type uint32;
           description "Failed log query number";
         }
         leaf log-read-number {
           type uint32;
           description "Log read number";
         }
         leaf latest-timestamp {
           type string;
           description "Latest timestamp";
         }
       }
     }
   }
   grouping ip-user-probe-statistics-block {
     list ip-user-probe-statistics-per-domain {
       description "Ip-user-probe-statistics-per-domain";
       leaf domain {
         type string;
         description "Domain name";
       }
       leaf total-user-probe-number {
         type uint32;
         description "Total user probe number";
       }
       leaf failed-user-probe-number {
         type uint32;
         description "Failed user probe number";
       }
     }
   }
   grouping user-group-mapping-statistics-block {
     list user-group-mapping-statistics-per-domain {
       description "User-group-mapping statistics per domain";
       leaf domain {
         type string;
         description "Domain name";
       }
       list user-group-mapping-statistics-per-server {
         description "User-group-mapping status per server";
         leaf host {
           type jt:ipaddr;
           description "Address of host";
         }
         leaf port {
           type uint32;
           description "Port of server";
         }
         leaf total-query-number {
           type uint32;
           description "Total query number";
         }
         leaf failed-query-number {
           type uint32;
           description "Failed query number";
         }
       }
     }
   }
   grouping users-by-group-block {
     list domain-user-list {
       description "User list in AD";
       leaf domain {
         type string;
         description "Domain name";
       }
       leaf total-num {
         type uint32;
         description "Total num";
       }
       leaf user {
         type string;
         description "User";
       }
     }
   }
   grouping groups-by-user-block {
     list domain-group-list {
       description "Group list in AD";
       leaf domain {
         type string;
         description "Domain name";
       }
       leaf total-num {
         type uint32;
         description "Total num";
       }
       container domain-group {
         leaf group {
           type string;
           description "Group";
         }
       }
       container domain-interested-group {
         leaf interested-group {
           type string;
           description "Group referenced by policy";
         }
       }
     }
   }
   grouping user-group-mapping-status-block {
     list user-group-mapping-status-per-domain {
       description "User-group-mapping status per domain";
       leaf domain {
         type string;
         description "Domain name";
       }
       list user-group-mapping-status-per-server {
         description "User-group-mapping status per server";
         leaf host {
           type jt:ipaddr;
           description "Address of host";
         }
         leaf port {
           type uint32;
           description "Port of server";
         }
         leaf last-query-status {
           type string;
           description "Last query status";
         }
         leaf last-query-time {
           type string;
           description "Last query time";
         }
       }
     }
   }
   grouping fetching-status-block {
     leaf status {
       type string;
       description "Status";
     }
   }
   grouping periodic-fetching-status-block {
     leaf information {
       type string;
       description "Periodic fetching inforamtion";
     }
     list domain-group-list-status {
       description "Domain group list";
       leaf domain-name {
         type string;
         description "Domain name of auth entry";
       }
       leaf group {
         type string;
         description "Group";
       }
       leaf status {
         type string;
         description "Status";
       }
     }
   }
   grouping periodic-fetching-configuration-block {
     leaf timestamp {
       type string;
       description "Periodic fetching timestamp";
     }
     list domain-group-list-configuration {
       description "Fetch domain group list configuration";
       leaf domain-name {
         type string;
         description "Domain name of auth entry";
       }
       leaf group {
         type string;
         description "Group";
       }
     }
   }
   grouping refreshing-status-block {
     leaf status {
       type string;
       description "Status";
     }
   }
   grouping cp-user-query-statistics-block {
     leaf authentication-source {
       type string;
       description "Authentication source";
     }
     leaf web-server {
       type string;
       description "Web server address";
     }
     leaf access-token {
       type string;
       description "Access token";
     }
     leaf query-sent-number {
       type uint32;
       description "CleaPass query sent number";
     }
     leaf response-recv-number {
       type uint32;
       description "Total query response received number";
     }
     leaf error-response-number {
       type uint32;
       description "Error query response received number";
     }
     leaf last-response-time {
       type string;
       description "Last response time";
     }
   }
   grouping cp-user-query-status-block {
     leaf authentication-source {
       type string;
       description "Authentication source";
     }
     leaf web-server {
       type string;
       description "Web server address";
     }
     leaf server-status {
       type string;
       description "Web server status";
     }
     leaf connection-number {
       type uint32;
       description "Current connection number";
     }
   }
   grouping device-identity-table-all-block {
     list device-id-table {
       description "Information of the device identity table";
       leaf logical-domain {
         type string;
         description "Logical System";
       }
       leaf domain {
         type string;
         description "Domain name";
       }
       leaf total-device-count {
         type uint32;
         description "Total count of device identity table records";
       }
       list device-info {
         leaf device-source-ip {
           type string;
           description "Source ip address";
         }
         leaf-list device-name {
           type string;
           description "Name of the device";
         }
         container device-group-name-list {
           leaf-list device-group-name {
             type string;
             description "Name of the device group";
           }
         }
         container ref-profile-list {
           leaf-list ref-profile {
             type string;
             description "Name of the profile";
           }
         }
         container dev-param-list {
           leaf-list dev-param {
             type string;
             description "Device parameters";
           }
         }
       }
     }
   }
   grouping device-identity-table-by-address-block {
     list device-id-table {
       description "Information of the device identity table";
       leaf logical-domain {
         type string;
         description "Logical System";
       }
       leaf domain {
         type string;
         description "Domain name";
       }
       leaf total-device-count {
         type uint32;
         description "Total count of device identity table records";
       }
       list device-info {
         leaf device-source-ip {
           type string;
           description "Source ip address";
         }
         leaf-list device-name {
           type string;
           description "Name of the device";
         }
         container device-group-name-list {
           leaf-list device-group-name {
             type string;
             description "Name of the device group";
           }
         }
         container ref-profile-list {
           leaf-list ref-profile {
             type string;
             description "Name of the profile";
           }
         }
         container dev-param-list {
           leaf-list dev-param {
             type string;
             description "Device parameters";
           }
         }
       }
     }
   }
   grouping device-identity-table-by-device-id-block {
     list device-id-table {
       description "Information of the device identity table";
       leaf logical-domain {
         type string;
         description "Logical System";
       }
       leaf domain {
         type string;
         description "Domain name";
       }
       leaf total-device-count {
         type uint32;
         description "Total count of device identity table records";
       }
       list device-info {
         leaf device-source-ip {
           type string;
           description "Source ip address";
         }
         leaf-list device-name {
           type string;
           description "Name of the device";
         }
         container device-group-name-list {
           leaf-list device-group-name {
             type string;
             description "Name of the device group";
           }
         }
         container ref-profile-list {
           leaf-list ref-profile {
             type string;
             description "Name of the profile";
           }
         }
         container dev-param-list {
           leaf-list dev-param {
             type string;
             description "Device parameters";
           }
         }
       }
     }
   }
   grouping device-identity-table-by-group-block {
     list device-id-table {
       description "Information of the device identity table";
       leaf logical-domain {
         type string;
         description "Logical System";
       }
       leaf domain {
         type string;
         description "Domain name";
       }
       leaf total-device-count {
         type uint32;
         description "Total count of device identity table records";
       }
       list device-info {
         leaf device-source-ip {
           type string;
           description "Source ip address";
         }
         leaf-list device-name {
           type string;
           description "Name of the device";
         }
         container device-group-name-list {
           leaf-list device-group-name {
             type string;
             description "Name of the device group";
           }
         }
         container ref-profile-list {
           leaf-list ref-profile {
             type string;
             description "Name of the profile";
           }
         }
         container dev-param-list {
           leaf-list dev-param {
             type string;
             description "Device parameters";
           }
         }
       }
     }
   }
   grouping jims-query-statistics-block {
     list jims-query-statistics-per-server {
       description "Identity management query statistics per server";
       leaf server-type {
         type string;
         description "Identity management server type";
       }
       leaf server-address {
         type string;
         description "Identity management server address";
       }
       leaf batch-queries-sent {
         type uint32;
         description "Batch queries sent";
       }
       leaf batch-queries-returned {
         type uint32;
         description "Total number of received batch query responses";
       }
       leaf batch-query-error-received {
         type uint32;
         description "Error number of received batch query responses";
       }
       leaf batch-last-response {
         type string;
         description "Last response time of batch query";
       }
       leaf auth-entry-lookup-queries-sent {
         type uint32;
         description "Total number of batch queries sent";
       }
       leaf auth-entry-lookup-queries-returned {
         type uint32;
         description "Total number of received ip query responses";
       }
       leaf auth-entry-lookup-query-errors-encountered {
         type uint32;
         description "Error number of received ip query responses";
       }
       leaf auth-entry-lookup-last-response {
         type string;
         description "Last response time of ip query";
       }
       leaf auth-entry-lookup-time-avg {
         type uint32;
         description "Auth entry lookup time, average";
       }
       leaf auth-entry-lookup-time-max {
         type uint32;
         description "Auth entry lookup time, max";
       }
       leaf cert-revocation-req-sent {
         type uint32;
         description "Certificate revocation requests sent";
       }
       leaf cert-revocation-resp-recvd {
         type uint32;
         description "Certificate revocation responses received";
       }
       leaf certs-revoked {
         type uint32;
         description "Certificates revoked";
       }
     }
   }
   grouping jims-query-status-block {
     list jims-query-status-per-server {
       description "Identity management query status per server";
       leaf server-type {
         type string;
         description "Identity management server type";
       }
       leaf fqdn-name {
         type string;
         description "Identity management FQDN name";
       }
       leaf server-address {
         type string;
         description "Identity management server address";
       }
       leaf server-port {
         type uint32;
         description "Identity management server port";
       }
       leaf source {
         type string;
         description "Source address";
       }
       leaf interface-name {
         type string;
         description "Interface name";
       }
       leaf routing-instance {
         type string;
         description "Routing instance name";
       }
       leaf connect-method {
         type string;
         description "Connection method";
       }
       leaf connect-status {
         type string;
         description "Server status";
       }
       leaf recv-status-msg {
         type string;
         description "Last received status message";
       }
       leaf token-string {
         type string;
         description "Access token";
       }
       leaf token-expire-time {
         type string;
         description "Token expire time";
       }
     }
   }
   grouping jims-more-info-block {
     list jims-more-info-per-server {
       description "Identity management query status per server";
       leaf server-type {
         type string;
         description "Identity management server type";
       }
       leaf server-address {
         type string;
         description "Identity management server address";
       }
       leaf online-to-offline-number {
         type uint32;
         description "Number of switching from online to offline";
       }
     }
   }
   grouping jims-validator-query-statistics-block {
     list jims-validator-query-statistics-per-server {
       description "Identity management jims validator query statistics per server";
       leaf server-address {
         type string;
         description "Identity management server address";
       }
       leaf validator-query-sent-number {
         type uint32;
         description "Validator query sent number";
       }
       leaf validator-query-response-recv-number {
         type uint32;
         description "Total number of received validator query responses";
       }
       leaf validator-query-error-response-number {
         type uint32;
         description "Error number of received validator query responses";
       }
       leaf group-query-sent-number {
         type uint32;
         description "Group query sent number";
       }
       leaf group-query-response-recv-number {
         type uint32;
         description "Total number of received group query responses";
       }
       leaf group-query-error-response-number {
         type uint32;
         description "Error number of received group query responses";
       }
     }
   }
   grouping jims-validator-query-status-block {
     list jims-validator-query-status-per-server {
       description "Identity management jims validator query status per server";
       leaf server-address {
         type string;
         description "Identity management server address";
       }
       leaf server-port {
         type uint32;
         description "Identity management server port";
       }
       leaf connect-method {
         type string;
         description "Connection method";
       }
       leaf connect-status {
         type string;
         description "Server status";
       }
       leaf recv-status-msg {
         type string;
         description "Last received status message";
       }
       leaf token-string {
         type string;
         description "Access token";
       }
       leaf token-expire-time {
         type string;
         description "Token expire time";
       }
     }
   }
   grouping ld-jims-query-statistics-block {
     leaf ld-jims-query-server-name {
       type string;
       description "Logical domain server name inforamtion";
     }
     list ld-jims-query-statistics-per-server {
       description "Logical domain identity management query statistics per server";
       leaf server-type {
         type string;
         description "Identity management server type";
       }
       leaf server-address {
         type string;
         description "Identity management server address";
       }
       leaf batch-queries-sent {
         type uint32;
         description "Batch queries sent";
       }
       leaf batch-queries-returned {
         type uint32;
         description "Total number of received batch query responses";
       }
       leaf batch-query-error-received {
         type uint32;
         description "Error number of received batch query responses";
       }
       leaf batch-last-response {
         type string;
         description "Last response time of batch query";
       }
       leaf auth-entry-lookup-queries-sent {
         type uint32;
         description "Total number of batch queries sent";
       }
       leaf auth-entry-lookup-queries-returned {
         type uint32;
         description "Total number of received ip query responses";
       }
       leaf auth-entry-lookup-query-errors-encountered {
         type uint32;
         description "Error number of received ip query responses";
       }
       leaf auth-entry-lookup-last-response {
         type string;
         description "Last response time of ip query";
       }
       leaf auth-entry-lookup-time-avg {
         type uint32;
         description "Auth entry lookup time, average";
       }
       leaf auth-entry-lookup-time-max {
         type uint32;
         description "Auth entry lookup time, max";
       }
       leaf cert-revocation-req-sent {
         type uint32;
         description "Certificate revocation requests sent";
       }
       leaf cert-revocation-resp-recvd {
         type uint32;
         description "Certificate revocation responses received";
       }
       leaf certs-revoked {
         type uint32;
         description "Certificates revoked";
       }
     }
   }
   grouping ld-jims-query-status-block {
     leaf ld-query-server-name {
       type string;
       description "Logical domain server name inforamtion";
     }
     list ld-jims-query-status-per-server {
       description "Logical domain identity management query status per server";
       leaf server-type {
         type string;
         description "Identity management server type";
       }
       leaf server-address {
         type string;
         description "Identity management server address";
       }
       leaf server-port {
         type uint32;
         description "Identity management server port";
       }
       leaf connect-method {
         type string;
         description "Connection method";
       }
       leaf connect-status {
         type string;
         description "Server status";
       }
       leaf recv-status-msg {
         type string;
         description "Last received status message";
       }
       leaf token-string {
         type string;
         description "Access token";
       }
       leaf token-expire-time {
         type string;
         description "Token expire time";
       }
     }
   }
   grouping swgauth-profile-statistics-block {
     leaf swgauth-profile-name {
       type string;
     }
     leaf swgauth-profile-total-sessions {
       type uint32;
     }
     leaf swgauth-profile-current-sessions {
       type uint32;
     }
     leaf swgauth-profile-http-sessions {
       type uint32;
     }
     leaf swgauth-profile-https-sessions {
       type uint32;
     }
     leaf swgauth-profile-not-supported-sessions {
       type uint32;
     }
     leaf swgauth-profile-on-prem-captive-portal-redirect {
       type uint32;
     }
     leaf swgauth-profile-roaming-captive-portal-redirect {
       type uint32;
     }
     leaf swgauth-profile-roaming-uid-not-rcvd-redirect {
       type uint32;
     }
     leaf swgauth-profile-roaming-uid-reset-redirect {
       type uint32;
     }
     leaf swgauth-profile-roaming-sessions-processed {
       type uint32;
     }
     leaf swgauth-profile-preflight-sessions-handled {
       type uint32;
     }
     leaf swgauth-profile-cors-sessions-handled {
       type uint32;
     }
     leaf swgauth-profile-nocors-sessions-handled {
       type uint32;
     }
     leaf swgauth-profile-sessions-rejected {
       type uint32;
     }
     leaf swgauth-profile-denied-pkts {
       type uint32;
     }
     leaf swgauth-profile-sessions-denied {
       type uint32;
     }
     leaf swgauth-profile-sessions-destroyed {
       type uint32;
     }
   }
   grouping swgauth-captiveportal-redirect-statistics-block {
     leaf swgauth-auth-entries-lru-evicted {
       type uint32;
     }
     leaf swgauth-session-dropped-max-limit {
       type uint32;
     }
     leaf swgauth-auth-entries {
       type uint32;
     }
     leaf swgauth-avg-enc-time {
       type uint32;
     }
     leaf swgauth-avg-dec-time {
       type uint32;
     }
   }
   grouping swgauth-captiveportal-connection-statistics-block {
     leaf swgauth-certificate-status {
       type string;
     }
     leaf swgauth-certificate-fetch-failed {
       type uint32;
     }
     leaf swgauth-certificate-fetched {
       type uint32;
     }
   }
   grouping web-transparent-proxy-session-information-block {
     list web-transparent-proxy-session {
       leaf client-session-identifier {
         type uint64;
         description "Session identifier";
       }
       leaf proxy-session-identifier {
         type uint64;
         description "Session identifier";
       }
       leaf client-src-address {
         type jt:ipaddr;
         description "Source address";
       }
       leaf client-src-port {
         type uint32;
         description "Source port";
       }
       leaf client-dst-address {
         type jt:ipaddr;
         description "Destination address";
       }
       leaf client-dst-port {
         type uint32;
         description "Destination port";
       }
       leaf proxy-src-address {
         type jt:ipaddr;
         description "Source address";
       }
       leaf proxy-src-port {
         type uint32;
         description "Source port";
       }
       leaf proxy-dst-address {
         type jt:ipaddr;
         description "Destination address";
       }
       leaf proxy-dst-port {
         type uint32;
         description "Destination port";
       }
       leaf proxy-http-request {
         type string;
         description "Http request";
       }
       leaf proxy-dyn-app-name {
         type string;
         description "App requestd";
       }
     }
   }
   grouping web-transparent-proxy-statistics-block {
     leaf active-transparent-proxy-sessions {
       type uint64;
       description "Active transparent proxy sessions";
     }
     leaf active-passthru-sessions {
       type uint64;
       description "Active passthrough sessions";
     }
     leaf active-http-passthru-sessions {
       type uint64;
       description "Active HTTP passthrough sessions";
     }
     leaf active-https-passthru-sessions {
       type uint64;
       description "Active HTTPS passthrough sessions";
     }
     leaf active-dns-cache-size {
       type uint64;
       description "Active DNS cache size";
     }
     leaf total-transparent-proxy-sessions {
       type uint64;
       description "Total transparent proxy sessions";
     }
     leaf total-passthru-sessions {
       type uint64;
       description "Total passthrough sessions";
     }
     leaf total-http-passthru-sessions {
       type uint64;
       description "Total HTTP passthrough sessions";
     }
     leaf total-https-passthru-sessions {
       type uint64;
       description "Total HTTPS passthrough sessions";
     }
   }
   grouping web-explicit-proxy-session-information-block {
     list web-explicit-proxy-session {
       leaf client-session-identifier {
         type uint64;
         description "Session identifier";
       }
       leaf proxy-session-identifier {
         type uint64;
         description "Session identifier";
       }
       leaf client-src-address {
         type jt:ipaddr;
         description "Source address";
       }
       leaf client-src-port {
         type uint32;
         description "Source port";
       }
       leaf client-dst-address {
         type jt:ipaddr;
         description "Destination address";
       }
       leaf client-dst-port {
         type uint32;
         description "Destination port";
       }
       leaf proxy-src-address {
         type jt:ipaddr;
         description "Source address";
       }
       leaf proxy-src-port {
         type uint32;
         description "Source port";
       }
       leaf proxy-dst-address {
         type jt:ipaddr;
         description "Destination address";
       }
       leaf proxy-dst-port {
         type uint32;
         description "Destination port";
       }
       leaf proxy-http-request {
         type string;
         description "Http request";
       }
       leaf proxy-dyn-app-name {
         type string;
         description "App requestd";
       }
       leaf client-tcp-status {
         type string;
         description "TCP 3-way handshake status";
       }
       leaf client-timeout {
         type uint32;
         description "Session timeout";
       }
       leaf client-sess-state {
         type string;
         description "Client session state";
       }
       leaf client-in-pkt-cnt {
         type uint64;
         description "In Packet count";
       }
       leaf client-in-byte-cnt {
         type uint64;
         description "In Byte count";
       }
       leaf client-out-pkt-cnt {
         type uint64;
         description "Out Packet count";
       }
       leaf client-out-byte-cnt {
         type uint64;
         description "Out Byte count";
       }
       leaf proxy-tcp-status {
         type string;
         description "TCP 3-way handshake status";
       }
       leaf proxy-syn-sent-status {
         type string;
         description "TCP SYN message sent status";
       }
       leaf proxy-syn-ack-recvd-status {
         type string;
         description "TCP SYN-ACK message received status";
       }
       leaf proxy-ack-sent-status {
         type string;
         description "TCP ACK message sent status";
       }
       leaf proxy-timeout {
         type uint32;
         description "Session timeout";
       }
       leaf proxy-sess-state {
         type string;
         description "Proxy session state";
       }
       leaf proxy-in-pkt-cnt {
         type uint64;
         description "In Packet count";
       }
       leaf proxy-in-byte-cnt {
         type uint64;
         description "In Byte count";
       }
       leaf proxy-out-pkt-cnt {
         type uint64;
         description "Out Packet count";
       }
       leaf proxy-out-byte-cnt {
         type uint64;
         description "Out Byte count";
       }
       leaf ssl-proxy-status {
         type string;
         description "SSL proxy status";
       }
       leaf dns-resolve-status {
         type string;
         description "DNS resolve status";
       }
       leaf proxy-flags-one {
         type uint32;
         description "First set of flags";
       }
       leaf proxy-flags-two {
         type uint32;
         description "Second set of flags";
       }
     }
   }
   grouping web-explicit-proxy-statistics-block {
     leaf active-explicit-https-proxy-sessions {
       type uint64;
       description "Total HTTPS passthrough sessions";
     }
     leaf active-explicit-http-proxy-sessions {
       type uint64;
       description "Total HTTPS passthrough sessions";
     }
     leaf total-explicit-https-proxy-sessions {
       type uint64;
       description "Total HTTPS passthrough sessions";
     }
     leaf total-explicit-http-proxy-sessions {
       type uint64;
       description "Total HTTPS passthrough sessions";
     }
     leaf explicit-proxy-rate-limit-session-drops {
       type uint64;
       description "Total explicit proxy sessions dropped due to rate limit";
     }
     leaf explicit-proxy-system-port-conflict {
       type uint64;
       description "Explicit proxy system port conflicts";
     }
   }
   grouping web-proxy-dns-fc-entries-block {
     list web-proxy-dns-fc {
       description "DNS cache of a DNS name";
       leaf web-proxy-dns-fc-dns-name {
         type string;
         description "DNS name";
       }
       list web-proxy-dns-fc-address {
         description "DNS address";
         leaf web-proxy-dns-fc-address-family {
           type string;
           description "IP address family";
         }
         leaf web-proxy-dns-fc-address-ttl {
           type int32;
           description "TTL value of this address";
         }
         container web-proxy-dns-fc-address-table {
           description "DNS address table";
           leaf-list web-proxy-dns-fc-address-entry {
             type string;
             description "IP address entry";
           }
         }
       }
     }
   }
   grouping web-proxy-dns-fc-statistics-block {
     leaf dns-fc-active-status {
       type string;
       description "DNS status";
     }
     leaf dns-fc-active-entries {
       type uint64;
       description "Active DNS Forwarding Cache Entries";
     }
     leaf dns-fc-total {
       type uint64;
       description "Total DNS Entries";
     }
     leaf dns-fc-cache-hits {
       type uint64;
       description "Total DNS Cache hits";
     }
     leaf dns-fc-cache-miss {
       type uint64;
       description "Total DNS Cache miss";
     }
     leaf dns-fc-add-failed {
       type uint64;
       description "Total DNS Cache Add failed";
     }
   }
   grouping web-proxy-dns-gc-statistics-block {
     leaf dns-gc-active-status {
       type string;
       description "DNS status";
     }
     leaf dns-gc-active-entries {
       type uint32;
       description "Active DNS Forwarding Cache Entries";
     }
     leaf dns-gc-total {
       type uint32;
       description "Total DNS Entries";
     }
     leaf dns-gc-cache-hits {
       type uint32;
       description "Total DNS Cache hits";
     }
     leaf dns-gc-cache-miss {
       type uint32;
       description "Total DNS Cache miss";
     }
     leaf dns-gc-res-req-fail {
       type uint32;
       description "Total DNS resolve req send fail";
     }
     leaf dns-gc-res-req-timeout {
       type uint32;
       description "Total DNS resolve req timeout";
     }
   }
   grouping lrf-statistics-summary-block {
     list lrf-statistics {
       description "LRF statistics";
       leaf interface-name {
         type string;
         description "Name of the adaptive services interface";
       }
       leaf flow-packets {
         type int32;
         description "Flow packets";
       }
       leaf flow-bytes {
         type int32;
         description "Flow bytes";
       }
       leaf active-flows {
         type int32;
         description "Active flows";
       }
       leaf total-flows {
         type int32;
         description "Total flows";
       }
     }
   }
   grouping lrf-collector-statistics-summary-block {
     list lrf-collector-statistics {
       description "LRF collector statistics";
       leaf interface-name {
         type string;
         description "Name of the adaptive services interface";
       }
       leaf tmpl-reg {
         type int32;
         description "Templates registered";
       }
       leaf tmpl-reg-failures {
         type int32;
         description "Template registration failures";
       }
       leaf tmpl-active {
         type int32;
         description "Templates active";
       }
       leaf sessions-received {
         type int32;
         description "Sessions received";
       }
       leaf sessions-ignored {
         type int32;
         description "Sessions ignored";
       }
       leaf records-logged {
         type int32;
         description "Records logged";
       }
       leaf rec-export {
         type int32;
         description "Records exported";
       }
       leaf rec-export-failures {
         type int32;
         description "Record export failures";
       }
       leaf rec-export-volume {
         type int32;
         description "Records exported for volume";
       }
       leaf rec-export-time {
         type int32;
         description "Records exported for time";
       }
       leaf rec-export-session-close {
         type int32;
         description "Records exported for session close";
       }
     }
   }
   grouping lrf-rule-statistics-summary-block {
     list lrf-rule-statistics {
       description "LRF rule statistics";
       leaf interface-name {
         type string;
         description "Name of the adaptive services interface";
       }
       leaf rule-name {
         type string;
         description "Rule name";
       }
       leaf rule-tmpl-name {
         type string;
         description "Template name";
       }
       leaf rule-tmpl-reg {
         type int32;
         description "Templates registered";
       }
       leaf rule-tmpl-reg-failures {
         type int32;
         description "Template registration failures";
       }
       leaf rule-coll-name {
         type string;
         description "Collector name";
       }
       leaf rule-sessions-received {
         type int32;
         description "Sessions received";
       }
       leaf rule-sessions-ignored {
         type int32;
         description "Sessions ignored";
       }
       leaf rule-sessions-logged {
         type int32;
         description "Sessions logged";
       }
       leaf rule-rec-export {
         type int32;
         description "Records exported";
       }
       leaf rule-rec-export-failures {
         type int32;
         description "Record export failures";
       }
       leaf rule-rec-export-volume {
         type int32;
         description "Records exported for volume";
       }
       leaf rule-rec-export-time {
         type int32;
         description "Records exported for time";
       }
       leaf rule-rec-export-session-close {
         type int32;
         description "Records exported for session close";
       }
     }
   }
   grouping lrf-template-block {
     leaf-list export-field {
       type string;
     }
     leaf-list export-field-id {
       type int32;
     }
     leaf-list export-field-len {
       type int32;
     }
     leaf-list export-field-vendor {
       type string;
     }
   }
   grouping services-accounting-information-block {
     leaf interface-name {
       type string;
       description "Physical interface name";
     }
     leaf local-index {
       type int32;
       description "Local physical interface index";
     }
     leaf service-name {
       type string;
       description "Service name";
     }
     leaf pic-status {
       type string;
       description "Current interface state";
     }
     container usage-information {
       leaf interface-name {
         type string;
         description "Physical interface name";
       }
       leaf uptime {
         type int32;
         description "CPU uptime, in milliseconds";
       }
       leaf inttime {
         type int32;
         description "CPU interrupt time, in microseconds";
       }
       leaf five-second-load {
         type int32;
         description "5-second load";
       }
       leaf one-minute-load {
         type int32;
         description "1-minute load";
       }
     }
     container memory-information {
       leaf interface-name {
         type string;
         description "Physical interface name";
       }
       leaf allocation-count {
         type int32;
         description "Flow record allocations";
       }
       leaf free-count {
         type int32;
         description "Flow record frees";
       }
       leaf allocations-per-second {
         type int32;
         description "Flow record allocations per second";
       }
       leaf frees-per-second {
         type int32;
         description "Flow record frees per second";
       }
       leaf memory-used {
         type int32;
         description "Total memory used";
       }
       leaf memory-free {
         type int32;
         description "Total memory free";
       }
       leaf v9-memory-used {
         type int32;
         description "Memory used by v9";
       }
       leaf maximum-allocated {
         type int32;
         description "Maximum flow records allocated";
       }
     }
     container flow-information {
       leaf interface-name {
         type string;
         description "Physical interface name";
       }
       leaf local_ifd_index {
         type int32;
         description "Local interface index";
       }
       leaf flow-packets {
         type int32;
         description "Flow packets";
       }
       leaf flow-bytes {
         type int32;
         description "Flow bytes";
       }
       leaf flow-packets-ten-second-rate {
         type int32;
         description "Flow packets 10-second rate";
       }
       leaf flow-bytes-ten-second-rate {
         type int32;
         description "Flow bytes 10-second rate";
       }
       leaf active-flows {
         type int32;
         description "Active flows";
       }
       leaf flows {
         type int32;
         description "Flows";
       }
       leaf flows-exported {
         type int32;
         description "Flows exported";
       }
       leaf flow-packets-exported {
         type int32;
         description "Flows packets exported";
       }
       leaf flows-expired {
         type int32;
         description "Flows inactive timed out";
       }
       leaf flows-aged {
         type int32;
         description "Flows active timed out";
       }
     }
     container vmon-mdi-template {
       leaf mdi-template-name {
         type string;
         description "Template Name";
       }
       leaf mdi-template-index {
         type uint32;
         description "Template Index";
       }
       leaf mdi-interval-duration {
         type uint32;
         description "Interval Duration";
       }
       leaf mdi-inactive-timeout {
         type uint32;
         description "Inactive Timeout";
       }
       leaf mdi-media-packet-count-in-l3 {
         type uint32;
         description "Media Packets Count in Layer3";
       }
       leaf mdi-media-packet-size {
         type uint32;
         description "Media Packet Size";
       }
       leaf mdi-media-rate {
         type uint32;
         description "Media Rate";
       }
       leaf mdi-l3-packet-rate {
         type uint32;
         description "Layer3 Packet Rate";
       }
       leaf mdi-df-status {
         type string;
         description "DF Enabled/Disabled";
       }
       leaf mdi-mlr-status {
         type string;
         description "MLR Enabled/Disabled";
       }
       leaf mdi-mrv-status {
         type string;
         description "MRV Enabled/Disabled";
       }
       leaf mdi-df-info-threshold {
         type string;
         description "DF Info level threshold";
       }
       leaf mdi-df-warning-threshold {
         type string;
         description "DF Warning level threshold";
       }
       leaf mdi-df-critical-threshold {
         type string;
         description "DF Ciritical level threshold";
       }
       leaf mdi-mlr-info-threshold-packet-count {
         type string;
         description "MLR Info level threshold";
       }
       leaf mdi-mlr-warning-threshold-packet-count {
         type string;
         description "MLR Warning level threshold";
       }
       leaf mdi-mlr-critical-threshold-packet-count {
         type string;
         description "MLR Ciritical level threshold";
       }
       leaf mdi-mlr-info-threshold-percentage {
         type string;
         description "MLR Info level threshold in percentage";
       }
       leaf mdi-mlr-warning-threshold-percentage {
         type string;
         description "MLR Warning level threshold in percentage";
       }
       leaf mdi-mlr-critical-threshold-percentage {
         type string;
         description "MLR Ciritical level threshold in percentage";
       }
       leaf mdi-mrv-info-threshold {
         type string;
         description "MRV Info level threshold";
       }
       leaf mdi-mrv-warning-threshold {
         type string;
         description "MRV Warning level threshold";
       }
       leaf mdi-mrv-critical-threshold {
         type string;
         description "MRV Ciritical level threshold";
       }
     }
     container vmon-mdi-stats {
       leaf fpc-slot {
         type int32;
         description "FPC Slot";
       }
       leaf tfeb-slot {
         type int32;
         description "TFEB Slot";
       }
       leaf afeb-slot {
         type int32;
         description "AFEB Slot";
       }
       leaf mdi-active-flows {
         type uint32;
         description "Active flows";
       }
       leaf mdi-total-inserted-flows {
         type uint32;
         description "Total Inserted flows";
       }
       leaf mdi-total-deleted-flows {
         type uint32;
         description "Total Deleted flows";
       }
       leaf mdi-flow-packets-count {
         type uint32;
         description "Total Packets Count";
       }
       leaf mdi-flow-bytes-count {
         type uint32;
         description "Total Bytes Count";
       }
       leaf mdi-df-alarm-count {
         type uint32;
         description "DF alarm count";
       }
       leaf mdi-df-info-level-alarm-count {
         type uint32;
         description "DF info level alarm count";
       }
       leaf mdi-df-warning-level-alarm-count {
         type uint32;
         description "DF warning level alarm count";
       }
       leaf mdi-df-critical-level-alarm-count {
         type uint32;
         description "DF critical level alarm count";
       }
       leaf mdi-mlr-alarm-count {
         type uint32;
         description "MLR alarm count";
       }
       leaf mdi-mlr-info-level-alarm-count {
         type uint32;
         description "MLR info level alarm count";
       }
       leaf mdi-mlr-warning-level-alarm-count {
         type uint32;
         description "MLR warning level alarm count";
       }
       leaf mdi-mlr-critical-level-alarm-count {
         type uint32;
         description "MLR critical level alarm count";
       }
       leaf mdi-mrv-alarm-count {
         type uint32;
         description "MRV alarm count";
       }
       leaf mdi-mrv-info-level-alarm-count {
         type uint32;
         description "MRV info level alarm count";
       }
       leaf mdi-mrv-warning-level-alarm-count {
         type uint32;
         description "MRV warning level alarm count";
       }
       leaf mdi-mrv-critical-level-alarm-count {
         type uint32;
         description "MRV critical level alarm count";
       }
     }
     container vmon-mdi-errors {
       leaf fpc-slot {
         type int32;
         description "FPC Slot";
       }
       leaf tfeb-slot {
         type int32;
         description "TFEB Slot";
       }
       leaf afeb-slot {
         type int32;
         description "AFEB Slot";
       }
       leaf mdi-flow-insert-error-count {
         type uint32;
         description "Flow insert error";
       }
       leaf mdi-flow-policer-error-count {
         type uint32;
         description "Flow policer error";
       }
       leaf mdi-unsupported-media-pkt-count {
         type uint32;
         description "Unsupported media packets count";
       }
       leaf mdi-pid-limit-exceeded {
         type uint32;
         description "PID limit execeeded";
       }
       leaf mdi-fragmented-pkt-count {
         type uint32;
         description "Fragmented packet count";
       }
       leaf mdi-max-label-exceed-count {
         type uint32;
         description "Maximum label exceed count";
       }
       leaf mdi-options-pkt-count {
         type uint32;
         description "Options packet skip MDI count";
       }
     }
     container vmon-mdi-flow-brief-split-df-mlr {
       leaf mdi-flow-sno {
         type uint32;
         description "Flow row number";
       }
       leaf mdi-source-address {
         type string;
         description "Source address of flow";
       }
       leaf mdi-source-port {
         type uint32;
         description "Source port of flow";
       }
       leaf mdi-destination-address {
         type string;
         description "Destination address of flow";
       }
       leaf mdi-destination-port {
         type uint32;
         description "Destination port of flow";
       }
       leaf mdi-flow-direction {
         type string;
         description "MDI Flow Direction";
       }
       leaf mdi-flow-type {
         type string;
         description "Flow Type";
       }
       leaf mdi-last-df {
         type string;
         description "Last DF";
       }
       leaf mdi-last-mlr {
         type string;
         description "Last MLR";
       }
       leaf mdi-avg-df {
         type string;
         description "Average DF";
       }
       leaf mdi-avg-mlr {
         type string;
         description "Average MLR";
       }
       leaf mdi-last-mrv {
         type string;
         description "Last MRV";
       }
       leaf mdi-avg-mrv {
         type string;
         description "Average MRV";
       }
       leaf mdi-interface-name {
         type string;
         description "Interface Name";
       }
       leaf mdi-template-name {
         type string;
         description "Template Name";
       }
       leaf mdi-flow-identifier {
         type uint32;
         description "Unique Identifier of flow";
       }
     }
     container vmon-mdi-flow-detail-split-df-mlr {
       leaf mdi-source-address {
         type string;
         description "Source address of flow";
       }
       leaf mdi-source-port {
         type uint32;
         description "Source port of flow";
       }
       leaf mdi-destination-address {
         type string;
         description "Destination address of flow";
       }
       leaf mdi-destination-port {
         type uint32;
         description "Destination port of flow";
       }
       leaf mdi-last-df {
         type string;
         description "Last DF";
       }
       leaf mdi-last-mlr {
         type string;
         description "Last MLR";
       }
       leaf mdi-avg-df {
         type string;
         description "Average DF";
       }
       leaf mdi-avg-mlr {
         type string;
         description "Average MLR";
       }
       leaf mdi-last-mrv {
         type string;
         description "Last MRV";
       }
       leaf mdi-avg-mrv {
         type string;
         description "Average MRV";
       }
       leaf mdi-interface-name {
         type string;
         description "Interface Name";
       }
       leaf mdi-template-name {
         type string;
         description "Template Name";
       }
       leaf mdi-flow-direction {
         type string;
         description "MDI Flow Direction";
       }
       leaf mdi-flow-type {
         type string;
         description "Flow Type";
       }
       leaf mdi-mpls-labels {
         type string;
         description "MPLS labels";
       }
       leaf mdi-record-count {
         type uint32;
         description "Count of MDI records";
       }
       leaf mdi-pid-count {
         type string;
         description "PID Count";
       }
       leaf mdi-flow-identifier {
         type uint32;
         description "Unique Identifier of flow";
       }
     }
     container vmon-mdi-flow-brief {
       leaf mdi-flow-sno {
         type uint32;
         description "Flow row number";
       }
       leaf mdi-source-address {
         type string;
         description "Source address of flow";
       }
       leaf mdi-source-port {
         type uint32;
         description "Source port of flow";
       }
       leaf mdi-destination-address {
         type string;
         description "Destination address of flow";
       }
       leaf mdi-destination-port {
         type uint32;
         description "Destination port of flow";
       }
       leaf mdi-flow-direction {
         type string;
         description "MDI Flow Direction";
       }
       leaf mdi-flow-type {
         type string;
         description "Flow Type";
       }
       leaf mdi-last-df-mlr {
         type string;
         description "Last DF:MLR";
       }
       leaf mdi-avg-df-mlr {
         type string;
         description "Average DF:MLR";
       }
       leaf mdi-last-mrv {
         type string;
         description "Last MRV";
       }
       leaf mdi-avg-mrv {
         type string;
         description "Average MRV";
       }
       leaf mdi-interface-name {
         type string;
         description "Interface Name";
       }
       leaf mdi-template-name {
         type string;
         description "Template Name";
       }
       leaf mdi-flow-identifier {
         type uint32;
         description "Unique Identifier of flow";
       }
     }
     container vmon-mdi-flow-detail {
       leaf mdi-source-address {
         type string;
         description "Source address of flow";
       }
       leaf mdi-source-port {
         type uint32;
         description "Source port of flow";
       }
       leaf mdi-destination-address {
         type string;
         description "Destination address of flow";
       }
       leaf mdi-destination-port {
         type uint32;
         description "Destination port of flow";
       }
       leaf mdi-last-df-mlr {
         type string;
         description "Last DF:MLR";
       }
       leaf mdi-avg-df-mlr {
         type string;
         description "Average DF:MLR";
       }
       leaf mdi-last-mrv {
         type string;
         description "Last MRV";
       }
       leaf mdi-avg-mrv {
         type string;
         description "Average MRV";
       }
       leaf mdi-interface-name {
         type string;
         description "Interface Name";
       }
       leaf mdi-template-name {
         type string;
         description "Template Name";
       }
       leaf mdi-flow-direction {
         type string;
         description "MDI Flow Direction";
       }
       leaf mdi-flow-type {
         type string;
         description "Flow Type";
       }
       leaf mdi-mpls-labels {
         type string;
         description "MPLS labels";
       }
       leaf mdi-record-count {
         type uint32;
         description "Count of MDI records";
       }
       leaf mdi-pid-count {
         type string;
         description "PID Count";
       }
       leaf mdi-flow-identifier {
         type uint32;
         description "Unique Identifier of flow";
       }
     }
     container vmon-mdi-record {
       leaf mdi-record-index {
         type uint32;
         description "MDI Record Index";
       }
       leaf mdi-df {
         type string;
         description "DF Value";
       }
       leaf mdi-mlr {
         type uint32;
         description "MLR Value";
       }
       leaf mdi-mrv {
         type string;
         description "MRV Value";
       }
     }
     container vmon-mdi-record-udp {
       leaf mdi-record-index {
         type uint32;
         description "MDI Record Index";
       }
       leaf mdi-df {
         type string;
         description "DF Value";
       }
       leaf mdi-mlr {
         type uint32;
         description "MLR Value";
       }
       leaf mdi-mrv {
         type string;
         description "MRV Value";
       }
       leaf mdi-pid1-val {
         type string;
         description "PID Value";
       }
       leaf mdi-pid1-mlr {
         type string;
         description "MLR Value";
       }
       leaf mdi-pid2-val {
         type string;
         description "PID Value";
       }
       leaf mdi-pid2-mlr {
         type string;
         description "MLR Value";
       }
       leaf mdi-pid3-val {
         type string;
         description "PID Value";
       }
       leaf mdi-pid3-mlr {
         type string;
         description "MLR Value";
       }
       leaf mdi-pid4-val {
         type string;
         description "PID Value";
       }
       leaf mdi-pid4-mlr {
         type string;
         description "MLR Value";
       }
       leaf mdi-pid5-val {
         type string;
         description "PID Value";
       }
       leaf mdi-pid5-mlr {
         type string;
         description "MLR Value";
       }
       leaf mdi-pid6-val {
         type string;
         description "PID Value";
       }
       leaf mdi-pid6-mlr {
         type string;
         description "MLR Value";
       }
     }
     container vmon-mdi-alarm-stats {
       leaf mdi-df-successful-alarms {
         type uint32;
         description "Successful DF Alarms Generated";
       }
       leaf mdi-df-threshold-exceed-alarms {
         type uint32;
         description " DF Alarms Suppressed due to threshold exceed";
       }
       leaf mdi-df-same-level-alarms {
         type uint32;
         description " DF Alarms Suppressed due to same level";
       }
       leaf mdi-df-template-missing-alarms {
         type uint32;
         description " DF Alarms Suppressed due to template missing";
       }
       leaf mdi-df-alarm-syslog-generated {
         type uint32;
         description " DF Alarm Syslog Generated ";
       }
       leaf mdi-df-total-alarms {
         type uint32;
         description "Total DF Alarms Generated";
       }
       leaf mdi-mlr-successful-alarms {
         type uint32;
         description "Successful MLR Alarms Generated";
       }
       leaf mdi-mlr-threshold-exceed-alarms {
         type uint32;
         description " MLR Alarms Suppressed due to threshold exceed";
       }
       leaf mdi-mlr-same-level-alarms {
         type uint32;
         description " MLR Alarms Suppressed due to same level";
       }
       leaf mdi-mlr-template-missing-alarms {
         type uint32;
         description " MLR Alarms Suppressed due to template missing";
       }
       leaf mdi-mlr-alarm-syslog-generated {
         type uint32;
         description " MLR Alarm Syslog Generated ";
       }
       leaf mdi-mlr-total-alarms {
         type uint32;
         description "Total MLR Alarms Generated";
       }
       leaf mdi-mrv-successful-alarms {
         type uint32;
         description "Successful MRV Alarms Generated";
       }
       leaf mdi-mrv-threshold-exceed-alarms {
         type uint32;
         description " MRV Alarms Suppressed due to threshold exceed";
       }
       leaf mdi-mrv-same-level-alarms {
         type uint32;
         description " MRV Alarms Suppressed due to same level";
       }
       leaf mdi-mrv-template-missing-alarms {
         type uint32;
         description " MRV Alarms Suppressed due to template missing";
       }
       leaf mdi-mrv-alarm-syslog-generated {
         type uint32;
         description " MRV Alarm Syslog Generated ";
       }
       leaf mdi-mrv-total-alarms {
         type uint32;
         description "Total MRV Alarms Generated";
       }
       leaf mdi-new-flow-successful-alarms {
         type uint32;
         description "Successful New Flow Alarms Generated";
       }
       leaf mdi-new-flow-threshold-exceed-alarms {
         type uint32;
         description "New Flow Alarms Suppressed due to threshold exceed";
       }
       leaf mdi-new-flow-same-level-alarms {
         type uint32;
         description "New Flow Alarms Suppressed due to same level";
       }
       leaf mdi-new-flow-template-missing-alarms {
         type uint32;
         description "New Flow Alarms Suppressed due to template missing";
       }
       leaf mdi-new-flow-alarm-syslog-generated {
         type uint32;
         description " NEW FLOW Alarm Syslog Generated ";
       }
       leaf mdi-new-flow-total-alarms {
         type uint32;
         description "Total New Flow Alarms Generated";
       }
       leaf mdi-flow-delete-successful-alarms {
         type uint32;
         description "Successful Flow Delete Alarms Generated";
       }
       leaf mdi-flow-delete-threshold-exceed-alarms {
         type uint32;
         description "Flow Delete Alarms Suppressed due to threshold exceed";
       }
       leaf mdi-flow-delete-same-level-alarms {
         type uint32;
         description "Flow Delete Alarms Suppressed due to same level";
       }
       leaf mdi-flow-delete-template-missing-alarms {
         type uint32;
         description "Flow Delete Alarms Suppressed due to template missing";
       }
       leaf mdi-flow-delete-alarm-syslog-generated {
         type uint32;
         description " Flow Delete Alarm Syslog Generated ";
       }
       leaf mdi-flow-delete-total-alarms {
         type uint32;
         description "Total Flow Delete Alarms Generated";
       }
       leaf fpc-slot {
         type int32;
         description "FPC Slot";
       }
       leaf tfeb-slot {
         type int32;
         description "TFEB Slot";
       }
       leaf afeb-slot {
         type int32;
         description "AFEB Slot";
       }
       leaf mdi-invalid-alarms {
         type uint32;
         description "Invalid Alarms Generated";
       }
     }
     container inline-jflow-template-version-information {
       leaf template-version {
         type string;
         description "MX Inline Jflow template version information";
       }
       leaf sparks-jflow-template-version {
         type string;
         description "Sparks Jflow template version information";
       }
       leaf pic-jflow-template-version {
         type string;
         description "PIC based Jflow template version information";
       }
       leaf ptx-inline-jflow-template-version {
         type string;
         description "PTX Inline Jflow template version information";
       }
       leaf evo-inline-jflow-template-version {
         type string;
         description "EVO Inline Jflow template version information";
       }
       leaf mx-imon-template-version {
         type string;
         description "Internal Modified MX IMON Template Version";
       }
     }
     container inline-jflow-flow-information {
       leaf fpc-slot {
         type int32;
         description "FPC Slot";
       }
       leaf tfeb-slot {
         type int32;
         description "TFEB Slot";
       }
       leaf pic-slot {
         type int32;
         description "PIC Slot";
       }
       leaf afeb-slot {
         type int32;
         description "AFEB Slot";
       }
       leaf inline-flow-packets {
         type int32;
         description "Flow packets";
       }
       leaf inline-flow-bytes {
         type int32;
         description "Flow bytes";
       }
       leaf inline-active-flows {
         type int32;
         description "Active flows";
       }
       leaf inline-flows {
         type int32;
         description "Flows";
       }
       leaf inline-flows-exported {
         type int32;
         description "Flows exported";
       }
       leaf inline-flow-packets-exported {
         type int32;
         description "Flows packets exported";
       }
       leaf inline-flows-expired {
         type int32;
         description "Flows inactive timed out";
       }
       leaf inline-flows-aged {
         type int32;
         description "Flows active timed out";
       }
       leaf inline-flow-insert-count {
         type int32;
         description "Flow Insert Count";
       }
       leaf inline-ipv4-flow-packets {
         type int32;
         description "IPv4 Flow packets";
       }
       leaf inline-ipv4-flow-bytes {
         type int32;
         description "IPv4 Flow bytes";
       }
       leaf inline-ipv4-active-flows {
         type int32;
         description "IPv4 Active flows";
       }
       leaf inline-ipv4-total-flows {
         type int32;
         description "IPv4 Flows";
       }
       leaf inline-ipv4-flows-exported {
         type int32;
         description "IPv4 Flows exported";
       }
       leaf inline-ipv4-flow-packets-exported {
         type int32;
         description "IPv4 Flows packets exported";
       }
       leaf inline-ipv4-flows-expired {
         type int32;
         description "IPv4 Flows inactive timed out";
       }
       leaf inline-ipv4-flows-aged {
         type int32;
         description "IPv4 Flows active timed out";
       }
       leaf inline-ipv4-flow-insert-count {
         type int32;
         description "IPv4 Flow Insert Count";
       }
       leaf inline-ipv6-flow-packets {
         type int32;
         description "IPv6 Flow packets";
       }
       leaf inline-ipv6-flow-bytes {
         type int32;
         description "IPv6 Flow bytes";
       }
       leaf inline-ipv6-active-flows {
         type int32;
         description "IPv6 Active flows";
       }
       leaf inline-ipv6-total-flows {
         type int32;
         description "IPv6 Flows";
       }
       leaf inline-ipv6-flows-exported {
         type int32;
         description "IPv6 Flows exported";
       }
       leaf inline-ipv6-flow-packets-exported {
         type int32;
         description "IPv6 Flows packets exported";
       }
       leaf inline-ipv6-flows-expired {
         type int32;
         description "IPv6 Flows inactive timed out";
       }
       leaf inline-ipv6-flows-aged {
         type int32;
         description "IPv6 Flows active timed out";
       }
       leaf inline-ipv6-flow-insert-count {
         type int32;
         description "IPv6 Flow Insert Count";
       }
       leaf inline-vpls-flow-packets {
         type int32;
         description "VPLS Flow packets";
       }
       leaf inline-vpls-flow-bytes {
         type int32;
         description "VPLS Flow bytes";
       }
       leaf inline-vpls-active-flows {
         type int32;
         description "VPLS Active flows";
       }
       leaf inline-vpls-total-flows {
         type int32;
         description "VPLS Flows";
       }
       leaf inline-vpls-flows-exported {
         type int32;
         description "VPLS Flows exported";
       }
       leaf inline-vpls-flow-packets-exported {
         type int32;
         description "VPLS Flows packets exported";
       }
       leaf inline-vpls-flows-expired {
         type int32;
         description "VPLS Flows inactive timed out";
       }
       leaf inline-vpls-flows-aged {
         type int32;
         description "VPLS Flows active timed out";
       }
       leaf inline-vpls-flow-insert-count {
         type int32;
         description "VPLS Flow Insert Count";
       }
       leaf inline-bridge-flow-packets {
         type int32;
         description "BRIDGE Flow packets";
       }
       leaf inline-bridge-flow-bytes {
         type int32;
         description "BRIDGE Flow bytes";
       }
       leaf inline-bridge-active-flows {
         type int32;
         description "BRIDGE Active flows";
       }
       leaf inline-bridge-total-flows {
         type int32;
         description "BRIDGE Flows";
       }
       leaf inline-bridge-flows-exported {
         type int32;
         description "BRIDGE Flows exported";
       }
       leaf inline-bridge-flow-packets-exported {
         type int32;
         description "BRIDGE Flows packets exported";
       }
       leaf inline-bridge-flows-expired {
         type int32;
         description "BRIDGE Flows inactive timed out";
       }
       leaf inline-bridge-flows-aged {
         type int32;
         description "BRIDGE Flows active timed out";
       }
       leaf inline-bridge-flow-insert-count {
         type int32;
         description "BRIDGE Flow Insert Count";
       }
       leaf inline-mpls-flow-packets {
         type int32;
         description "MPLS Flow packets";
       }
       leaf inline-mpls-flow-bytes {
         type int32;
         description "MPLS Flow bytes";
       }
       leaf inline-mpls-active-flows {
         type int32;
         description "MPLS Active flows";
       }
       leaf inline-mpls-total-flows {
         type int32;
         description "MPLS Flows";
       }
       leaf inline-mpls-flows-exported {
         type int32;
         description "MPLS Flows exported";
       }
       leaf inline-mpls-flow-packets-exported {
         type int32;
         description "MPLS Flows packets exported";
       }
       leaf inline-mpls-flows-expired {
         type int32;
         description "MPLS Flows inactive timed out";
       }
       leaf inline-mpls-flows-aged {
         type int32;
         description "MPLS Flows active timed out";
       }
       leaf inline-mpls-flow-insert-count {
         type int32;
         description "MPLS Flow Insert Count";
       }
       leaf inline-ipv4-flows {
         type int32;
         description "IPv4 Flows";
       }
       leaf inline-ipv6-flows {
         type int32;
         description "IPv6 Flows";
       }
       leaf inline-vpls-flows {
         type int32;
         description "VPLS Flows";
       }
       leaf inline-bridge-flows {
         type int32;
         description "BRIDGE Flows";
       }
       leaf inline-mpls-flows {
         type int32;
         description "MPLS Flows";
       }
     }
     container packet-distribution-information {
       leaf packet-size-range-start {
         type int32;
         description "Start of packet size range";
       }
       leaf packet-size-range-end {
         type int32;
         description "End of packet size range";
       }
       leaf range-number-packets {
         type int32;
         description "Number of packets in range";
       }
       leaf range-percentage-packets {
         type string;
         description "Percentage of packets in range";
       }
     }
     container error-information {
       leaf error-packets-dropped-no-memory {
         type int32;
         description "Number of packets dropped because memory is exhausted";
       }
       leaf error-packets-dropped-not-ip {
         type int32;
         description "Number of packets dropped because they are not IP";
       }
       leaf error-packets-dropped-not-ipv4 {
         type int32;
         description "Number of packets dropped because they are not IPv4";
       }
       leaf error-packets-too-small {
         type int32;
         description "Number of packets dropped because their header is too small";
       }
       leaf error-allocation-failures {
         type int32;
         description "Number of failed attempts to allocate memory";
       }
       leaf error-free-failures {
         type int32;
         description "Number of failed attempts to free memory";
       }
       leaf error-free-list-failures {
         type int32;
         description "Number of operations that failed because free list memory is exhausted";
       }
       leaf error-memory-warning {
         type string;
         description "Reached low memory condition";
       }
       leaf error-memory-overload {
         type string;
         description "Whether memory is exhausted";
       }
       leaf error-packets-per-second-overload {
         type string;
         description "Whether the number of incoming packets exceeds the designed per-second limit";
       }
       leaf error-bytes-per-second-overload {
         type string;
         description "Whether the number of incoming bytes exceeds the designed per-second limit";
       }
     }
     container inline-jflow-error-information {
       leaf fpc-slot {
         type int32;
         description "FPC Slot";
       }
       leaf tfeb-slot {
         type int32;
         description "TFEB Slot";
       }
       leaf afeb-slot {
         type int32;
         description "AFEB Slot";
       }
       leaf pic-slot {
         type int32;
         description "PIC Slot";
       }
       leaf inline-flow-creation-failures {
         type int32;
         description "Number of flow creation failures";
       }
       leaf inline-route-record-lookup-failure {
         type int32;
         description "Number of Route record lookup failures";
       }
       leaf inline-as-lookup-failures {
         type int32;
         description "Number of AS lookup Failures";
       }
       leaf inline-export-packet-failures {
         type int32;
         description "Number of export packet failures";
       }
       leaf inline-memory-overload {
         type string;
         description "Memory overload status";
       }
       leaf inline-memory-alloc-fail-count {
         type int32;
         description "Count of memory alloc failures";
       }
       leaf inline-ipv4-flow-creation-failures {
         type int32;
         description "Number of IPv4 flow creation failures";
       }
       leaf inline-ipv4-route-record-lookup-failure {
         type int32;
         description "Number of IPv4 Route record lookup failures";
       }
       leaf inline-ipv4-as-lookup-failures {
         type int32;
         description "Number of IPv4 AS lookup Failures";
       }
       leaf inline-ipv4-export-packet-failures {
         type int32;
         description "IPv4 Number of export packet failures";
       }
       leaf inline-ipv6-flow-creation-failures {
         type int32;
         description "Number of IPv6 flow creation failures";
       }
       leaf inline-ipv6-route-record-lookup-failure {
         type int32;
         description "Number of IPv6 Route record lookup failures";
       }
       leaf inline-ipv6-as-lookup-failures {
         type int32;
         description "Number of IPv6 AS lookup Failures";
       }
       leaf inline-ipv6-export-packet-failures {
         type int32;
         description "IPv6 Number of export packet failures";
       }
       leaf inline-vpls-flow-creation-failures {
         type int32;
         description "Number of VPLS flow creation failures";
       }
       leaf inline-vpls-route-record-lookup-failure {
         type int32;
         description "Number of VPLS Route record lookup failures";
       }
       leaf inline-vpls-as-lookup-failures {
         type int32;
         description "Number of VPLS AS lookup Failures";
       }
       leaf inline-vpls-export-packet-failures {
         type int32;
         description "VPLS Number of export packet failures";
       }
       leaf inline-bridge-flow-creation-failures {
         type int32;
         description "Number of BRIDGE flow creation failures";
       }
       leaf inline-bridge-export-packet-failures {
         type int32;
         description "BRIDGE Number of export packet failures";
       }
       leaf inline-mpls-flow-creation-failures {
         type int32;
         description "Number of MPLS flow creation failures";
       }
       leaf inline-mpls-route-record-lookup-failure {
         type int32;
         description "Number of MPLS Route record lookup failures";
       }
       leaf inline-mpls-as-lookup-failures {
         type int32;
         description "Number of MPLS AS lookup Failures";
       }
       leaf inline-mpls-export-packet-failures {
         type int32;
         description "MPLS Number of export packet failures";
       }
       leaf ring-buffer-failures {
         type int32;
         description "Number of Ring Buffer Enque Failures";
       }
       leaf inline-ipv4-errors {
         type int32;
         description "IPv4 Errors";
       }
       leaf inline-ipv6-errors {
         type int32;
         description "IPv6 Errors";
       }
       leaf inline-vpls-errors {
         type int32;
         description "VPLS Errors";
       }
       leaf inline-bridge-errors {
         type int32;
         description "BRIDGE Errors";
       }
       leaf inline-mpls-errors {
         type int32;
         description "MPLS Errors";
       }
     }
     container v9-error-information {
       leaf interface-name {
         type string;
         description "Physical interface name";
       }
       leaf service-set-dropped {
         type int32;
         description "Number of service set drops";
       }
       leaf active-timeout-failures {
         type int32;
         description "Number of active timeout failures";
       }
       leaf export-packet-failures {
         type int32;
         description "Number of export packet failures";
       }
       leaf flow-creation-failures {
         type int32;
         description "Number of flow creation failures";
       }
       leaf memory-overload {
         type string;
         description "Memory overload status";
       }
     }
     container status-information {
       leaf interface-name {
         type string;
         description "Physical interface name";
       }
       leaf status-export-format {
         type int32;
         description "Export format";
       }
       leaf status-route-record-count {
         type int32;
         description "Route record count";
       }
       leaf status-ifl-snmp-map-count {
         type int32;
         description "Local index to SNMP index count";
       }
       leaf status-as-count {
         type int32;
         description "Autonomous system number count";
       }
       leaf status-monitor-config-set {
         type string;
         description "Configuration set on PIC";
       }
       leaf status-monitor-route-record-set {
         type string;
         description "Route records set on PIC";
       }
       leaf status-monitor-ifl-snmp-set {
         type string;
         description "Local index to SNMP index map set on PIC";
       }
       leaf status-service-id {
         type int32;
         description "Service ID";
       }
       leaf status-export-interval {
         type int32;
         description "Export interval, in seconds";
       }
       leaf status-proto {
         type string;
         description "Protocol";
       }
       leaf status-engine-type {
         type int32;
         description "Engine type";
       }
       leaf status-engine-id {
         type int32;
         description "Engine ID";
       }
       leaf status-monitor-time-set {
         type string;
         description "Time set on PIC";
       }
     }
     container inline-jflow-status-information {
       leaf fpc-slot {
         type int32;
         description "FPC Slot";
       }
       leaf tfeb-slot {
         type int32;
         description "TFEB Slot";
       }
       leaf afeb-slot {
         type int32;
         description "AFEB Slot";
       }
       leaf pic-slot {
         type int32;
         description "PIC Slot";
       }
       leaf inline-status-ipv4-export-format {
         type string;
         description "IPV4 export format";
       }
       leaf inline-status-ipv6-export-format {
         type string;
         description "IPV6 export format";
       }
       leaf inline-status-vpls-export-format {
         type string;
         description "VPLS export format";
       }
       leaf inline-status-bridge-export-format {
         type string;
         description "BRIDGE export format";
       }
       leaf inline-status-mpls-export-format {
         type string;
         description "MPLS export format";
       }
       leaf inline-status-route-record-count {
         type int32;
         description "Route record count";
       }
       leaf inline-status-as-count {
         type int32;
         description "Autonomous system number count";
       }
       leaf inline-status-ipv4-route-record-count {
         type int32;
         description "IPv4 Route record count";
       }
       leaf inline-status-ipv6-route-record-count {
         type int32;
         description "IPv6 Route record count";
       }
       leaf inline-status-mpls-route-record-count {
         type int32;
         description "MPLS Route record count";
       }
       leaf ring-buffer-entries {
         type int32;
         description "Ring Buffer Entries Count";
       }
       leaf inline-status-route-record-set {
         type string;
         description "Route records set on FPC";
       }
       leaf inline-status-config-set {
         type string;
         description "Configuration set on FPC";
       }
       leaf inline-status-service-status {
         type string;
         description "Service Status on FPC";
       }
       leaf inline-status-use-extended-flow-memory {
         type string;
         description "Using extended flow memory";
       }
       leaf inline-status-flex-flow-sizing {
         type string;
         description "Flex flow sizing enabled";
       }
       leaf inline-status-ipv4-max-flow-count {
         type int32;
         description "IPv4 MAX FLOW count";
       }
       leaf inline-status-ipv6-max-flow-count {
         type int32;
         description "IPv6 MAX FLOW count";
       }
       leaf inline-status-vpls-max-flow-count {
         type int32;
         description "VPLS MAX FLOW count";
       }
       leaf inline-status-bridge-max-flow-count {
         type int32;
         description "BRIDGE MAX FLOW count";
       }
       leaf inline-status-mpls-max-flow-count {
         type int32;
         description "MPLS MAX FLOW count";
       }
       leaf inline-status-max-supported-flow-table-size {
         type int32;
         description "MAX supported Flow Table size";
       }
     }
     container flow-detail {
       container detail-entry {
         leaf tos {
           type int32;
           description "Type of service";
         }
         leaf protocol {
           type int32;
           description "Protocol";
         }
         leaf tcp-flags {
           type int32;
           description "TCP flags";
         }
         leaf source-address {
           type jt:ipaddr;
           description "Source address of flow";
         }
         leaf source-prefix-length {
           type string;
           description "Source prefix length";
         }
         leaf source-port {
           type int32;
           description "Source port";
         }
         leaf destination-address {
           type jt:ipaddr;
           description "Destination address of flow";
         }
         leaf destination-prefix-length {
           type string;
           description "Destination prefix length";
         }
         leaf destination-port {
           type int32;
           description "Destination port";
         }
         leaf input-snmp-interface-index {
           type int32;
           description "Input SNMP interface index";
         }
         leaf output-snmp-interface-index {
           type int32;
           description "Output SNMP interface index";
         }
         leaf input-interface-name {
           type string;
           description "Input interface name";
         }
         leaf output-interface-name {
           type string;
           description "Output interface name";
         }
         leaf source-as {
           type int32;
           description "Source autonomous system number";
         }
         leaf destination-as {
           type int32;
           description "Destination autonomous system number";
         }
         leaf start-time {
           type string;
           description "System uptime at start of flow";
         }
         leaf end-time {
           type string;
           description "System uptime at end of flow";
         }
         leaf packet-count {
           type int32;
           description "Number of packets in the flow";
         }
         leaf byte-count {
           type int32;
           description "Number of bytes in the flow";
         }
         leaf icmp-type {
           type int32;
           description "ICMP type";
         }
         container last-active-timeout {
           leaf time-delta {
             type string;
             description "Time since last active timeout";
           }
           leaf last-packet-count {
             type int32;
             description "Packets exported in last active timeout";
           }
           leaf last-byte-count {
             type int32;
             description "Bytes exported in last active timeout";
           }
         }
       }
     }
     container flow-aggregate-template-detail {
       container flow-aggregate-template-detail-ipv4 {
         container detail-entry {
           leaf source-address {
             type jt:ipaddr;
             description "Source address of flow";
           }
           leaf destination-address {
             type jt:ipaddr;
             description "Destination address of flow";
           }
           leaf source-port {
             type int32;
             description "Source port";
           }
           leaf destination-port {
             type int32;
             description "Destination port";
           }
           leaf protocol {
             type int32;
             description "Protocol";
           }
           leaf tos {
             type int32;
             description "Type of service";
           }
           leaf tcp-flags {
             type int32;
             description "TCP flags";
           }
           leaf source-mask {
             type jt:ipaddr;
             description "Source mask";
           }
           leaf destination-mask {
             type jt:ipaddr;
             description "Destination mask";
           }
           leaf input-snmp-interface-index {
             type int32;
             description "Input SNMP interface index";
           }
           leaf output-snmp-interface-index {
             type int32;
             description "Output SNMP interface index";
           }
           leaf start-time {
             type string;
             description "System uptime at start of flow";
           }
           leaf end-time {
             type string;
             description "System uptime at end of flow";
           }
           leaf packet-count {
             type int32;
             description "Number of packets in the flow";
           }
           leaf byte-count {
             type int32;
             description "Number of bytes in the flow";
           }
           leaf icmp-type {
             type int32;
             description "ICMP type";
           }
         }
       }
       container flow-aggregate-template-detail-mpls {
         container detail-entry {
           leaf mpls-label-1 {
             type int32;
             description "MPLS label 1";
           }
           leaf mpls-label-2 {
             type int32;
             description "MPLS label 2";
           }
           leaf mpls-label-3 {
             type int32;
             description "MPLS label 3";
           }
           leaf input-snmp-interface-index {
             type int32;
             description "Input SNMP interface index";
           }
           leaf output-snmp-interface-index {
             type int32;
             description "Output SNMP interface index";
           }
           leaf start-time {
             type string;
             description "System uptime at start of flow";
           }
           leaf end-time {
             type string;
             description "System uptime at end of flow";
           }
           leaf packet-count {
             type int32;
             description "Number of packets in the flow";
           }
           leaf byte-count {
             type int32;
             description "Number of bytes in the flow";
           }
           leaf icmp-type {
             type int32;
             description "ICMP type";
           }
         }
       }
       container flow-aggregate-template-detail-mpls-ipv4 {
         container detail-entry {
           leaf mpls-label-1 {
             type int32;
             description "MPLS label 1";
           }
           leaf mpls-label-2 {
             type int32;
             description "MPLS label 2";
           }
           leaf mpls-label-3 {
             type int32;
             description "MPLS label 3";
           }
           leaf source-address {
             type jt:ipaddr;
             description "Source address of flow";
           }
           leaf destination-address {
             type jt:ipaddr;
             description "Destination address of flow";
           }
           leaf top-label-address {
             type jt:ipaddr;
             description "MPLS Top Label IPv4 Address";
           }
           leaf source-port {
             type int32;
             description "Source port";
           }
           leaf destination-port {
             type int32;
             description "Destination port";
           }
           leaf protocol {
             type int32;
             description "Protocol";
           }
           leaf tos {
             type int32;
             description "Type of service";
           }
           leaf tcp-flags {
             type int32;
             description "TCP flags";
           }
           leaf source-mask {
             type jt:ipaddr;
             description "Source mask";
           }
           leaf destination-mask {
             type jt:ipaddr;
             description "Destination mask";
           }
           leaf input-snmp-interface-index {
             type int32;
             description "Input SNMP interface index";
           }
           leaf output-snmp-interface-index {
             type int32;
             description "Output SNMP interface index";
           }
           leaf start-time {
             type string;
             description "System uptime at start of flow";
           }
           leaf end-time {
             type string;
             description "System uptime at end of flow";
           }
           leaf packet-count {
             type int32;
             description "Number of packets in the flow";
           }
           leaf byte-count {
             type int32;
             description "Number of bytes in the flow";
           }
           leaf icmp-type {
             type int32;
             description "ICMP type";
           }
         }
       }
       container flow-aggregate-template-detail-ipv6 {
         container detail-entry {
           leaf source-ipv6-address {
             type string;
             description "Source address of flow";
           }
           leaf destination-ipv6-address {
             type string;
             description "Destination address of flow";
           }
           leaf source-port {
             type int32;
             description "Source port";
           }
           leaf destination-port {
             type int32;
             description "Destination port";
           }
           leaf protocol {
             type int32;
             description "Protocol";
           }
           leaf tos {
             type int32;
             description "Type of service";
           }
           leaf tcp-flags {
             type int32;
             description "TCP flags";
           }
           leaf source-mask {
             type jt:ipaddr;
             description "Source mask";
           }
           leaf destination-mask {
             type jt:ipaddr;
             description "Destination mask";
           }
           leaf input-snmp-interface-index {
             type int32;
             description "Input SNMP interface index";
           }
           leaf output-snmp-interface-index {
             type int32;
             description "Output SNMP interface index";
           }
           leaf start-time {
             type string;
             description "System uptime at start of flow";
           }
           leaf end-time {
             type string;
             description "System uptime at end of flow";
           }
           leaf packet-count {
             type int32;
             description "Number of packets in the flow";
           }
           leaf byte-count {
             type int32;
             description "Number of bytes in the flow";
           }
           leaf icmp-type {
             type int32;
             description "ICMP type";
           }
         }
       }
       container flow-aggregate-template-detail-peer-as-billing {
         container detail-entry {
           leaf tos {
             type int32;
             description "Type of service";
           }
           leaf input-snmp-interface-index {
             type int32;
             description "Input SNMP interface index";
           }
           leaf start-time {
             type string;
             description "System uptime at start of flow";
           }
           leaf end-time {
             type string;
             description "System uptime at end of flow";
           }
           leaf packet-count {
             type int32;
             description "Number of packets in the flow";
           }
           leaf byte-count {
             type int32;
             description "Number of bytes in the flow";
           }
           leaf destination-peer-as {
             type int32;
             description "Peer Destination autonomous system number";
           }
           leaf bgp-nexthop {
             type jt:ipaddr;
             description "Bgp nexthop";
           }
           leaf icmp-type {
             type int32;
             description "ICMP type";
           }
         }
       }
     }
     container flow-aggregate-as-detail {
       container detail-entry {
         leaf source-as {
           type int32;
           description "Source autonomous system number";
         }
         leaf destination-as {
           type int32;
           description "Destination autonomous system number";
         }
         leaf input-snmp-interface-index {
           type int32;
           description "Input SNMP interface index";
         }
         leaf output-snmp-interface-index {
           type int32;
           description "Output SNMP interface index";
         }
         leaf input-interface-name {
           type string;
           description "Input interface name";
         }
         leaf output-interface-name {
           type string;
           description "Output interface name";
         }
         leaf start-time {
           type string;
           description "System uptime at start of flow";
         }
         leaf end-time {
           type string;
           description "System uptime at end of flow";
         }
         leaf flow-count {
           type int32;
           description "Number of flows in the aggregate";
         }
         leaf packet-count {
           type int32;
           description "Number of packets in the flow";
         }
         leaf byte-count {
           type int32;
           description "Number of bytes in the flow";
         }
         leaf icmp-type {
           type int32;
           description "ICMP type";
         }
       }
     }
     container flow-aggregate-protocol-port-detail {
       container detail-entry {
         leaf protocol {
           type int32;
           description "Protocol";
         }
         leaf source-port {
           type int32;
           description "Source port";
         }
         leaf destination-port {
           type int32;
           description "Destination port";
         }
         leaf start-time {
           type string;
           description "System uptime at start of flow";
         }
         leaf end-time {
           type string;
           description "System uptime at end of flow";
         }
         leaf flow-count {
           type int32;
           description "Number of flows in the aggregate";
         }
         leaf packet-count {
           type int32;
           description "Number of packets in the flow";
         }
         leaf byte-count {
           type int32;
           description "Number of bytes in the flow";
         }
         leaf icmp-type {
           type int32;
           description "ICMP type";
         }
       }
     }
     container flow-aggregate-source-prefix-detail {
       container detail-entry {
         leaf source-address {
           type jt:ipaddr;
           description "Source address of flow";
         }
         leaf source-prefix-length {
           type string;
           description "Source prefix length";
         }
         leaf input-snmp-interface-index {
           type int32;
           description "Input SNMP interface index";
         }
         leaf input-interface-name {
           type string;
           description "Input interface name";
         }
         leaf source-as {
           type int32;
           description "Source autonomous system number";
         }
         leaf start-time {
           type string;
           description "System uptime at start of flow";
         }
         leaf end-time {
           type string;
           description "System uptime at end of flow";
         }
         leaf flow-count {
           type int32;
           description "Number of flows in the aggregate";
         }
         leaf packet-count {
           type int32;
           description "Number of packets in the flow";
         }
         leaf byte-count {
           type int32;
           description "Number of bytes in the flow";
         }
         leaf icmp-type {
           type int32;
           description "ICMP type";
         }
       }
     }
     container flow-aggregate-destination-prefix-detail {
       container detail-entry {
         leaf destination-address {
           type jt:ipaddr;
           description "Destination address of flow";
         }
         leaf destination-prefix-length {
           type string;
           description "Destination prefix length";
         }
         leaf output-snmp-interface-index {
           type int32;
           description "Output SNMP interface index";
         }
         leaf output-interface-name {
           type string;
           description "Output interface name";
         }
         leaf destination-as {
           type int32;
           description "Destination autonomous system number";
         }
         leaf start-time {
           type string;
           description "System uptime at start of flow";
         }
         leaf end-time {
           type string;
           description "System uptime at end of flow";
         }
         leaf flow-count {
           type int32;
           description "Number of flows in the aggregate";
         }
         leaf packet-count {
           type int32;
           description "Number of packets in the flow";
         }
         leaf byte-count {
           type int32;
           description "Number of bytes in the flow";
         }
         leaf icmp-type {
           type int32;
           description "ICMP type";
         }
       }
     }
     container flow-aggregate-source-destination-prefix-detail {
       container detail-entry {
         leaf source-address {
           type jt:ipaddr;
           description "Source address of flow";
         }
         leaf source-prefix-length {
           type string;
           description "Source prefix length";
         }
         leaf destination-address {
           type jt:ipaddr;
           description "Destination address of flow";
         }
         leaf destination-prefix-length {
           type string;
           description "Destination prefix length";
         }
         leaf input-snmp-interface-index {
           type int32;
           description "Input SNMP interface index";
         }
         leaf output-snmp-interface-index {
           type int32;
           description "Output SNMP interface index";
         }
         leaf input-interface-name {
           type string;
           description "Input interface name";
         }
         leaf output-interface-name {
           type string;
           description "Output interface name";
         }
         leaf source-as {
           type int32;
           description "Source autonomous system number";
         }
         leaf destination-as {
           type int32;
           description "Destination autonomous system number";
         }
         leaf start-time {
           type string;
           description "System uptime at start of flow";
         }
         leaf end-time {
           type string;
           description "System uptime at end of flow";
         }
         leaf flow-count {
           type int32;
           description "Number of flows in the aggregate";
         }
         leaf packet-count {
           type int32;
           description "Number of packets in the flow";
         }
         leaf byte-count {
           type int32;
           description "Number of bytes in the flow";
         }
         leaf icmp-type {
           type int32;
           description "ICMP type";
         }
       }
     }
     container imon-flowgroup-stats {
       leaf fpc-slot {
         type int32;
         description "FPC Slot";
       }
       leaf imon-instance-flowgroup-name {
         type string;
         description "Instance name";
       }
       leaf imon-instance-flowgroup-index {
         type uint32;
         description "Instance index";
       }
       leaf imon-inst-flow-exceeded-count {
         type uint32;
         description "Flow exceeded count";
       }
       leaf imon-inst-flow-missed-count {
         type uint32;
         description "Flow missed count";
       }
       leaf imon-inst-flow-aged-out-count {
         type uint32;
         description "Flow aged out count";
       }
       leaf imon-inst-flow-learnt-count {
         type uint32;
         description "Flow learnt count";
       }
       leaf imon-inst-flow-meter-exceeded-count {
         type uint32;
         description "Flow meter exceeded count";
       }
     }
     container imon-sw-stats {
       leaf fpc-slot {
         type int32;
         description "FPC Slot";
       }
       leaf imon-sw-instance-name {
         type string;
         description "Instance name";
       }
       leaf imon-sw-inst-flow-aged-out-count {
         type uint32;
         description "Flow aged out count";
       }
       leaf imon-sw-inst-flow-learnt-count {
         type uint32;
         description "Flow learnt count";
       }
     }
     container imon-stats {
       leaf fpc-slot {
         type int32;
         description "FPC Slot";
       }
       leaf imon-fpc-packets {
         type uint32;
         description "Total packets at FPC level";
       }
       leaf imon-fpc-bytes {
         type uint32;
         description "Total bytes at FPC level";
       }
       leaf imon-collector-name {
         type string;
         description "Collector name";
       }
       leaf imon-collector-index {
         type uint32;
         description "Collector index";
       }
       leaf imon-collector-packets {
         type uint32;
         description "Total packets at collector level";
       }
       leaf imon-collector-bytes {
         type uint32;
         description "Total bytes at collector level";
       }
       leaf imon-instance-name {
         type string;
         description "Instance name";
       }
       leaf imon-instance-index {
         type uint32;
         description "Instance index";
       }
       leaf imon-instance-packets {
         type uint32;
         description "Total packets at instance level";
       }
       leaf imon-instance-bytes {
         type uint32;
         description "Total bytes at instance level";
       }
     }
     container imon-flow-ctr-map {
       leaf fpc-slot {
         type int32;
         description "FPC Slot";
       }
       leaf imon-flow-ctr-instance-name {
         type string;
         description "Flow counter instance name";
       }
       leaf imon-counter-name {
         type string;
         description "Counter name";
       }
       leaf imon-min-value {
         type uint32;
         description "Minimum Value";
       }
       leaf imon-max-value {
         type uint32;
         description "Maximum Value";
       }
       leaf imon-entp-elem-id {
         type uint32;
         description "Enterprise element id";
       }
       leaf imon-counter-type {
         type string;
         description "Counter type";
       }
     }
     container imon-flow-feature-map {
       leaf fpc-slot {
         type int32;
         description "FPC Slot";
       }
       leaf imon-flow-feature-instance-name {
         type string;
         description "Flow Feature instance name";
       }
       leaf imon-feature-name {
         type string;
         description "Feature name";
       }
       leaf imon-feature-entp-elem-id {
         type uint32;
         description "Flow feature Enterprise element id";
       }
     }
   }
   grouping services-mobile-edge-peers-info-block {
     container counters {
       leaf control-peers {
         type uint32;
         description "Total control peers";
       }
       leaf access-peers {
         type uint32;
         description "Total access peers";
       }
       leaf core-peers {
         type uint32;
         description "Total core peers";
       }
       leaf cp-peers {
         type uint32;
         description "Total cp peers";
       }
       leaf assoc-setup-req-rej-sent {
         type uint32;
         description "Total association setup request rejects sent";
       }
     }
     list peer {
       list session-info {
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
     list control-peers-information {
       list peer {
         leaf ip-address {
           type jt:ipaddr;
           description "Session IPv4 address";
         }
         leaf hostname {
           type string;
           description "Session host name";
         }
         leaf routing-instance {
           type string;
           description "Routing-instance name";
         }
         leaf peer-group-name {
           type string;
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list access-peers-information {
       list peer {
         leaf ip-address {
           type jt:ipaddr;
           description "Session IPv4 address";
         }
         leaf hostname {
           type string;
           description "Session host name";
         }
         leaf routing-instance {
           type string;
           description "Routing-instance name";
         }
         leaf peer-group-name {
           type string;
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list core-peers-information {
       list peer {
         leaf ip-address {
           type jt:ipaddr;
           description "Session IPv4 address";
         }
         leaf hostname {
           type string;
           description "Session host name";
         }
         leaf routing-instance {
           type string;
           description "Routing-instance name";
         }
         leaf peer-group-name {
           type string;
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list cp-peers-information {
       list peer {
         leaf ip-address {
           type jt:ipaddr;
           description "Session IPv4 address";
         }
         leaf hostname {
           type string;
           description "Session host name";
         }
         leaf routing-instance {
           type string;
           description "Routing-instance name";
         }
         leaf peer-group-name {
           type string;
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
   }
   grouping services-mobile-edge-peers-stats-info-block {
     container counters {
       leaf control-peers {
         type uint32;
         description "Total control peers";
       }
       leaf access-peers {
         type uint32;
         description "Total access peers";
       }
       leaf core-peers {
         type uint32;
         description "Total core peers";
       }
       leaf cp-peers {
         type uint32;
         description "Total cp peers";
       }
       leaf assoc-setup-req-rej-sent {
         type uint32;
         description "Total association setup request rejects sent";
       }
     }
     list peer {
       list session-info {
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
     list control-peers-statistics-information {
       list peer {
         leaf ip-address {
           type jt:ipaddr;
           description "Session IPv4 address";
         }
         leaf hostname {
           type string;
           description "Session host name";
         }
         leaf routing-instance {
           type string;
           description "Routing-instance name";
         }
         container counters {
           leaf heartbeat-request-received {
             type uint64;
             description "Heartbeat Requests Received";
           }
           leaf heartbeat-response-sent {
             type uint64;
             description "Heartbeat Responses Sent";
           }
           leaf heartbeat-request-sent {
             type uint64;
             description "Heartbeat Requests Sent";
           }
           leaf heartbeat-response-received {
             type uint64;
             description "Heartbeat Responses Received";
           }
           leaf association-setup-request-received {
             type uint64;
             description "Association Setup Requests Received";
           }
           leaf association-setup-response-sent {
             type uint64;
             description "Association Setup Responses Sent";
           }
           leaf association-setup-request-sent {
             type uint64;
             description "Association Setup Requests Sent";
           }
           leaf association-setup-response-received {
             type uint64;
             description "Association Setup Responses Received";
           }
           leaf association-release-request-received {
             type uint64;
             description "Association Release Requests Received";
           }
           leaf association-release-response-sent {
             type uint64;
             description "Association Release Responses Sent";
           }
           leaf session-establishment-request-received {
             type uint64;
             description "Session Establishment Requests Received";
           }
           leaf session-establishment-response-acknowledgement-sent {
             type uint64;
             description "Session Establishment Accept Sent";
           }
           leaf session-establishment-response-rejection-sent {
             type uint64;
             description "Session Establishment Reject Sent";
           }
           leaf session-modification-request-received {
             type uint64;
             description "Session Modification Requests Received";
           }
           leaf session-modification-response-acknowledgement-sent {
             type uint64;
             description "Session Modification Responses Ack Sent";
           }
           leaf session-modification-response-rejection-sent {
             type uint64;
             description "Session Modification Responses Nack Sent";
           }
           leaf session-deletion-request-received {
             type uint64;
             description "Session Deletion Requests Received";
           }
           leaf session-deletion-response-acknowledgement-sent {
             type uint64;
             description "Session Deletion Responses Sent Accepted";
           }
           leaf session-deletion-response-rejection-sent {
             type uint64;
             description "Session Deletion Responses Sent Rejected";
           }
           leaf load-control-supported {
             type uint64;
             description "Load Control information Report Supported";
           }
           leaf load-control-sent {
             type uint64;
             description "Load Control Information Report Sent";
           }
           leaf ovld-control-supported {
             type uint64;
             description "Overload Control Information Report Supported";
           }
           leaf ovld-control-sent {
             type uint64;
             description "Overload Control Information Report Sent";
           }
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list access-peers-statistics-information {
       list peer {
         leaf ip-address {
           type jt:ipaddr;
           description "Session IPv4 address";
         }
         leaf hostname {
           type string;
           description "Session host name";
         }
         leaf routing-instance {
           type string;
           description "Routing-instance name";
         }
         container counters {
           leaf echo-request-received {
             type uint64;
             description "Echo Requests Received";
           }
           leaf echo-response-sent {
             type uint64;
             description "Echo Response Sent";
           }
           leaf echo-request-sent {
             type uint64;
             description "Echo Requests Sent";
           }
           leaf echo-response-received {
             type uint64;
             description "Echo Response Received";
           }
           leaf error-indication-received {
             type uint64;
             description "Error Indication Received";
           }
           leaf end-markers-sent {
             type uint64;
             description "End Marker Pkts Sent";
           }
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list core-peers-statistics-information {
       list peer {
         leaf ip-address {
           type jt:ipaddr;
           description "Session IPv4 address";
         }
         leaf hostname {
           type string;
           description "Session host name";
         }
         leaf routing-instance {
           type string;
           description "Routing-instance name";
         }
         container counters {
           leaf echo-request-received {
             type uint64;
             description "Echo Requests Received";
           }
           leaf echo-response-sent {
             type uint64;
             description "Echo Response Sent";
           }
           leaf echo-request-sent {
             type uint64;
             description "Echo Requests Sent";
           }
           leaf echo-response-received {
             type uint64;
             description "Echo Response Received";
           }
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
     list cp-peers-statistics-information {
       list peer {
         leaf ip-address {
           type jt:ipaddr;
           description "Session IPv4 address";
         }
         leaf hostname {
           type string;
           description "Session host name";
         }
         leaf routing-instance {
           type string;
           description "Routing-instance name";
         }
         list session-info {
           leaf core-peer-address {
             type jt:ipaddr;
             description "Core data network peer IPv4 address";
           }
           leaf cp-peer-address {
             type jt:ipaddr;
             description "CPF-U network peer IPv4 address";
           }
           list bearer-info {
             list pdr {
               list qer {
               }
             }
             list urr {
               container downlink-drop-notification {
                 leaf reporting-trigger-usage {
                   type string;
                 }
                 leaf start-time-usage {
                   type string;
                 }
                 leaf stop-time-usage {
                   type string;
                 }
               }
             }
           }
           container session-statistics {
           }
         }
       }
     }
   }
   grouping services-mobile-edge-sessions-information-block {
     list session-info {
       leaf ip-address {
         type jt:ipaddr;
         description "Session IPv4 address";
       }
       leaf state {
         type string;
         description "Session state";
       }
       leaf state-time {
         type string;
         description "State time";
       }
       leaf num-bearers {
         type uint32;
         description "Number of Bearers";
       }
       leaf ipv6-prefix {
         type jt:ipaddr;
         description "Session IPv6 prefix";
       }
       leaf num-qos-flows {
         type uint32;
         description "Number of QoS Flows";
       }
       leaf vrf-id {
         type uint32;
         description "VRF ID";
       }
       leaf apn-name {
         type string;
       }
       leaf cpf-peer-address {
         type jt:ipaddr;
         description "Control peer IPv4 address";
       }
       leaf cpf-peer-hostname {
         type string;
       }
       leaf cpf-peer-ri {
         type string;
         description "CPF peer routing instance";
       }
       leaf access-peer-address {
         type jt:ipaddr;
         description "Access peer IPv4 address";
       }
       leaf access-peer-hostname {
         type string;
       }
       leaf access-peer-ri {
         type string;
         description "Access peer routing instance";
       }
       leaf core-peers {
         type uint32;
         description "Total core peers";
       }
       leaf cp-peers {
         type uint32;
         description "Total cp peers";
       }
       leaf apfe {
         type string;
         description "Anchor PFE";
       }
       leaf apfe-secondary {
         type string;
         description "Secondary Anchor PFE";
       }
       leaf local-seid {
         type uint32;
         description "UPF SEID";
       }
       leaf remote-seid {
         type uint32;
         description "CPF SEID";
       }
       leaf framed-ipv6-route {
         type jt:ipaddr;
         description "Framed IPv6 route";
       }
       leaf framed-ipv4-route {
         type jt:ipaddr;
         description "Framed IPv4 route";
       }
       leaf core-peer-address {
         type jt:ipaddr;
         description "Core data network peer IPv4 address";
       }
       leaf cp-peer-address {
         type jt:ipaddr;
         description "CPF-U network peer IPv4 address";
       }
       list bearer-info {
         list pdr {
           list qer {
           }
         }
         list urr {
           container downlink-drop-notification {
             leaf reporting-trigger-usage {
               type string;
             }
             leaf start-time-usage {
               type string;
             }
             leaf stop-time-usage {
               type string;
             }
           }
         }
       }
       container session-statistics {
       }
     }
     container no-session {
       leaf total-sessions {
         type uint32;
         description "Total Sessions";
       }
       leaf total-bearers {
         type uint32;
         description "Total bearer sessions";
       }
     }
   }
   grouping services-mobile-edge-sessions-detail-info-block {
     list session-info {
       leaf ip-address {
         type jt:ipaddr;
         description "Session IPv4 address";
       }
       leaf state {
         type string;
         description "Session state";
       }
       leaf state-time {
         type string;
         description "State time";
       }
       leaf num-bearers {
         type uint32;
         description "Number of Bearers";
       }
       leaf ipv6-prefix {
         type jt:ipaddr;
         description "Session IPv6 prefix";
       }
       leaf num-qos-flows {
         type uint32;
         description "Number of QoS Flows";
       }
       leaf vrf-id {
         type uint32;
         description "VRF ID";
       }
       leaf apn-name {
         type string;
       }
       leaf cpf-peer-address {
         type jt:ipaddr;
         description "Control peer IPv4 address";
       }
       leaf cpf-peer-hostname {
         type string;
       }
       leaf cpf-peer-ri {
         type string;
         description "CPF peer routing instance";
       }
       leaf access-peer-address {
         type jt:ipaddr;
         description "Access peer IPv4 address";
       }
       leaf access-peer-hostname {
         type string;
       }
       leaf access-peer-ri {
         type string;
         description "Access peer routing instance";
       }
       leaf core-peers {
         type uint32;
         description "Total core peers";
       }
       leaf cp-peers {
         type uint32;
         description "Total cp peers";
       }
       leaf apfe {
         type string;
         description "Anchor PFE";
       }
       leaf apfe-secondary {
         type string;
         description "Secondary Anchor PFE";
       }
       leaf local-seid {
         type uint32;
         description "UPF SEID";
       }
       leaf remote-seid {
         type uint32;
         description "CPF SEID";
       }
       leaf framed-ipv6-route {
         type jt:ipaddr;
         description "Framed IPv6 route";
       }
       leaf framed-ipv4-route {
         type jt:ipaddr;
         description "Framed IPv4 route";
       }
       leaf core-peer-address {
         type jt:ipaddr;
         description "Core data network peer IPv4 address";
       }
       leaf cp-peer-address {
         type jt:ipaddr;
         description "CPF-U network peer IPv4 address";
       }
       list bearer-info {
         leaf ebi-nsapi {
           type uint32;
           description "Bearer EBI/NSAPI";
         }
         leaf state {
           type string;
           description "Session state";
         }
         leaf access-peer-address {
           type jt:ipaddr;
           description "Access peer IPv4 address";
         }
         leaf access-peer-ri {
           type string;
           description "Access peer routing instance";
         }
         leaf local-teid-u {
           type uint32;
           description "Local teid-u";
         }
         leaf remote-teid-u {
           type uint32;
           description "Remote teid-u";
         }
         leaf core-peer-address {
           type jt:ipaddr;
           description "Core data network peer IPv4 address";
         }
         leaf core-peer-ri {
           type string;
           description "Core peer routing instance";
         }
         leaf core-local-teid-u {
           type uint32;
           description "Core-side local teid-u";
         }
         leaf core-remote-teid-u {
           type uint32;
           description "Core-side remote teid-u";
         }
         leaf cp-peer-address {
           type jt:ipaddr;
           description "CPF-U network peer IPv4 address";
         }
         leaf cp-peer-ri {
           type string;
           description "CP-U peer routing instance";
         }
         leaf cp-local-teid-u {
           type uint32;
           description "CP peer local teid-u";
         }
         leaf cp-remote-teid-u {
           type uint32;
           description "CP peer remote teid-u";
         }
         leaf cos-forwarding-class {
           type string;
           description "CoS forwarding class";
         }
         list pdr {
           list qer {
           }
         }
         list urr {
           container downlink-drop-notification {
             leaf reporting-trigger-usage {
               type string;
             }
             leaf start-time-usage {
               type string;
             }
             leaf stop-time-usage {
               type string;
             }
           }
         }
       }
       container session-statistics {
       }
       list qos-flow-info {
         leaf qfi {
           type uint32;
           description "QFI";
         }
         leaf cos-forwarding-class {
           type string;
           description "CoS forwarding class";
         }
         leaf cos-egress-forwarding-class {
           type string;
           description "CoS egress forwarding class";
         }
       }
     }
     list bearer-info {
       list pdr {
         list qer {
         }
       }
       list urr {
         container downlink-drop-notification {
           leaf reporting-trigger-usage {
             type string;
           }
           leaf start-time-usage {
             type string;
           }
           leaf stop-time-usage {
             type string;
           }
         }
       }
     }
     container no-session {
       leaf total-sessions {
         type uint32;
         description "Total Sessions";
       }
       leaf total-bearers {
         type uint32;
         description "Total bearer sessions";
       }
     }
   }
   grouping services-mobile-edge-sessions-detail-cpp-block {
     list peer {
       leaf ip-address {
         type jt:ipaddr;
         description "Session IPv4 address";
       }
       leaf hostname {
         type string;
         description "Session host name";
       }
       list session-info {
         leaf ip-address {
           type jt:ipaddr;
           description "Session IPv4 address";
         }
         leaf state {
           type string;
           description "Session state";
         }
         leaf state-time {
           type string;
           description "State time";
         }
         leaf num-bearers {
           type uint32;
           description "Number of Bearers";
         }
         leaf ipv6-prefix {
           type jt:ipaddr;
           description "Session IPv6 prefix";
         }
         leaf num-qos-flows {
           type uint32;
           description "Number of QoS Flows";
         }
         leaf vrf-id {
           type uint32;
           description "VRF ID";
         }
         leaf apn-name {
           type string;
         }
         leaf cpf-peer-address {
           type jt:ipaddr;
           description "Control peer IPv4 address";
         }
         leaf cpf-peer-hostname {
           type string;
         }
         leaf cpf-peer-ri {
           type string;
           description "CPF peer routing instance";
         }
         leaf access-peer-address {
           type jt:ipaddr;
           description "Access peer IPv4 address";
         }
         leaf access-peer-hostname {
           type string;
         }
         leaf access-peer-ri {
           type string;
           description "Access peer routing instance";
         }
         leaf core-peers {
           type uint32;
           description "Total core peers";
         }
         leaf cp-peers {
           type uint32;
           description "Total cp peers";
         }
         leaf apfe {
           type string;
           description "Anchor PFE";
         }
         leaf apfe-secondary {
           type string;
           description "Secondary Anchor PFE";
         }
         leaf local-seid {
           type uint32;
           description "UPF SEID";
         }
         leaf remote-seid {
           type uint32;
           description "CPF SEID";
         }
         leaf framed-ipv6-route {
           type jt:ipaddr;
           description "Framed IPv6 route";
         }
         leaf framed-ipv4-route {
           type jt:ipaddr;
           description "Framed IPv4 route";
         }
         leaf core-peer-address {
           type jt:ipaddr;
           description "Core data network peer IPv4 address";
         }
         leaf cp-peer-address {
           type jt:ipaddr;
           description "CPF-U network peer IPv4 address";
         }
         list bearer-info {
           leaf ebi-nsapi {
             type uint32;
             description "Bearer EBI/NSAPI";
           }
           leaf state {
             type string;
             description "Session state";
           }
           leaf access-peer-address {
             type jt:ipaddr;
             description "Access peer IPv4 address";
           }
           leaf access-peer-ri {
             type string;
             description "Access peer routing instance";
           }
           leaf local-teid-u {
             type uint32;
             description "Local teid-u";
           }
           leaf remote-teid-u {
             type uint32;
             description "Remote teid-u";
           }
           leaf core-peer-address {
             type jt:ipaddr;
             description "Core data network peer IPv4 address";
           }
           leaf core-peer-ri {
             type string;
             description "Core peer routing instance";
           }
           leaf core-local-teid-u {
             type uint32;
             description "Core-side local teid-u";
           }
           leaf core-remote-teid-u {
             type uint32;
             description "Core-side remote teid-u";
           }
           leaf cp-peer-address {
             type jt:ipaddr;
             description "CPF-U network peer IPv4 address";
           }
           leaf cp-peer-ri {
             type string;
             description "CP-U peer routing instance";
           }
           leaf cp-local-teid-u {
             type uint32;
             description "CP peer local teid-u";
           }
           leaf cp-remote-teid-u {
             type uint32;
             description "CP peer remote teid-u";
           }
           leaf cos-forwarding-class {
             type string;
             description "CoS forwarding class";
           }
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
         list qos-flow-info {
           leaf qfi {
             type uint32;
             description "QFI";
           }
           leaf cos-forwarding-class {
             type string;
             description "CoS forwarding class";
           }
           leaf cos-egress-forwarding-class {
             type string;
             description "CoS egress forwarding class";
           }
         }
       }
     }
     container no-session {
       leaf total-sessions {
         type uint32;
         description "Total Sessions";
       }
       leaf total-bearers {
         type uint32;
         description "Total bearer sessions";
       }
     }
   }
   grouping services-mobile-edge-sessions-extensive-block {
     list session-info {
       leaf ip-address {
         type jt:ipaddr;
         description "Session IPv4 address";
       }
       leaf state {
         type string;
         description "Session state";
       }
       leaf state-time {
         type string;
         description "State time";
       }
       leaf num-bearers {
         type uint32;
         description "Number of Bearers";
       }
       leaf ipv6-prefix {
         type jt:ipaddr;
         description "Session IPv6 prefix";
       }
       leaf num-qos-flows {
         type uint32;
         description "Number of QoS Flows";
       }
       leaf vrf-id {
         type uint32;
         description "VRF ID";
       }
       leaf apn-name {
         type string;
       }
       leaf cpf-peer-address {
         type jt:ipaddr;
         description "Control peer IPv4 address";
       }
       leaf cpf-peer-hostname {
         type string;
       }
       leaf cpf-peer-ri {
         type string;
         description "CPF peer routing instance";
       }
       leaf access-peer-address {
         type jt:ipaddr;
         description "Access peer IPv4 address";
       }
       leaf access-peer-hostname {
         type string;
       }
       leaf access-peer-ri {
         type string;
         description "Access peer routing instance";
       }
       leaf core-peers {
         type uint32;
         description "Total core peers";
       }
       leaf cp-peers {
         type uint32;
         description "Total cp peers";
       }
       leaf apfe {
         type string;
         description "Anchor PFE";
       }
       leaf apfe-secondary {
         type string;
         description "Secondary Anchor PFE";
       }
       leaf local-seid {
         type uint32;
         description "UPF SEID";
       }
       leaf remote-seid {
         type uint32;
         description "CPF SEID";
       }
       leaf framed-ipv6-route {
         type jt:ipaddr;
         description "Framed IPv6 route";
       }
       leaf framed-ipv4-route {
         type jt:ipaddr;
         description "Framed IPv4 route";
       }
       leaf core-peer-address {
         type jt:ipaddr;
         description "Core data network peer IPv4 address";
       }
       leaf cp-peer-address {
         type jt:ipaddr;
         description "CPF-U network peer IPv4 address";
       }
       list bearer-info {
         leaf ebi-nsapi {
           type uint32;
           description "Bearer EBI/NSAPI";
         }
         leaf state {
           type string;
           description "Session state";
         }
         leaf access-peer-address {
           type jt:ipaddr;
           description "Access peer IPv4 address";
         }
         leaf access-peer-ri {
           type string;
           description "Access peer routing instance";
         }
         leaf local-teid-u {
           type uint32;
           description "Local teid-u";
         }
         leaf remote-teid-u {
           type uint32;
           description "Remote teid-u";
         }
         leaf core-peer-address {
           type jt:ipaddr;
           description "Core data network peer IPv4 address";
         }
         leaf core-peer-ri {
           type string;
           description "Core peer routing instance";
         }
         leaf core-local-teid-u {
           type uint32;
           description "Core-side local teid-u";
         }
         leaf core-remote-teid-u {
           type uint32;
           description "Core-side remote teid-u";
         }
         leaf cp-peer-address {
           type jt:ipaddr;
           description "CPF-U network peer IPv4 address";
         }
         leaf cp-peer-ri {
           type string;
           description "CP-U peer routing instance";
         }
         leaf cp-local-teid-u {
           type uint32;
           description "CP peer local teid-u";
         }
         leaf cp-remote-teid-u {
           type uint32;
           description "CP peer remote teid-u";
         }
         leaf cos-forwarding-class {
           type string;
           description "CoS forwarding class";
         }
         list far {
           leaf far-id {
             type uint32;
             description "FAR ID";
           }
           leaf destination-interface {
             type string;
           }
           leaf transport-level-marking {
             type uint32;
           }
           leaf apply-action {
             type string;
           }
           leaf out-hdr-desc {
             type string;
           }
           leaf remote-peer-address {
             type jt:ipaddr;
             description "Remote data network peer IPv4 address";
           }
           leaf remote-teid-u {
             type uint32;
             description "Remote teid-u";
           }
           leaf cos-forwarding-class {
             type string;
             description "CoS forwarding class";
           }
         }
         list pdr {
           leaf pdr-id {
             type uint32;
             description "PDR ID";
           }
           leaf source-interface {
             type string;
           }
           leaf local-teid-u {
             type uint32;
             description "Local teid-u";
           }
           leaf precedence {
             type uint32;
             description "PDR precedence";
           }
           leaf far-id {
             type uint32;
             description "FAR ID";
           }
           leaf urr-id {
             type uint32;
             description "URR ID";
           }
           container tfe {
             leaf tfe-id {
               type uint32;
               description "TFE ID";
             }
           }
           list qer {
             leaf qer-id {
               type uint32;
               description "QER ID";
             }
             leaf qfi {
               type uint32;
               description "QFI";
             }
             leaf rqi {
               type uint32;
               description "RQI";
             }
             container gate-status {
               leaf uplink-gate {
                 type string;
                 description "Uplink Gate";
               }
               leaf downlink-gate {
                 type string;
                 description "Downlink Gate";
               }
             }
             container mbr {
               leaf uplink-mbr {
                 type uint32;
                 description "Uplink MBR";
               }
               leaf downlink-mbr {
                 type uint32;
                 description "Downlink MBR";
               }
             }
             container gbr {
               leaf uplink-gbr {
                 type uint32;
                 description "Uplink GBR";
               }
               leaf downlink-gbr {
                 type uint32;
                 description "Downlink GBR";
               }
             }
           }
           list sdf {
             leaf flow-description {
               type string;
             }
           }
           list qos-flow-id {
             leaf qfi {
               type uint32;
               description "QFI";
             }
           }
           container cos-forwarding-class-info {
             leaf cos-forwarding-class {
               type string;
               description "CoS forwarding class";
             }
             leaf cos-egress-forwarding-class {
               type string;
               description "CoS egress forwarding class";
             }
           }
         }
         list urr {
           leaf id {
             type uint32;
           }
           leaf measurement-method {
             type string;
           }
           leaf reporting-trigger {
             type string;
           }
           leaf time-threshold {
             type uint32;
           }
           leaf time-quota {
             type uint32;
           }
           leaf downlink-drop-threshold {
             type uint64;
           }
           leaf downlink-drop-byte-threshold {
             type uint64;
           }
           leaf measurement-information {
             type string;
           }
           leaf time-usage {
             type uint32;
           }
           container volume-threshold {
             leaf uplink-volume-threshold {
               type uint64;
             }
             leaf downlink-volume-threshold {
               type uint64;
             }
             leaf total-volume-threshold {
               type uint64;
             }
           }
           container volume-quota {
             leaf uplink-volume-quota {
               type uint64;
             }
             leaf downlink-volume-quota {
               type uint64;
             }
             leaf total-volume-quota {
               type uint64;
             }
           }
           container volume-usage {
             leaf reporting-trigger-usage {
               type string;
             }
             leaf start-time-usage {
               type string;
             }
             leaf stop-time-usage {
               type string;
             }
             leaf uplink-volume-usage {
               type uint64;
             }
             leaf downlink-volume-usage {
               type uint64;
             }
             leaf total-volume-usage {
               type uint64;
             }
           }
           container downlink-drop-notification {
             leaf reporting-trigger-usage {
               type string;
             }
             leaf start-time-usage {
               type string;
             }
             leaf stop-time-usage {
               type string;
             }
           }
         }
       }
       container session-statistics {
         leaf session-establishment-request-received {
           type uint64;
           description "Session Establishment Requests Received";
         }
         leaf last-sess-est-req-time {
           type string;
           description "Last Session EST Req Time";
         }
         leaf sess-est-resp-sent {
           type uint32;
           description "Session EST Resp Sent";
         }
         leaf last-sess-est-resp-sent-time {
           type string;
           description "Last Session EST Resp Time";
         }
         leaf session-modification-request-received {
           type uint64;
           description "Session Modification Requests Received";
         }
         leaf last-sess-mod-req-time {
           type string;
           description "Last Session MOD Req Time";
         }
         leaf session-modification-response-sent {
           type uint32;
           description "Session MOD Resp Sent";
         }
         leaf last-session-modification-response-sent-time {
           type string;
           description "Last Session MOD Resp Time";
         }
         leaf session-deletion-request-received {
           type uint64;
           description "Session Deletion Requests Received";
         }
         leaf last-sess-del-req-time {
           type string;
           description "Last Session DEL Req Time";
         }
         leaf sess-del-resp-sent {
           type uint32;
           description "Session DEL Resp Sent";
         }
         leaf last-sess-del-resp-sent-time {
           type string;
           description "Last Session DEL Resp Time";
         }
         list urr-stats {
           leaf urr-id {
             type uint32;
             description "URR ID";
           }
           leaf urr-usage-report {
             type uint32;
             description "URR Usage Report";
           }
           leaf urr-last-usage-report {
             type string;
             description "Last URR Usage Report Time";
           }
         }
         list session-report-statistics {
           leaf usage-report-count {
             type uint32;
             description "Usage Report Count";
           }
           leaf last-usage-report-time {
             type string;
             description "Last Usage Report Time";
           }
           leaf downlink-data-report-count {
             type uint32;
             description "Downlink Data Report Count";
           }
           leaf last-downlink-data-report-time {
             type string;
             description "Downlink Data Report Time";
           }
           leaf error-indication-report-count {
             type uint32;
             description "Error Indication Report Count";
           }
           leaf last-error-indication-report-time {
             type string;
             description "Error Indication Report Time";
           }
           leaf total-session-report-count {
             type uint32;
             description "Total Session Report Count";
           }
         }
       }
       list user-id {
         leaf user-id-imsi {
           type uint64;
           description "Display IMSI";
         }
         leaf user-id-imei {
           type uint64;
           description "Display IMEI";
         }
         leaf user-id-msisdn {
           type uint64;
           description "Display MSISDN";
         }
         leaf user-id-nai {
           type string;
           description "Display NAI";
         }
       }
     }
     container no-session {
       leaf total-sessions {
         type uint32;
         description "Total Sessions";
       }
       leaf total-bearers {
         type uint32;
         description "Total bearer sessions";
       }
     }
   }
   grouping services-mobile-edge-sessions-histogram-block {
     leaf title {
       type string;
       description "Histogram title";
     }
     leaf histogram-ts {
       type string;
     }
     leaf histogram-counters {
       type string;
     }
     container histogram-5minutely {
       leaf title {
         type string;
         description "Histogram title";
       }
       leaf histogram-ts {
         type string;
       }
       leaf histogram-counters {
         type string;
       }
     }
     container histogram-hourly {
       leaf title {
         type string;
         description "Histogram title";
       }
       leaf histogram-ts {
         type string;
       }
       leaf histogram-counters {
         type string;
       }
     }
   }
   grouping services-mobile-edge-session-summary-block {
     container counters {
       leaf session-state-invalid {
         type jt:ipaddr;
         description "Session State Invalid";
       }
       leaf session-state-init {
         type uint32;
         description "Session State Init";
       }
       leaf session-state-wait {
         type uint32;
         description "Session State Wait";
       }
       leaf session-state-established {
         type uint32;
         description "Session State Established";
       }
       leaf session-state-deleting {
         type string;
         description "Session State Deleting";
       }
       leaf session-state-total {
         type uint32;
         description "Session State Total";
       }
       leaf bearer-state-invalid {
         type uint32;
         description "Bearer State Invalid";
       }
       leaf bearer-state-init {
         type uint32;
         description "Bearer State Init";
       }
       leaf bearer-state-wait {
         type uint32;
         description "Bearer State Wait";
       }
       leaf bearer-state-established {
         type uint32;
         description "Bearer State Established";
       }
       leaf bearer-state-deleting {
         type uint32;
         description "Bearer State Deleting";
       }
       leaf bearer-state-total {
         type uint32;
         description "Bearer State total";
       }
       leaf bearer-resource-type-gbr {
         type uint32;
         description "Bearer Resource Type GBR";
       }
       leaf bearer-resource-type-non-gbr {
         type uint32;
         description "Bearer Resource Type Non-GBR";
       }
       leaf bearer-resource-type-total {
         type uint32;
         description "Bearer Resource Type Total";
       }
       leaf bearer-downlink-far-state-forward {
         type uint32;
         description "Bearer Downlink Far State Forward";
       }
       leaf bearer-downlink-far-state-idle {
         type uint32;
         description "Bearer Downlink Far State Idle";
       }
       leaf bearer-downlink-far-state-buff {
         type uint32;
         description "Bearer Downlink Far State Buffering";
       }
       leaf bearer-downlink-far-state-drop {
         type uint32;
         description "Bearer Downlink Far State Drop";
       }
       leaf bearer-downlink-far-state-total {
         type uint32;
         description "Bearer Downlink Far State Total";
       }
       leaf qf-state-established {
         type uint32;
         description "QoS Flow State Established";
       }
       leaf qf-state-wait {
         type uint32;
         description "QoS Flow State Wait";
       }
       leaf qf-state-invalid {
         type uint32;
         description "QoS Flow State Invalid";
       }
       leaf qf-state-total {
         type uint32;
         description "QoS Flow State Total";
       }
       leaf qf-resource-type-gbr {
         type uint32;
         description "QoS Flow Resource Type GBR";
       }
       leaf qf-resource-type-non-gbr {
         type uint32;
         description "QoS Flow Resource Type Non-GBR";
       }
       leaf qf-resource-type-total {
         type uint32;
         description "QoS Flow Resource Type Total";
       }
     }
   }
   grouping services-mobile-edge-session-summary-cpp-block {
     list peer {
       leaf ip-address {
         type jt:ipaddr;
         description "Session IPv4 address";
       }
       leaf hostname {
         type string;
         description "Session host name";
       }
       leaf routing-instance {
         type string;
         description "Routing-instance name";
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
       list session-info {
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
   }
   grouping services-mobile-edge-session-summary-anp-block {
     list peer {
       leaf ip-address {
         type jt:ipaddr;
         description "Session IPv4 address";
       }
       leaf hostname {
         type string;
         description "Session host name";
       }
       leaf routing-instance {
         type string;
         description "Routing-instance name";
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
       list session-info {
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
   }
   grouping services-mobile-edge-session-summary-pic-block {
     list apfe-pic {
       leaf name {
         type string;
         description "Session apn name";
       }
       leaf redundancy-role {
         type string;
       }
       leaf redundancy-sync-state {
         type string;
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
     }
   }
   grouping services-mobile-edge-session-summary-slot-block {
     list apfe-slot {
       leaf name {
         type string;
         description "Session apn name";
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
     }
   }
   grouping services-mobile-edge-session-summary-apns-block {
     list apn {
       leaf name {
         type string;
         description "Session apn name";
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
     }
   }
   grouping services-mobile-edge-session-summary-ag-block {
     list apfe-pic {
       leaf name {
         type string;
         description "Session apn name";
       }
       leaf redundancy-role {
         type string;
       }
       leaf redundancy-sync-state {
         type string;
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
     }
   }
   grouping services-mobile-edge-session-summary-cnp-block {
     list peer {
       leaf ip-address {
         type jt:ipaddr;
         description "Session IPv4 address";
       }
       leaf hostname {
         type string;
         description "Session host name";
       }
       leaf routing-instance {
         type string;
         description "Routing-instance name";
       }
       container counters {
         leaf session-state-invalid {
           type jt:ipaddr;
           description "Session State Invalid";
         }
         leaf session-state-init {
           type uint32;
           description "Session State Init";
         }
         leaf session-state-wait {
           type uint32;
           description "Session State Wait";
         }
         leaf session-state-established {
           type uint32;
           description "Session State Established";
         }
         leaf session-state-deleting {
           type string;
           description "Session State Deleting";
         }
         leaf session-state-total {
           type uint32;
           description "Session State Total";
         }
         leaf bearer-state-invalid {
           type uint32;
           description "Bearer State Invalid";
         }
         leaf bearer-state-init {
           type uint32;
           description "Bearer State Init";
         }
         leaf bearer-state-wait {
           type uint32;
           description "Bearer State Wait";
         }
         leaf bearer-state-established {
           type uint32;
           description "Bearer State Established";
         }
         leaf bearer-state-deleting {
           type uint32;
           description "Bearer State Deleting";
         }
         leaf bearer-state-total {
           type uint32;
           description "Bearer State total";
         }
       }
       list session-info {
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
   }
   grouping services-mobile-edge-sessions-summary-tran-block {
     leaf total-sessions {
       type uint32;
       description "Total Sessions";
     }
   }
   grouping services-mobile-edge-sessions-cpp-info-block {
     list peer {
       leaf ip-address {
         type jt:ipaddr;
         description "Session IPv4 address";
       }
       leaf hostname {
         type string;
         description "Session host name";
       }
       leaf routing-instance {
         type string;
         description "Routing-instance name";
       }
       list session-info {
         leaf ip-address {
           type jt:ipaddr;
           description "Session IPv4 address";
         }
         leaf state {
           type string;
           description "Session state";
         }
         leaf state-time {
           type string;
           description "State time";
         }
         leaf num-bearers {
           type uint32;
           description "Number of Bearers";
         }
         leaf ipv6-prefix {
           type jt:ipaddr;
           description "Session IPv6 prefix";
         }
         leaf num-qos-flows {
           type uint32;
           description "Number of QoS Flows";
         }
         leaf vrf-id {
           type uint32;
           description "VRF ID";
         }
         leaf apn-name {
           type string;
         }
         leaf cpf-peer-address {
           type jt:ipaddr;
           description "Control peer IPv4 address";
         }
         leaf cpf-peer-hostname {
           type string;
         }
         leaf cpf-peer-ri {
           type string;
           description "CPF peer routing instance";
         }
         leaf access-peer-address {
           type jt:ipaddr;
           description "Access peer IPv4 address";
         }
         leaf access-peer-hostname {
           type string;
         }
         leaf access-peer-ri {
           type string;
           description "Access peer routing instance";
         }
         leaf core-peers {
           type uint32;
           description "Total core peers";
         }
         leaf cp-peers {
           type uint32;
           description "Total cp peers";
         }
         leaf apfe {
           type string;
           description "Anchor PFE";
         }
         leaf apfe-secondary {
           type string;
           description "Secondary Anchor PFE";
         }
         leaf local-seid {
           type uint32;
           description "UPF SEID";
         }
         leaf remote-seid {
           type uint32;
           description "CPF SEID";
         }
         leaf framed-ipv6-route {
           type jt:ipaddr;
           description "Framed IPv6 route";
         }
         leaf framed-ipv4-route {
           type jt:ipaddr;
           description "Framed IPv4 route";
         }
         leaf core-peer-address {
           type jt:ipaddr;
           description "Core data network peer IPv4 address";
         }
         leaf cp-peer-address {
           type jt:ipaddr;
           description "CPF-U network peer IPv4 address";
         }
         list bearer-info {
           list pdr {
             list qer {
             }
           }
           list urr {
             container downlink-drop-notification {
               leaf reporting-trigger-usage {
                 type string;
               }
               leaf start-time-usage {
                 type string;
               }
               leaf stop-time-usage {
                 type string;
               }
             }
           }
         }
         container session-statistics {
         }
       }
     }
     container no-session {
       leaf total-sessions {
         type uint32;
         description "Total Sessions";
       }
       leaf total-bearers {
         type uint32;
         description "Total bearer sessions";
       }
     }
   }
   grouping services-mobile-edge-summary-info-block {
     container routing-engine-high-availability {
       leaf graceful-restart {
         type string;
       }
       leaf mastership {
         type string;
       }
       leaf state {
         type string;
         description "Session state";
       }
       leaf bulk-sync {
         type string;
       }
       leaf session-scale {
         type string;
       }
       leaf cpu-load {
         type uint32;
       }
       leaf memory-load {
         type uint32;
       }
       leaf session-load {
         type uint32;
       }
       leaf session-load-top {
         type uint32;
       }
       leaf session-load-top-ts {
         type string;
       }
       leaf gbr-cac-load {
         type uint32;
       }
       leaf gbr-cac-load-top {
         type uint32;
       }
       leaf gbr-cac-load-top-ts {
         type string;
       }
       leaf inflight-load {
         type uint32;
       }
       leaf inflight-load-top {
         type uint32;
       }
       leaf inflight-load-top-ts {
         type string;
       }
       leaf pfe-queue-load {
         type uint32;
       }
       leaf pfe-queue-load-top {
         type uint32;
       }
       leaf pfe-queue-load-top-ts {
         type string;
       }
       leaf aggregate-load {
         type uint32;
       }
       leaf aggregate-load-top {
         type uint32;
       }
       leaf aggregate-load-top-ts {
         type string;
       }
       leaf aggregate-overload {
         type uint32;
       }
       leaf aggregate-overload-top {
         type uint32;
       }
       leaf aggregate-overload-top-ts {
         type string;
       }
       leaf proc-session-msg-per-sec {
         type uint32;
       }
       leaf proc-session-msg-per-sec-top {
         type uint32;
       }
       leaf proc-session-msg-per-sec-top-ts {
         type string;
       }
       leaf recv-session-msg-per-sec {
         type uint32;
       }
       leaf recv-session-msg-per-sec-top {
         type uint32;
       }
       leaf recv-session-msg-per-sec-top-ts {
         type string;
       }
     }
   }
   grouping services-mobile-edge-resources-cac-stats-block {
     container cac-global-stats {
       leaf calls-admitted {
         type uint32;
         description "Total calls admitted";
       }
       leaf calls-rejected {
         type uint32;
         description "Total calls rejected";
       }
       leaf oversubscription-events {
         type uint32;
         description "Number of times allocations exceeded reserved bandwidth";
       }
       list apfe-cac-stats {
         leaf apfe {
           type string;
           description "Anchor PFE";
         }
         leaf reserved-bandwidth {
           type uint32;
           description "Reserved bandwidth in Kbps";
         }
         leaf allocated-bandwidth {
           type uint32;
           description "Allocated badnwidth in Kbps";
         }
         leaf high-watermark {
           type uint32;
           description "High watermark for allocated bandwidth in Kbps";
         }
         leaf oversubscription-events {
           type uint32;
           description "Number of times allocations exceeded reserved bandwidth";
         }
       }
     }
   }
   grouping analytics-agent-information-block {
     list analytics-service-agent-information {
       leaf analytics-service-agent-name {
         type string;
         description "Service agent ID";
       }
       leaf analytics-service-agent-output-plugin-count {
         type int32;
         description "Number of output plugins configured";
       }
       leaf analytics-service-agent-input-plugin-count {
         type int32;
         description "Number of input plugins configured";
       }
       leaf analytics-service-agent-process-id {
         type int32;
         description "Service agent process id(PID)";
       }
       leaf analytics-service-agent-input-plugins {
         type string;
         description "Service agent input plugin list";
       }
       leaf analytics-service-agent-output-plugins {
         type string;
         description "Service agent output plugin list";
       }
     }
     container analytics-controller-information {
       leaf analytics-controller-process-id {
         type int32;
         description "Analytics agent process id(PID)";
       }
       leaf analytics-controller-conf-file {
         type string;
         description "Analytics agent configuration file";
       }
       leaf analytics-controller-log-file {
         type string;
         description "Analytics agent log file";
       }
       leaf analytics-controller-service-agent-count {
         type int32;
         description "Number of service agents";
       }
     }
   }
   grouping probe-results-block {
     list probe-results-terse {
       leaf test-name {
         type string;
         description "Name of test";
       }
       leaf destination-interface {
         type string;
         description "Name of output interface for probes";
       }
       leaf target-address {
         type string;
         description "Target address of test";
       }
       leaf last-status {
         type string;
         description "Status";
       }
       leaf last-status-changed {
         type string;
         description "Last time when status updated";
       }
       leaf twl-local-link {
         type string;
         description "Name of local link for TWAMP-Light probes";
       }
       leaf last-probe-status {
         type string;
         description "Probe status";
       }
     }
     list probe-test-results {
       leaf owner {
         type string;
         description "Test owner name";
       }
       leaf test-name {
         type string;
         description "Name of test";
       }
       leaf target-address {
         type string;
         description "Target address of test";
       }
       leaf target-url {
         type string;
         description "Target URL of test";
       }
       leaf source-address {
         type string;
         description "Source address of test";
       }
       leaf probe-type {
         type string;
         description "Name of the probe";
       }
       leaf icmp-id {
         type uint32;
         description "Icmp id for icmp-ping probes";
       }
       leaf test-size {
         type uint32;
         description "Number of probes in test";
       }
       leaf server-status {
         type string;
         description "TWAMP server is Connected or Not";
       }
       leaf twamp-client-retries {
         type uint32;
         description "Retries to connect TWAMP server at every test-interval";
       }
       leaf server-address {
         type jt:ipaddr;
         description "Server address";
       }
       leaf server-port {
         type uint32;
         description "Server port";
       }
       leaf client-address {
         type jt:ipaddr;
         description "Client address";
       }
       leaf client-port {
         type uint32;
         description "Client port";
       }
       leaf reflector-address {
         type jt:ipaddr;
         description "Reflector address";
       }
       leaf reflector-port {
         type uint32;
         description "Reflector port";
       }
       leaf sender-address {
         type jt:ipaddr;
         description "Sender address";
       }
       leaf sender-port {
         type uint32;
         description "Sender port";
       }
       leaf routing-instance-name {
         type string;
         description "Routing Instance Name";
       }
       leaf destination-interface {
         type string;
         description "Name of output interface for probes";
       }
       leaf twl-local-link {
         type string;
         description "Name of local link for TWAMP-Light probes";
       }
       leaf http-status {
         type uint32;
         description "HTTP Status Code";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf egress-stddev-thresh {
         type uint32;
         description "Maximum egress standard deviation threshold";
       }
       leaf ingress-thresh {
         type uint32;
         description "Maximum ingress delay threshold";
       }
       leaf ingress-jitter-thresh {
         type uint32;
         description "Maximum ingress jitter threshold";
       }
       leaf ingress-stddev-thresh {
         type uint32;
         description "Maximum ingress standard deviation threshold";
       }
       container probe-single-results {
         leaf probe-sent-time {
           type string;
           description "Time at which probe was sent";
         }
         leaf probe-status {
           type string;
           description "Operation response status from probes";
         }
         leaf probe-time {
           type string;
           description "Time at which probe response was received or timed out";
         }
         leaf hardware-timestamp-status {
           type string;
           description "Use of hardware timestamps in probes";
         }
         leaf http-status {
           type uint32;
           description "HTTP Status Code";
         }
         leaf rtt {
           type uint32;
           description "Round trip time of probes";
         }
         leaf ingress {
           type uint32;
           description "Ingress trip time of probes";
         }
         leaf egress {
           type uint32;
           description "Egress trip time of probes";
         }
         leaf egress-jitter {
           type int32;
           description "Egress jitter of probes";
         }
         leaf ingress-jitter {
           type int32;
           description "Ingress jitter of probes";
         }
         leaf round-trip-jitter {
           type int32;
           description "Round trip jitter of probes";
         }
         leaf egress-interarrival-jitter {
           type int32;
           description "Egress interarrival jitter of probes";
         }
         leaf ingress-interarrival-jitter {
           type int32;
           description "Ingress interarrival jitter of probes";
         }
         leaf round-trip-interarrival-jitter {
           type int32;
           description "Round trip interarrival jitter of probes";
         }
         leaf owner {
           type string;
           description "Test owner name";
         }
         leaf test-name {
           type string;
           description "Name of test";
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-last-test-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-moving-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-global-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
       container probe-test-hwts-err-stats {
         leaf invalid-client-recv-ts-cntr {
           type uint32;
           description "Client recv timestamp less than Client send timestamp";
         }
         leaf invalid-client-nots-cntr {
           type uint32;
           description "Client timestamps (T1, T4) are marked as deadbeef";
         }
         leaf invalid-server-send-ts-cntr {
           type uint32;
           description "Server send timestamp less than Server recv timestamp";
         }
         leaf invalid-server-spent-time-cntr {
           type uint32;
           description "Server side spent time greater than RTT";
         }
         leaf pkt-rcvd-after-timeout-cntr {
           type uint32;
           description "RTT is greater than probe-interval";
         }
       }
     }
   }
   grouping history-results-block {
     list history-test-results {
       leaf owner {
         type string;
         description "Test owner name";
       }
       leaf test-name {
         type string;
         description "Name of test";
       }
       leaf probe-type {
         type string;
         description "Name of the probe";
       }
       leaf icmp-id {
         type uint32;
         description "Icmp id for icmp-ping probes";
       }
       leaf target-address {
         type string;
         description "Target address of test";
       }
       leaf target-url {
         type string;
         description "Target URL of test";
       }
       leaf source-address {
         type string;
         description "Source address of test";
       }
       leaf destination-interface {
         type string;
         description "Name of output interface for probes";
       }
       leaf twl-local-link {
         type string;
         description "Name of local link for TWAMP-Light probes";
       }
       leaf loss-thresh-total {
         type uint32;
         description "Maximum number of all lost probes";
       }
       leaf loss-thresh-succ {
         type uint32;
         description "Maximum number of successive lost probes";
       }
       leaf delay-thresh {
         type uint32;
         description "Maximum delay threshold";
       }
       leaf jitter-thresh {
         type uint32;
         description "Maximum jitter threshold";
       }
       leaf stddev-thresh {
         type uint32;
         description "Maximum standard deviation threshold";
       }
       leaf egress-thresh {
         type uint32;
         description "Maximum egress delay threshold";
       }
       leaf egress-jitter-thresh {
         type uint32;
         description "Maximum egress jitter threshold";
       }
       leaf ingress-thresh {
         type uint32;
         description "Maximum ingress delay threshold";
       }
       leaf ingress-jitter-thresh {
         type uint32;
         description "Maximum ingress jitter threshold";
       }
       container probe-single-results {
         leaf probe-sent-time {
           type string;
           description "Time at which probe was sent";
         }
         leaf probe-status {
           type string;
           description "Operation response status from probes";
         }
         leaf probe-time {
           type string;
           description "Time at which probe response was received or timed out";
         }
         leaf hardware-timestamp-status {
           type string;
           description "Use of hardware timestamps in probes";
         }
         leaf http-status {
           type uint32;
           description "HTTP Status Code";
         }
         leaf rtt {
           type uint32;
           description "Round trip time of probes";
         }
         leaf ingress {
           type uint32;
           description "Ingress trip time of probes";
         }
         leaf egress {
           type uint32;
           description "Egress trip time of probes";
         }
         leaf egress-jitter {
           type int32;
           description "Egress jitter of probes";
         }
         leaf ingress-jitter {
           type int32;
           description "Ingress jitter of probes";
         }
         leaf round-trip-jitter {
           type int32;
           description "Round trip jitter of probes";
         }
         leaf egress-interarrival-jitter {
           type int32;
           description "Egress interarrival jitter of probes";
         }
         leaf ingress-interarrival-jitter {
           type int32;
           description "Ingress interarrival jitter of probes";
         }
         leaf round-trip-interarrival-jitter {
           type int32;
           description "Round trip interarrival jitter of probes";
         }
         leaf owner {
           type string;
           description "Test owner name";
         }
         leaf test-name {
           type string;
           description "Name of test";
         }
       }
       container probe-test-current-results {
         container probe-test-generic-results {
           leaf results-scope {
             type string;
             description "Scope of results";
           }
           leaf probes-sent {
             type uint32;
             description "Number of probes sent";
           }
           leaf probe-responses {
             type uint32;
             description "Responses from probes";
           }
           leaf loss-percentage {
             type string;
             description "Percentage of probes lost (no response)";
           }
           container probe-last-test-info {
             leaf last-test-time {
               type string;
               description "Time at which last test was completed";
             }
           }
           container probe-test-rtt {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-egress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-ingress-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-positive-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-negative-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container probe-test-round-trip-jitter {
             container probe-summary-results {
               leaf probe-results-type {
                 type string;
                 description "Results type";
               }
               leaf samples {
                 type uint32;
                 description "Number of samples";
               }
               leaf min-delay {
                 type uint32;
                 description "Minimum delay time";
               }
               leaf max-delay {
                 type uint32;
                 description "Maximum delay time";
               }
               leaf avg-delay {
                 type uint32;
                 description "Average delay time";
               }
               leaf jitter-delay {
                 type uint32;
                 description "Difference between maximum and minimum delay times";
               }
               leaf stddev-delay {
                 type uint64;
                 description "Standard deviation of delay time";
               }
               leaf sum-delay {
                 type uint64;
                 description "Sum of delay times";
               }
             }
           }
           container rpm-results-thresh {
             leaf rtt-thresh {
               type uint32;
               description "Round trip time thresh";
             }
             leaf rtt-jitter-thresh {
               type uint32;
               description "Round trip jitter threshold";
             }
             leaf rtt-stddev-thresh {
               type uint32;
               description "Round trip standard deviaion thresh";
             }
             leaf igr-thresh {
               type uint32;
               description "Ingress threshold";
             }
             leaf igr-jitter-thresh {
               type uint32;
               description "Ingress jitter threshold";
             }
             leaf igr-stddev-thresh {
               type uint32;
               description "Ingress standard deviation threshold";
             }
             leaf egr-thresh {
               type uint32;
               description "Egress threshold";
             }
             leaf egr-jitter-thresh {
               type uint32;
               description "Egress jitter threshold";
             }
             leaf egr-stddev-thresh {
               type uint32;
               description "Egress standared deviation threshold";
             }
           }
         }
       }
     }
   }
   grouping active-servers-block {
     list configured-servers {
       leaf protocol {
         type string;
         description "Protocol";
       }
       leaf port {
         type uint32;
         description "Port";
       }
       leaf destination-interface {
         type string;
         description "Name of output interface for probes";
       }
     }
   }
   grouping twamp-client-information-block {
     list client-connection {
       description "Client connection information";
       leaf connection-name {
         type string;
         description "TWAMP Client control connection name";
       }
       leaf client-address {
         type jt:ipaddr;
         description "Client address";
       }
       leaf client-port {
         type uint32;
         description "Client port";
       }
       leaf server-address {
         type jt:ipaddr;
         description "Server address";
       }
       leaf server-port {
         type uint32;
         description "Server port";
       }
       leaf session-count {
         type uint32;
         description "Number of sessions";
       }
       leaf authentication-mode {
         type string;
         description "Authentication mode";
       }
     }
     list twamp-test-session {
       description "TWAMP Test Session information";
       leaf connection-name {
         type string;
         description "TWAMP Client control connection name";
       }
       leaf session-name {
         type string;
         description "TWAMP Client test session name";
       }
       leaf sender-address {
         type jt:ipaddr;
         description "Sender address";
       }
       leaf sender-port {
         type uint32;
         description "Sender port";
       }
       leaf reflector-address {
         type jt:ipaddr;
         description "Reflector address";
       }
       leaf reflector-port {
         type uint32;
         description "Reflector port";
       }
     }
   }
   grouping twamp-server-information-block {
     list connection {
       description "Server connection";
       leaf connection-id {
         type uint32;
         description "Connection ID";
       }
       leaf client-address {
         type jt:ipaddr;
         description "Client address";
       }
       leaf client-port {
         type uint32;
         description "Client port";
       }
       leaf server-address {
         type jt:ipaddr;
         description "Server address";
       }
       leaf server-port {
         type uint32;
         description "Server port";
       }
       leaf session-count {
         type uint32;
         description "Number of sessions";
       }
       leaf authentication-mode {
         type string;
         description "Authentication mode";
       }
     }
     container server {
       description "Server information";
       list session {
         description "Server session";
         leaf session-id {
           type uint32;
           description "Session ID";
         }
         leaf connection-id {
           type uint32;
           description "Connection ID";
         }
         leaf sender-address {
           type jt:ipaddr;
           description "Sender address";
         }
         leaf sender-port {
           type uint32;
           description "Sender port";
         }
         leaf reflector-address {
           type jt:ipaddr;
           description "Reflector address";
         }
         leaf reflector-port {
           type uint32;
           description "Reflector port";
         }
         leaf session-state {
           type string;
           description "Session state";
         }
         leaf authentication-mode {
           type string;
           description "Authentication mode";
         }
         leaf ip-version {
           type uint32;
           description "IP version";
         }
         leaf padding-length {
           type uint32;
           description "Padding length";
         }
         leaf start-time {
           type string;
           description "Starting time";
         }
         leaf timeout {
           type uint32;
           description "Timeout";
         }
         container packet-statistics {
           leaf request-sessions-received {
             type uint32;
             description "Request sessions received";
           }
           leaf accept-sessions-sent {
             type uint32;
             description "Accept sessions sent";
           }
           leaf start-sessions-received {
             type uint32;
             description "Start sessions received";
           }
           leaf stop-sessions-received {
             type uint32;
             description "Stop sessions received";
           }
           leaf test-packets-received {
             type uint32;
             description "Test packets received";
           }
           leaf test-packets-reflected {
             type uint32;
             description "Test packets reflected";
           }
           leaf last-sequence-number-received {
             type uint32;
             description "Last sequence number received";
           }
           leaf last-sequence-number-sent {
             type uint32;
             description "Last sequence number sent";
           }
           leaf test-packets-dropped {
             type uint32;
             description "Test packets dropped";
           }
           container test-packets-dropped-details {
             leaf session-nonexist {
               type uint32;
               description "Test packets dropped because session does not exist";
             }
             leaf session-notactive {
               type uint32;
               description "Test packets dropped because session is not active";
             }
             leaf packet-unsupported {
               type uint32;
               description "Packet unsupported";
             }
             leaf packet-malformed {
               type uint32;
               description "Packet malformed";
             }
             leaf internal-error {
               type uint32;
               description "Internal error";
             }
           }
         }
       }
     }
     container server-statistics {
       description "Server statistics";
       container packet-statistics {
         description "Test session packet statistics";
         container test-packets-dropped-details {
           description "Test packets dropped details";
           leaf session-nonexist {
             type uint32;
             description "Test packets dropped because session does not exist";
           }
           leaf session-notactive {
             type uint32;
             description "Test packets dropped because session is not active";
           }
           leaf packet-unsupported {
             type uint32;
             description "Packet unsupported";
           }
           leaf packet-malformed {
             type uint32;
             description "Packet malformed";
           }
           leaf internal-error {
             type uint32;
             description "Internal error";
           }
         }
       }
     }
   }
   grouping secintel-recommended-action-block {
     leaf secintel-recommended-action-name {
       type string;
     }
     leaf secintel-recommended-action-property {
       type string;
     }
     leaf secintel-recommended-action-value {
       type string;
     }
     leaf secintel-recommended-action-action {
       type string;
     }
   }
   grouping secintel-redirect-files-block {
     leaf secintel-redirect-files-name {
       type string;
     }
     leaf secintel-redirect-files-size {
       type uint64;
     }
     leaf secintel-redirect-files-time {
       type string;
     }
     leaf secintel-redirect-file-content {
       type string;
     }
   }
   grouping secintel-statistics-block {
     leaf secintel-statistics-category {
       type string;
     }
     leaf secintel-statistics-profile {
       type string;
     }
     leaf secintel-statistics-total {
       type uint32;
     }
     leaf secintel-statistics-permit {
       type uint32;
     }
     leaf secintel-statistics-block-drop {
       type uint32;
     }
     leaf secintel-statistics-block-close {
       type uint32;
     }
     leaf secintel-statistics-close-redirect {
       type uint32;
     }
     leaf secintel-statistics-rs-permit {
       type uint32;
     }
     leaf-list logical-system-name {
       type string;
       description "Name of the logical system";
     }
     leaf-list dns-logical-system {
       type string;
       description "Logical system name";
     }
     leaf-list sm-dns-logical-system {
       type string;
       description "Logical system name";
     }
     leaf-list sm-dns-wl-logical-system {
       type string;
       description "Logical system name";
     }
   }
   grouping dns-statistics-block {
     leaf dns-statistics-white-category {
       type string;
     }
     leaf dns-statistics-udp-requests {
       type uint64;
     }
     leaf dns-statistics-udp-permit {
       type uint64;
     }
     leaf dns-statistics-tcp-requests {
       type uint64;
     }
     leaf dns-statistics-tcp-permit {
       type uint64;
     }
     leaf dns-statistics-space {
       type string;
     }
     leaf dns-statistics-category {
       type string;
     }
     leaf dns-statistics-profile {
       type string;
     }
     leaf dns-statistics-proto {
       type string;
     }
     leaf dns-statistics-tcp-proto {
       type string;
     }
     leaf dns-statistics-querytype {
       type string;
     }
     leaf dns-statistics-requests {
       type uint64;
     }
     leaf dns-statistics-sinkhole {
       type uint64;
     }
     leaf dns-statistics-drop {
       type uint64;
     }
     leaf dns-statistics-permit {
       type uint64;
     }
     leaf dns-statistics-log {
       type uint64;
     }
     leaf dns-statistics-total {
       type string;
     }
     leaf dns-statistics-total-requests {
       type uint64;
     }
     leaf dns-statistics-total-sinkhole {
       type uint64;
     }
     leaf dns-statistics-total-drop {
       type uint64;
     }
     leaf dns-statistics-total-permit {
       type uint64;
     }
     leaf dns-statistics-total-log {
       type uint64;
     }
     leaf-list logical-system-name {
       type string;
       description "Name of the logical system";
     }
     leaf-list dns-logical-system {
       type string;
       description "Logical system name";
     }
     leaf-list sm-dns-logical-system {
       type string;
       description "Logical system name";
     }
     leaf-list sm-dns-wl-logical-system {
       type string;
       description "Logical system name";
     }
     leaf dns-statistics-udp-proto {
       type string;
     }
   }
   grouping dns-filtering-cache-block {
     leaf dns-cache-refresh-rate {
       type uint32;
     }
     leaf dns-cache-lsys-name {
       type string;
     }
     leaf dns-cache-entry-name {
       type string;
     }
     leaf dns-cache-entry-ttl {
       type uint32;
     }
     leaf dns-cache-entry-prevalence {
       type uint32;
     }
     leaf dns-cache-entry-verdict {
       type string;
     }
     leaf dns-cache-entry-hitcount {
       type uint32;
     }
   }
   grouping dns-filtering-cache-summary-block {
     leaf dns-cache-summary-refresh-rate {
       type uint32;
     }
     leaf dns-cache-summary-lsys-name {
       type string;
     }
     leaf dns-cache-total-count {
       type string;
     }
     leaf dns-cache-benign-count {
       type uint32;
     }
     leaf dns-cache-c2-count {
       type uint32;
     }
   }
   grouping dns-filtering-cache-c2-block {
     leaf dns-cache-refresh-rate-c2 {
       type uint32;
     }
     leaf dns-cache-lsys-name-c2 {
       type string;
     }
     leaf dns-cache-entry-name-c2 {
       type string;
     }
     leaf dns-cache-entry-ttl-c2 {
       type uint32;
     }
     leaf dns-cache-entry-prevalence-c2 {
       type uint32;
     }
     leaf dns-cache-entry-verdict-c2 {
       type string;
     }
     leaf dns-cache-entry-hitcount-c2 {
       type uint32;
     }
   }
   grouping dns-filtering-cache-benign-block {
     leaf dns-cache-refresh-rate-benign {
       type uint32;
     }
     leaf dns-cache-lsys-name-benign {
       type string;
     }
     leaf dns-cache-entry-name-benign {
       type string;
     }
     leaf dns-cache-entry-ttl-benign {
       type uint32;
     }
     leaf dns-cache-entry-prevalence-benign {
       type uint32;
     }
     leaf dns-cache-entry-verdict-benign {
       type string;
     }
     leaf dns-cache-entry-hitcount-benign {
       type uint32;
     }
   }
   grouping services-match-policies-information-block {
     list services-match-policies {
       description "Rule match result";
       leaf policy-match {
         type string;
         description "Policy match";
       }
       leaf policy-direction {
         type string;
         description "Policy direction";
       }
       leaf policy-action {
         type string;
         description "Policy action";
       }
       leaf policy-state {
         type string;
         description "Policy state";
       }
       leaf source-address-title {
         type string;
         description "Source address title";
       }
       leaf source-address {
         type string;
         description "Source address";
       }
       leaf destination-address-title {
         type string;
         description "Destination address tite";
       }
       leaf destination-address {
         type string;
         description "Destination address";
       }
       leaf application-type {
         type string;
         description "Application type";
       }
       leaf ip-protocol {
         type uint32;
         description "Ip protocol";
       }
       leaf policy-timeout {
         type string;
         description "Policy timeout";
       }
       leaf destination-port {
         type string;
         description "Destination port";
       }
     }
   }
   grouping service-cos-statistics-information-block {
     container service-cos-statistics-entry {
       leaf interface-name {
         type string;
         description "Name of the adaptive services interface";
       }
       leaf service-set-name {
         type string;
         description "Name of the service set";
       }
       container cos-stats-service-set-dscp-information {
         list cos-stats-service-set-dscp-entry {
           leaf received-dscp {
             type string;
             description "Received DiffServ Code Point";
           }
           leaf total-received-dscp-packets {
             type uint32;
             description "Total packets received per DSCP";
           }
           leaf total-marked-dscp-packets {
             type uint32;
             description "Total packets marked per DSCP";
           }
         }
       }
       container cos-stats-service-set-forwarding-class-information {
         list cos-stats-service-set-forwarding-class-entry {
           leaf received-forwarding-class {
             type uint32;
             description "Received forwarding class";
           }
           leaf total-received-forwarding-class-packets {
             type uint32;
             description "Total packets received per forwarding class";
           }
           leaf total-assigned-forwarding-class-packets {
             type uint32;
             description "Total packets assigned per forwarding class";
           }
         }
       }
     }
   }
   grouping service-hcm-statistics-information-block {
     container service-hcm-statistics-entry {
       leaf interface-name {
         type string;
         description "Name of the adaptive services interface";
       }
       container hcm-stats-rule-information {
         list hcm-stats-rule-entry {
           leaf term-number {
             type uint32;
             description "Term number";
           }
           leaf total-term-count {
             type uint32;
             description "Total count per rule-term";
           }
           leaf hcm-rule-name {
             type string;
             description "Rule name";
           }
         }
       }
     }
   }
   grouping service-hcm-pic-statistics-information-block {
     leaf interface-name {
       type string;
       description "Name of the adaptive services interface";
     }
     leaf hcm-plugin-sess-interest {
       type uint64;
       description "Number of Session Interest events";
     }
     leaf hcm-plugin-sess-create {
       type uint64;
       description "Number of Session Create events";
     }
     leaf hcm-plugin-sess-close {
       type uint64;
       description "Number of Session Close events";
     }
     leaf hcm-plugin-sess-destroy {
       type uint64;
       description "Number of Session Destroy events";
     }
     leaf hcm-plugin-data-event {
       type uint64;
       description "Number of Session Data events";
     }
     leaf hcm-plugin-no-sess-ext {
       type uint64;
       description "Number of Session Handle failures";
     }
     leaf hcm-plugin-invalid-sess-ext {
       type uint64;
       description "Number of Session Handles invalid";
     }
     leaf hcm-plugin-sess-ext-alloc {
       type uint64;
       description "Number of Session Extension allocations";
     }
     leaf hcm-plugin-sess-ext-alloc-fail {
       type uint64;
       description "Number of Session Extension alloc failures";
     }
     leaf hcm-plugin-sess-ext-free {
       type uint64;
       description "Number of Session Extension frees";
     }
     leaf hcm-plugin-subsc-ext-alloc {
       type uint64;
       description "Number of Subscriber Extension allocations";
     }
     leaf hcm-plugin-subsc-ext-alloc-fail {
       type uint64;
       description "Number of Subscriber Extension alloc failures";
     }
     leaf hcm-plugin-subsc-ext-free {
       type uint64;
       description "Number of Subscriber Extension frees";
     }
     leaf hcm-plugin-sess-ignore {
       type uint64;
       description "Number of Sessions ignored";
     }
     leaf hcm-plugin-no-stbuf-hdl {
       type uint64;
       description "Total number missing stbuf";
     }
     leaf hcm-plugin-stbuf-init {
       type uint64;
       description "Number of stbuf initializations";
     }
     leaf hcm-plugin-stbuf-init-fail {
       type uint64;
       description "Number of stbuf initialization failures";
     }
     leaf hcm-plugin-stbuf-store-fail {
       type uint64;
       description "Number of stbuf store failures";
     }
     leaf hcm-plugin-stbuf-dstry {
       type uint64;
       description "Number of stbuf frees";
     }
     leaf hcm-plugin-stbuf-dstry-fail {
       type uint64;
       description "Number of stbuf free failures";
     }
     leaf hcm-plugin-stbuf-send {
       type uint64;
       description "Number of stbuf sends";
     }
     leaf hcm-plugin-stbuf-send-fail {
       type uint64;
       description "Number of stbuf send failures";
     }
     leaf hcm-plugin-stbuf-recv {
       type uint64;
       description "Number of stbuf receives";
     }
     leaf hcm-plugin-stbuf-throttled {
       type uint64;
       description "Number of stbuf throttles";
     }
     leaf hcm-plugin-stbuf-invalid {
       type uint64;
       description "Number of invalid stbuf";
     }
     leaf hcm-plugin-thr-creates {
       type uint64;
       description "Number of THR creates";
     }
     leaf hcm-plugin-no-thr-hdl {
       type uint64;
       description "Number of missing THR handles";
     }
     leaf hcm-plugin-thr-hdl-create-fail {
       type uint64;
       description "Number of THR create failures";
     }
     leaf hcm-plugin-thr-hdl-store-fail {
       type uint64;
       description "Number of THR store failures";
     }
     leaf hcm-plugin-thr-short-circuit-fail {
       type uint64;
       description "Number of THR short circuit failures";
     }
     leaf hcm-plugin-thr-state-update-fail {
       type uint64;
       description "Number of THR update failures";
     }
     leaf hcm-plugin-thr-state-update {
       type uint64;
       description "Number of THR state updates";
     }
     leaf hcm-plugin-thr-dstry-fail {
       type uint64;
       description "Number of THR destroy failures";
     }
     leaf hcm-plugin-thr-dstry {
       type uint64;
       description "Number of THR destroys";
     }
     leaf hcm-plugin-jcpp-hdl-alloc {
       type uint64;
       description "Number of JCPP handle allocations";
     }
     leaf hcm-plugin-jcpp-hdl-alloc-fail {
       type uint64;
       description "Number of JCPP handle allocation failures";
     }
     leaf hcm-plugin-hdr-insert {
       type uint64;
       description "Number of HCM Header Insertions";
     }
     leaf hcm-plugin-hdr-insert-fail {
       type uint64;
       description "Number of HCM Header Insertion failures";
     }
     leaf hcm-plugin-hdr-rename {
       type uint64;
       description "Number of HCM Header Renamings";
     }
     leaf hcm-plugin-hdr-rename-fail {
       type uint64;
       description "Number of HCM Header Renaming failures";
     }
     leaf hcm-plugin-ipv4-mask-modification {
       type uint64;
       description "Number of HCM IPV4 Mask modifications";
     }
     leaf hcm-plugin-ipv6-mask-modification {
       type uint64;
       description "Number of HCM IPV6 Mask modifications";
     }
     leaf hcm-plugin-tag-too-large {
       type uint64;
       description "Number of HCM tags too large";
     }
     leaf hcm-plugin-tag-encrypt-fail {
       type uint64;
       description "Number of HCM tag encryption failures";
     }
     leaf hcm-plugin-total-request {
       type uint64;
       description "Number of times HCM requests";
     }
     leaf hcm-plugin-no-subsc {
       type uint64;
       description "Number of missing Subscribers in HCM";
     }
     leaf hcm-plugin-missing-subsc-attribute {
       type uint64;
       description "Number of missing subscriber attributes";
     }
     leaf hcm-plugin-missing-ipv4-attribute {
       type uint64;
       description "Number of missing ipv4 attributes";
     }
     leaf hcm-plugin-missing-ipv6-attribute {
       type uint64;
       description "Number of missing ipv6 attributes";
     }
     leaf hcm-plugin-both-ipv4-ipv6-attribute {
       type uint64;
       description "Number of HCM IPV4/IPV6 tag insertions";
     }
   }
   grouping service-pgcp-flow-table-information-block {
     list pgcp-per-service-set-flow-table {
       description "Flows sorted by service set";
       leaf interface-name {
         type string;
         description "Name of the adaptive services interface";
       }
       leaf service-set-name {
         type string;
         description "Name of the service set";
       }
       list service-pgcp-flow-table {
         description "Stateful firewall flows";
         leaf-list service-pgcp-flow-table.heading {
           type string;
           description "Stateful firewall flows";
         }
         list pgcp-flow-entry {
           description "Flow brief information";
           leaf pgcp-flow-protocol {
             type string;
             description "PGCP Flow protocol description";
           }
           leaf pgcp-flow-source-ip {
             type string;
             description "PGCP Source IP address";
           }
           leaf pgcp-flow-source-port {
             type int32;
             description "PGCP Source port address";
           }
           leaf pgcp-flow-destination-ip {
             type string;
             description "Flow destination IP address";
           }
           leaf pgcp-flow-destination-port {
             type string;
             description "PGCP Flow destination port";
           }
           leaf pgcp-flow-state {
             type string;
             description "Flow state";
           }
           leaf pgcp-flow-direction {
             type string;
             description "PGCP Flow direction";
           }
           leaf pgcp-flow-frame-counter {
             type uint64;
             description "Number of frames transmitted";
           }
           leaf pgcp-flow-gate-id {
             type uint64;
             description "PGCP gate-id";
           }
           leaf pgcp-flow-table-byte-count {
             type uint64;
             description "PGCP Flow byte count";
           }
           leaf pgcp-flow-table-role {
             type string;
             description "Role of flow in conversation";
           }
           leaf pgcp-flow-table-timeout {
             type uint64;
             description "Timeout value of PGCP flow (seconds)";
           }
           leaf pgcp-flow-table-protocol-detail {
             type string;
             description "PGCP Flow protocol detail information";
           }
           leaf flow-gate-tman-policing {
             type string;
             description "Install/uninstall a traffic management policing for this gate";
           }
           leaf flow-gate-sdr {
             type uint32;
             description "Sustainable data rate threshold for a gate";
           }
           leaf flow-gate-sdr-mbs {
             type uint32;
             description "Maximum sdr burst size limit for a gate";
           }
           leaf flow-gate-pdr {
             type uint32;
             description "Peak data rate threshold for a gate";
           }
           leaf flow-gate-pdr-mbs {
             type uint32;
             description "Maximum pdr burst size limit for a gate";
           }
           leaf source-routing-instance {
             type string;
             description "Source routing-instance";
           }
           leaf destination-routing-instance {
             type string;
             description "Destination routing-instance";
           }
           leaf flow-replication-status {
             type string;
             description "Flow replication status with backup Data-Pic, values: In-Progress/Disabled/Completed";
           }
           leaf pgcp-flow-table-tcp-window-size {
             type uint64;
             description "PGCP TCP protocol window size";
           }
           leaf pgcp-flow-table-tcp-acknowledge {
             type uint64;
             description "PGCP TCP protocol acknowledge";
           }
           leaf pgcp-flow-table-tcp-tickle {
             type uint64;
             description "PGCP Time between TCP tickles (seconds)";
           }
           container pgcp-flow-nat {
             description "NAT translation";
             leaf pgcp-flow-nat.nat-type {
               type string;
               description "NAT translation";
             }
             leaf pgcp-flow-nat-ip {
               type string;
               description "PGCP NAT IP address";
             }
             leaf pgcp-flow-nat-port {
               type string;
               description "PGCP NAT port";
             }
             leaf pgcp-flow-translated-ip {
               type string;
               description "Translated PGCP IP address";
             }
             leaf pgcp-flow-translated-port {
               type string;
               description "Translated PGCP port";
             }
           }
         }
       }
     }
   }
   grouping service-pgcp-conversation-information-block {
     container pgcp-per-service-set-conversation {
       description "Show conversations";
       leaf interface-name {
         type string;
         description "Name of the adaptive services interface";
       }
       leaf service-set-name {
         type string;
         description "Name of the service set";
       }
       list pgcp-conversation {
         description "Stateful firewall conversations";
         leaf pgcp-flow-table-conv-initiator {
           type int32;
           description "Number of initiator flows";
         }
         leaf pgcp-flow-table-conv-responder {
           type int32;
           description "Number of responder flows";
         }
         list service-pgcp-flow-table {
           description "Stateful firewall flows";
           leaf-list service-pgcp-flow-table.heading {
             type string;
             description "Stateful firewall flows";
           }
           list pgcp-flow-entry {
             description "Flow brief information";
             leaf pgcp-flow-protocol {
               type string;
               description "PGCP Flow protocol description";
             }
             leaf pgcp-flow-source-ip {
               type string;
               description "PGCP Source IP address";
             }
             leaf pgcp-flow-source-port {
               type int32;
               description "PGCP Source port address";
             }
             leaf pgcp-flow-destination-ip {
               type string;
               description "Flow destination IP address";
             }
             leaf pgcp-flow-destination-port {
               type string;
               description "PGCP Flow destination port";
             }
             leaf pgcp-flow-state {
               type string;
               description "Flow state";
             }
             leaf pgcp-flow-direction {
               type string;
               description "PGCP Flow direction";
             }
             leaf pgcp-flow-frame-counter {
               type uint64;
               description "Number of frames transmitted";
             }
             leaf pgcp-flow-gate-id {
               type uint64;
               description "PGCP gate-id";
             }
             leaf pgcp-flow-table-byte-count {
               type uint64;
               description "PGCP Flow byte count";
             }
             leaf pgcp-flow-table-role {
               type string;
               description "Role of flow in conversation";
             }
             leaf pgcp-flow-table-timeout {
               type uint64;
               description "Timeout value of PGCP flow (seconds)";
             }
             leaf pgcp-flow-table-protocol-detail {
               type string;
               description "PGCP Flow protocol detail information";
             }
             leaf flow-gate-tman-policing {
               type string;
               description "Install/uninstall a traffic management policing for this gate";
             }
             leaf flow-gate-sdr {
               type uint32;
               description "Sustainable data rate threshold for a gate";
             }
             leaf flow-gate-sdr-mbs {
               type uint32;
               description "Maximum sdr burst size limit for a gate";
             }
             leaf flow-gate-pdr {
               type uint32;
               description "Peak data rate threshold for a gate";
             }
             leaf flow-gate-pdr-mbs {
               type uint32;
               description "Maximum pdr burst size limit for a gate";
             }
             leaf source-routing-instance {
               type string;
               description "Source routing-instance";
             }
             leaf destination-routing-instance {
               type string;
               description "Destination routing-instance";
             }
             leaf flow-replication-status {
               type string;
               description "Flow replication status with backup Data-Pic, values: In-Progress/Disabled/Completed";
             }
             leaf pgcp-flow-table-tcp-window-size {
               type uint64;
               description "PGCP TCP protocol window size";
             }
             leaf pgcp-flow-table-tcp-acknowledge {
               type uint64;
               description "PGCP TCP protocol acknowledge";
             }
             leaf pgcp-flow-table-tcp-tickle {
               type uint64;
               description "PGCP Time between TCP tickles (seconds)";
             }
             container pgcp-flow-nat {
               description "NAT translation";
               leaf pgcp-flow-nat.nat-type {
                 type string;
                 description "NAT translation";
               }
               leaf pgcp-flow-nat-ip {
                 type string;
                 description "PGCP NAT IP address";
               }
               leaf pgcp-flow-nat-port {
                 type string;
                 description "PGCP NAT port";
               }
               leaf pgcp-flow-translated-ip {
                 type string;
                 description "Translated PGCP IP address";
               }
               leaf pgcp-flow-translated-port {
                 type string;
                 description "Translated PGCP port";
               }
             }
           }
         }
       }
     }
   }
   grouping pgcpd-active-configuration-block {
     list virtual-interface-entry {
       leaf virtual-interface-name {
         type string;
       }
       leaf routing-instance {
         type string;
       }
       leaf interface-name {
         type string;
         description "Name of the adaptive services interface";
       }
       leaf vif-service-state {
         type string;
       }
     }
     list controller-entry {
       leaf controller-name {
         type string;
       }
       leaf remote-ip-address {
         type string;
       }
       leaf remote-port {
         type uint32;
       }
     }
     container h248-timers-entry {
       leaf maximum-waiting-delay {
         type uint32;
       }
       leaf tmax-retransmission-delay {
         type uint32;
       }
       leaf initial-average-ack-delay {
         type uint32;
       }
       leaf maximum-net-propagation-delay {
         type uint32;
       }
     }
     container h248-options-entry {
       leaf wildcard-response-service-change {
         type string;
       }
       leaf audit-observed-events-returns-history {
         type string;
         description "Activation of event history";
       }
       leaf h248-profile {
         type string;
       }
     }
     container base-root-entry {
       description "Array of h248 base root properties";
       leaf brp_name {
         type string;
         description "Property's name";
       }
       leaf brp_minimum {
         type uint32;
         description "Property's minimum range value";
       }
       leaf brp_maximum {
         type uint32;
         description "Property's maximum range value";
       }
       leaf brp_default {
         type uint32;
         description "Property's default value";
       }
     }
     container h248-segmentation-properties-entry {
       description "Array of h248 segmentation properties";
       leaf sgp_name {
         type string;
         description "Property's name";
       }
       leaf sgp_minimum {
         type uint32;
         description "Property's minimum range value";
       }
       leaf sgp_maximum {
         type uint32;
         description "Property's maximum range value";
       }
       leaf sgp_default {
         type uint32;
         description "Property's default value";
       }
     }
     container h248-diffserv-entry {
       leaf dscp {
         type string;
       }
     }
     container h248-notification-behavior-entry {
       leaf notification-regulation {
         type string;
         description "Notify regulation";
       }
     }
     container h248-application-data-inactivity-detection-entry {
       leaf ip-flow-stop-detection {
         type string;
         description "Notify behavior to media inactivity event";
       }
     }
     container h248-event-timestamp-notification-entry {
       leaf requested-timestamp {
         type string;
         description "Notification timestamp";
       }
     }
     container inactivity-timer-entry {
       leaf detect {
         type string;
         description "Detect inactivity timeout";
       }
       container maximum-inactivity-time {
         leaf minimum {
           type uint32;
           description "Minimum valid value of maximum inactivity timeout";
         }
         leaf maximum {
           type uint32;
           description "Maximum valid value of maximum inactivity timeout";
         }
         leaf default {
           type uint32;
           description "Default valid value of maximum inactivity timeout";
         }
       }
     }
     container fast-update-filters-entry {
       description "Firewall filters limitation";
       leaf max-terms {
         type uint64;
         description "Maximum number of filter terms";
       }
       leaf max-term-percentage {
         type uint32;
         description "Maximum percentage of gates with filter terms";
       }
     }
     container overload-control-entry {
       leaf queue-limit-percentage {
         type uint32;
       }
       leaf reject-new-calls-threshold {
         type uint32;
       }
       leaf reject-all-commands-threshold {
         type uint32;
       }
     }
     list gateway-entry {
       leaf gateway-name {
         type string;
       }
       leaf local-ip-address {
         type string;
       }
       leaf gateway-vrf {
         type string;
       }
       leaf local-port {
         type uint32;
       }
       leaf platform {
         type string;
       }
       leaf service-state {
         type string;
       }
       leaf active-controller {
         type string;
       }
       leaf replication-socket {
         type string;
       }
       leaf synchronization-state {
         type string;
       }
       leaf up-time {
         type string;
         description "Gateway uptime";
       }
       leaf load-status {
         type string;
         description "Gateway load status";
       }
       leaf cleanup-timeout {
         type uint32;
       }
       leaf maximum-concurrent-calls {
         type uint32;
         description "Maximum concurrent calls";
       }
       leaf inactivity-timeout-delay {
         type uint32;
       }
       leaf inactivity-timeout-duration {
         type uint32;
       }
       leaf latch-deadlock-duration {
         type uint32;
       }
       container h248-timers-entry {
         leaf maximum-waiting-delay {
           type uint32;
         }
         leaf tmax-retransmission-delay {
           type uint32;
         }
         leaf initial-average-ack-delay {
           type uint32;
         }
         leaf maximum-net-propagation-delay {
           type uint32;
         }
       }
       container base-root-entry {
         description "Array of h248 base root properties";
         leaf brp_name {
           type string;
           description "Property's name";
         }
         leaf brp_minimum {
           type uint32;
           description "Property's minimum range value";
         }
         leaf brp_maximum {
           type uint32;
           description "Property's maximum range value";
         }
         leaf brp_default {
           type uint32;
           description "Property's default value";
         }
       }
       container h248-options-entry {
         leaf wildcard-response-service-change {
           type string;
         }
         leaf audit-observed-events-returns-history {
           type string;
           description "Activation of event history";
         }
         leaf h248-profile {
           type string;
         }
       }
       container h248-segmentation-properties-entry {
         description "Array of h248 segmentation properties";
         leaf sgp_name {
           type string;
           description "Property's name";
         }
         leaf sgp_minimum {
           type uint32;
           description "Property's minimum range value";
         }
         leaf sgp_maximum {
           type uint32;
           description "Property's maximum range value";
         }
         leaf sgp_default {
           type uint32;
           description "Property's default value";
         }
       }
       container h248-diffserv-entry {
         leaf dscp {
           type string;
         }
       }
       container h248-notification-behavior-entry {
         leaf notification-regulation {
           type string;
           description "Notify regulation";
         }
       }
       container h248-application-data-inactivity-detection-entry {
         leaf ip-flow-stop-detection {
           type string;
           description "Notify behavior to media inactivity event";
         }
       }
       container h248-event-timestamp-notification-entry {
         leaf requested-timestamp {
           type string;
           description "Notification timestamp";
         }
       }
       container inactivity-timer-entry {
         leaf detect {
           type string;
           description "Detect inactivity timeout";
         }
         container maximum-inactivity-time {
           leaf minimum {
             type uint32;
             description "Minimum valid value of maximum inactivity timeout";
           }
           leaf maximum {
             type uint32;
             description "Maximum valid value of maximum inactivity timeout";
           }
           leaf default {
             type uint32;
             description "Default valid value of maximum inactivity timeout";
           }
         }
       }
       container fast-update-filters-entry {
         description "Firewall filters limitation";
         leaf max-terms {
           type uint64;
           description "Maximum number of filter terms";
         }
         leaf max-term-percentage {
           type uint32;
           description "Maximum percentage of gates with filter terms";
         }
       }
       list controller-entry {
         leaf controller-name {
           type string;
         }
         leaf remote-ip-address {
           type string;
         }
         leaf remote-port {
           type uint32;
         }
       }
       container overload-control-entry {
         leaf queue-limit-percentage {
           type uint32;
         }
         leaf reject-new-calls-threshold {
           type uint32;
         }
         leaf reject-all-commands-threshold {
           type uint32;
         }
       }
     }
     list rule-ref-entry {
       leaf rule-ref-name {
         type string;
       }
     }
     list rule-entry {
       leaf rule-name {
         type string;
         description "Rule name";
       }
       leaf rule-gateway-name {
         type string;
       }
     }
     container service-pic-entry {
       leaf pic-name {
         type string;
         description "Services PIC Name";
       }
       leaf pic-status {
         type string;
       }
       leaf pic-redundancy-state {
         type string;
       }
       leaf primary-pic {
         type string;
       }
       leaf secondary-pic {
         type string;
       }
       leaf pic-ha-state {
         type string;
       }
       leaf last-change {
         type string;
       }
     }
     list service-set-entry {
       leaf service-set-name {
         type string;
         description "Name of the service set";
       }
       leaf id {
         type uint32;
       }
     }
     container firewall-entry {
       leaf connection-status {
         type string;
       }
       leaf number-of-terms {
         type uint64;
       }
       leaf number-of-filters {
         type uint64;
       }
     }
     container pgcpd-config {
       list media-service-entry {
         leaf media-service-name {
           type string;
         }
         leaf media-service-nat-pool {
           type string;
         }
       }
       list virtual-interface-entry {
         leaf virtual-interface-name {
           type string;
         }
         leaf routing-instance {
           type string;
         }
         leaf interface-name {
           type string;
           description "Name of the adaptive services interface";
         }
         leaf vif-service-state {
           type string;
         }
         list media-service-ref-entry {
           leaf media-service-ref-name {
             type string;
           }
         }
       }
       list gateway-entry {
         leaf gateway-name {
           type string;
         }
         leaf local-ip-address {
           type string;
         }
         leaf gateway-vrf {
           type string;
         }
         leaf local-port {
           type uint32;
         }
         leaf platform {
           type string;
         }
         leaf service-state {
           type string;
         }
         leaf active-controller {
           type string;
         }
         leaf replication-socket {
           type string;
         }
         leaf synchronization-state {
           type string;
         }
         leaf up-time {
           type string;
           description "Gateway uptime";
         }
         leaf load-status {
           type string;
           description "Gateway load status";
         }
         leaf cleanup-timeout {
           type uint32;
         }
         leaf maximum-concurrent-calls {
           type uint32;
           description "Maximum concurrent calls";
         }
         leaf inactivity-timeout-delay {
           type uint32;
         }
         leaf inactivity-timeout-duration {
           type uint32;
         }
         leaf latch-deadlock-duration {
           type uint32;
         }
         container h248-timers-entry {
           leaf maximum-waiting-delay {
             type uint32;
           }
           leaf tmax-retransmission-delay {
             type uint32;
           }
           leaf initial-average-ack-delay {
             type uint32;
           }
           leaf maximum-net-propagation-delay {
             type uint32;
           }
         }
         container base-root-entry {
           description "Array of h248 base root properties";
           leaf brp_name {
             type string;
             description "Property's name";
           }
           leaf brp_minimum {
             type uint32;
             description "Property's minimum range value";
           }
           leaf brp_maximum {
             type uint32;
             description "Property's maximum range value";
           }
           leaf brp_default {
             type uint32;
             description "Property's default value";
           }
         }
         container h248-options-entry {
           leaf wildcard-response-service-change {
             type string;
           }
           leaf audit-observed-events-returns-history {
             type string;
             description "Activation of event history";
           }
           leaf h248-profile {
             type string;
           }
         }
         container h248-segmentation-properties-entry {
           description "Array of h248 segmentation properties";
           leaf sgp_name {
             type string;
             description "Property's name";
           }
           leaf sgp_minimum {
             type uint32;
             description "Property's minimum range value";
           }
           leaf sgp_maximum {
             type uint32;
             description "Property's maximum range value";
           }
           leaf sgp_default {
             type uint32;
             description "Property's default value";
           }
         }
         container h248-diffserv-entry {
           leaf dscp {
             type string;
           }
         }
         container h248-notification-behavior-entry {
           leaf notification-regulation {
             type string;
             description "Notify regulation";
           }
         }
         container h248-application-data-inactivity-detection-entry {
           leaf ip-flow-stop-detection {
             type string;
             description "Notify behavior to media inactivity event";
           }
         }
         container h248-event-timestamp-notification-entry {
           leaf requested-timestamp {
             type string;
             description "Notification timestamp";
           }
         }
         container inactivity-timer-entry {
           leaf detect {
             type string;
             description "Detect inactivity timeout";
           }
           container maximum-inactivity-time {
             leaf minimum {
               type uint32;
               description "Minimum valid value of maximum inactivity timeout";
             }
             leaf maximum {
               type uint32;
               description "Maximum valid value of maximum inactivity timeout";
             }
             leaf default {
               type uint32;
               description "Default valid value of maximum inactivity timeout";
             }
           }
         }
         container fast-update-filters-entry {
           description "Firewall filters limitation";
           leaf max-terms {
             type uint64;
             description "Maximum number of filter terms";
           }
           leaf max-term-percentage {
             type uint32;
             description "Maximum percentage of gates with filter terms";
           }
         }
         list controller-entry {
           leaf controller-name {
             type string;
           }
           leaf remote-ip-address {
             type string;
           }
           leaf remote-port {
             type uint32;
           }
         }
         container overload-control-entry {
           leaf queue-limit-percentage {
             type uint32;
           }
           leaf reject-new-calls-threshold {
             type uint32;
           }
           leaf reject-all-commands-threshold {
             type uint32;
           }
         }
       }
       list rule-entry {
         leaf rule-name {
           type string;
           description "Rule name";
         }
         leaf rule-gateway-name {
           type string;
         }
       }
       list service-set-entry {
         leaf service-set-name {
           type string;
           description "Name of the service set";
         }
         leaf id {
           type uint32;
         }
         list rule-ref-entry {
           leaf rule-ref-name {
             type string;
           }
         }
       }
       container service-pic-entry {
         leaf pic-name {
           type string;
           description "Services PIC Name";
         }
         leaf pic-status {
           type string;
         }
         leaf pic-redundancy-state {
           type string;
         }
         leaf primary-pic {
           type string;
         }
         leaf secondary-pic {
           type string;
         }
         leaf pic-ha-state {
           type string;
         }
         leaf last-change {
           type string;
         }
       }
       container firewall-entry {
         leaf connection-status {
           type string;
         }
         leaf number-of-terms {
           type uint64;
         }
         leaf number-of-filters {
           type uint64;
         }
       }
     }
   }
   grouping service-pgcp-statistics-gateway-block {
     leaf pgcp-statistics-since {
       type string;
       description "Since when statistics were collected";
     }
     list gateway-entry {
       leaf gateway-name {
         type string;
       }
       leaf local-ip-address {
         type string;
       }
       leaf gateway-vrf {
         type string;
       }
       leaf local-port {
         type uint32;
       }
       leaf platform {
         type string;
       }
       leaf service-state {
         type string;
       }
       leaf active-controller {
         type string;
       }
       leaf replication-socket {
         type string;
       }
       leaf synchronization-state {
         type string;
       }
       leaf up-time {
         type string;
         description "Gateway uptime";
       }
       leaf load-status {
         type string;
         description "Gateway load status";
       }
       leaf cleanup-timeout {
         type uint32;
       }
       leaf maximum-concurrent-calls {
         type uint32;
         description "Maximum concurrent calls";
       }
       leaf inactivity-timeout-delay {
         type uint32;
       }
       leaf inactivity-timeout-duration {
         type uint32;
       }
       leaf latch-deadlock-duration {
         type uint32;
       }
       container inactivity-timer-entry {
         container maximum-inactivity-time {
           leaf minimum {
             type uint32;
             description "Minimum valid value of maximum inactivity timeout";
           }
           leaf maximum {
             type uint32;
             description "Maximum valid value of maximum inactivity timeout";
           }
           leaf default {
             type uint32;
             description "Default valid value of maximum inactivity timeout";
           }
         }
       }
     }
     container service-pic-entry {
       leaf pic-name {
         type string;
         description "Services PIC Name";
       }
       leaf pic-status {
         type string;
       }
       leaf pic-redundancy-state {
         type string;
       }
       leaf primary-pic {
         type string;
       }
       leaf secondary-pic {
         type string;
       }
       leaf pic-ha-state {
         type string;
       }
       leaf last-change {
         type string;
       }
     }
     container services-pgcp-traffic-entry {
       leaf traffic-bytes-recv {
         type uint64;
         description "Number of bytes received";
       }
       leaf traffic-bytes-sent {
         type uint64;
         description "Number of bytes sent";
       }
       leaf traffic-packets-recv {
         type uint64;
         description "Number of packets received";
       }
       leaf traffic-packets-sent {
         type uint64;
         description "Number of packets sent";
       }
     }
     container services-pgcp-dropped-traffic-entry {
       leaf drop-packets-flow-drop-state {
         type uint64;
         description "Number of packets dropped as result of flow in state drop";
       }
       leaf drop-bytes-flow-drop-state {
         type uint64;
         description "Number of bytes dropped as result of flow in state drop";
       }
       leaf drop-packets-flow-rate-limit {
         type uint64;
         description "Number of packets dropped as result of rate limit";
       }
       leaf drop-bytes-flow-rate-limit {
         type uint64;
         description "Number of bytes dropped as result of rate limit";
       }
       leaf drop-packets-algs {
         type uint64;
         description "Number of packets dropped as result of ALG varification";
       }
       leaf drop-bytes-algs {
         type uint64;
         description "Number of bytes dropped as result of ALG varification";
       }
       leaf drop-packets-other {
         type uint64;
         description "Number of packets dropped as result of other reason";
       }
       leaf drop-bytes-other {
         type uint64;
         description "Number of bytes dropped as result of other reason";
       }
     }
     container usage-counters-entry {
       leaf contexts-number {
         type uint32;
         description "Number of contexts";
       }
       leaf emergency-contexts-number {
         type uint32;
         description "Number of emergency contexts";
       }
     }
     container service-pgcp-statistics-h248 {
       leaf messages-received {
         type uint32;
         description "Number of H.248 messages received";
       }
       leaf octets-received {
         type uint32;
         description "Number of H.248 octets received";
       }
       leaf messages-sent {
         type uint32;
         description "Number of H.248 messages sent";
       }
       leaf octets-sent {
         type uint32;
         description "Number of H.248 octest sent";
       }
       leaf protocol-errors {
         type uint32;
         description "Number of H.248 protocol erros";
       }
       leaf transport-losses {
         type uint32;
         description "Number of H.248 transport losses";
       }
       leaf last-detected-event {
         type string;
         description "Last detected H.248 event";
       }
       leaf last-detected-event-time {
         type uint32;
         description "Last detected H.248 event time";
       }
       leaf last-reset-time {
         type uint32;
         description "Last H.248 reset time";
       }
     }
     container service-pgcp-stat-h248-per-command-header {
       leaf per-command-header-name {
         type string;
         description "Statistics header";
       }
     }
     container service-pgcp-stat-h248-per-command {
       leaf command-name {
         type string;
         description "H.248 command requests";
       }
       leaf commands-total {
         type uint32;
         description "Total number of h.248 command requests";
       }
       leaf commands-wildcard {
         type uint32;
         description "The number of command request that had wildcard termination ID or termination list";
       }
       leaf commands-success {
         type uint32;
         description "Number of H.248 successful replies";
       }
       leaf commands-error {
         type uint32;
         description "Number of H.248 failed replies";
       }
     }
   }
   grouping service-pgcp-terminations-block {
     list gateway-entry {
       leaf gateway-name {
         type string;
       }
       leaf local-ip-address {
         type string;
       }
       leaf gateway-vrf {
         type string;
       }
       leaf local-port {
         type uint32;
       }
       leaf platform {
         type string;
       }
       leaf service-state {
         type string;
       }
       leaf active-controller {
         type string;
       }
       leaf replication-socket {
         type string;
       }
       leaf synchronization-state {
         type string;
       }
       leaf up-time {
         type string;
         description "Gateway uptime";
       }
       leaf load-status {
         type string;
         description "Gateway load status";
       }
       leaf cleanup-timeout {
         type uint32;
       }
       leaf maximum-concurrent-calls {
         type uint32;
         description "Maximum concurrent calls";
       }
       leaf inactivity-timeout-delay {
         type uint32;
       }
       leaf inactivity-timeout-duration {
         type uint32;
       }
       leaf latch-deadlock-duration {
         type uint32;
       }
       container inactivity-timer-entry {
         container maximum-inactivity-time {
           leaf minimum {
             type uint32;
             description "Minimum valid value of maximum inactivity timeout";
           }
           leaf maximum {
             type uint32;
             description "Maximum valid value of maximum inactivity timeout";
           }
           leaf default {
             type uint32;
             description "Default valid value of maximum inactivity timeout";
           }
         }
       }
       leaf termination-count {
         type uint32;
         description "Number of terminations in the gateway";
       }
     }
     list service-pgcp-termination-entry-information {
       leaf termination-id-string {
         type string;
         description "Termination id as string";
       }
       leaf termination-state {
         type string;
         description "Termination state (in/out of service)";
       }
       leaf termination-duration {
         type uint32;
         description "Termination duration (in milliseconds)";
       }
       leaf termination-h248-dump {
         type string;
         description "Termination information";
       }
     }
     list service-pgcp-termination-gates-information {
       leaf gate-id {
         type uint64;
         description "Gate id";
       }
       leaf gate-direction {
         type string;
         description "Gate direction (A->B/B->A)";
       }
       leaf gate-state {
         type string;
         description "Gate state (active/disabled)";
       }
       leaf gate-action {
         type string;
         description "Gate action (forward/drop)";
       }
     }
     container service-pgcp-terminations-count {
       leaf gateway-name {
         type string;
       }
       leaf termination-count {
         type uint32;
         description "Number of terminations in the gateway";
       }
     }
   }
   grouping service-pgcp-gates-block {
     list gateway-entry {
       leaf gateway-name {
         type string;
       }
       leaf local-ip-address {
         type string;
       }
       leaf gateway-vrf {
         type string;
       }
       leaf local-port {
         type uint32;
       }
       leaf platform {
         type string;
       }
       leaf service-state {
         type string;
       }
       leaf active-controller {
         type string;
       }
       leaf replication-socket {
         type string;
       }
       leaf synchronization-state {
         type string;
       }
       leaf up-time {
         type string;
         description "Gateway uptime";
       }
       leaf load-status {
         type string;
         description "Gateway load status";
       }
       leaf cleanup-timeout {
         type uint32;
       }
       leaf maximum-concurrent-calls {
         type uint32;
         description "Maximum concurrent calls";
       }
       leaf inactivity-timeout-delay {
         type uint32;
       }
       leaf inactivity-timeout-duration {
         type uint32;
       }
       leaf latch-deadlock-duration {
         type uint32;
       }
       container inactivity-timer-entry {
         container maximum-inactivity-time {
           leaf minimum {
             type uint32;
             description "Minimum valid value of maximum inactivity timeout";
           }
           leaf maximum {
             type uint32;
             description "Maximum valid value of maximum inactivity timeout";
           }
           leaf default {
             type uint32;
             description "Default valid value of maximum inactivity timeout";
           }
         }
       }
       leaf gate-count {
         type uint32;
         description "Number of gates in the gateway";
       }
     }
     container service-pgcp-gate-entry-information {
       leaf gate-id {
         type uint64;
         description "Gate id";
       }
       leaf gate-state {
         type string;
         description "Gate state (active/disabled)";
       }
       leaf gate-action {
         type string;
         description "Gate action (forward/drop)";
       }
       leaf gate-service-set-id {
         type uint32;
         description "Service set id";
       }
       leaf media-card-name {
         type string;
         description "Media card name";
       }
       leaf media-handler-name {
         type string;
         description "Media handler name";
       }
       leaf termination-id-string {
         type string;
         description "Termination id as string";
       }
       container gate-rtcp-information {
         list gate-rtcp-receiver-information {
           container gate-rtcp-receiver-entry {
             leaf gate-rtcp-received-ssrc {
               type uint32;
               description "RTP Synchronization source";
             }
             leaf gate-rtcp-receiver-lost-pkts {
               type uint32;
               description "Number of packets lost";
             }
             leaf gate-rtcp-receiver-lost-pkt-fraction {
               type string;
               description "Fraction of packets lost";
             }
             leaf gate-rtcp-receiver-jitter {
               type uint32;
               description "Jitter for received packets";
             }
           }
         }
         container gate-rtcp-extended-information {
           container gate-rtcp-extended-report {
             leaf rtcp-xr-ssrc {
               type uint32;
               description "RTCP XR Synchronization source";
             }
             leaf packet-loss-concealment-type {
               type string;
               description "The type of packet loss concealment algorithm in use";
             }
             leaf network-packet-loss-rate {
               type uint32;
               description "The proportion of packets lost since the start of transmission";
             }
             leaf jitter-buffer-discard-rate {
               type uint32;
               description "The proportion of packets discarded by the receiving jitter buffer";
             }
             leaf rtcp-round-trip-delay {
               type uint32;
               description "The round-trip delay between the RTP endpoints";
             }
             leaf end-system-delay {
               type uint32;
               description "End system delay";
             }
             leaf signal-level {
               type uint32;
               description "The ratio of the signal level to a 0 dBm0 reference";
             }
             leaf noise-level {
               type uint32;
               description "The ratio of the silent period background noise level";
             }
             leaf residual-echo-return-loss {
               type uint32;
               description "The echo return loss after the effects of echo cancellation";
             }
             leaf r-factor {
               type uint32;
               description "A value representing the receiving end call quality of the RTP stream";
             }
             leaf external-r-factor {
               type uint32;
               description "External r factor";
             }
             leaf estimated-moslq {
               type uint32;
               description "An estimated receiving end Listening Quality MOS";
             }
             leaf estimated-moscq {
               type uint32;
               description "An estimated receiving end Conversational Quality MOS";
             }
           }
           container gate-rtcp-extended-burst-metrics-report {
             leaf minimum-gap-threshold {
               type uint32;
               description "A parameter used to define bursts";
             }
             leaf burst-loss-density {
               type uint32;
               description "The average proportion of packets both lost and discarded during burst periods";
             }
             leaf burst-duration {
               type uint32;
               description "The average length of burst periods";
             }
             leaf gap-loss-density {
               type uint32;
               description "The average proportion of packets lost and discarded during gap periods";
             }
             leaf gap-duration {
               type uint32;
               description "The average length of gap periods";
             }
           }
         }
         container gate-rtcp-sender-information {
           leaf gate-rtcp-sender-ssrc {
             type uint32;
             description "RTP Synchronization source";
           }
           leaf gate-rtcp-sender-octets {
             type uint32;
             description "Number of bytes sent";
           }
           leaf gate-rtcp-sender-pkts {
             type uint32;
             description "Number of packets sent";
           }
           leaf gate-rtcp-invalid-pkts {
             type uint32;
             description "Invalid RTCP packets";
           }
         }
       }
       list service-rate-limit-information {
         container service-rate-limit-entry {
           leaf service-rate-limit-mark-color {
             type string;
             description "Mark color";
           }
           leaf service-rate-limit-packet-count {
             type uint32;
             description "Number of packets marked";
           }
           leaf service-rate-limit-byte-count {
             type uint32;
             description "Number of bytes marked";
           }
         }
       }
       leaf gate-direction {
         type string;
         description "Gate direction (A->B/B->A)";
       }
       leaf source-routing-instance {
         type string;
         description "Source routing-instance";
       }
       leaf destination-routing-instance {
         type string;
         description "Destination routing-instance";
       }
       leaf gate-remote-source-address {
         type string;
         description "Gate remote source address";
       }
       leaf gate-remote-source-port {
         type string;
         description "Gate remote source port";
       }
       leaf gate-remote-destination-address {
         type string;
         description "Gate remote destination address";
       }
       leaf gate-remote-destination-port {
         type string;
         description "Gate remote destination port";
       }
       leaf gate-local-source-address {
         type string;
         description "Gate local source address";
       }
       leaf gate-local-source-port {
         type string;
         description "Gate local source port";
       }
       leaf gate-local-destination-address {
         type string;
         description "Gate local destination address";
       }
       leaf gate-local-destination-port {
         type string;
         description "Gate local destination port";
       }
       leaf gate-transport {
         type string;
         description "Gate transport protocols";
       }
       leaf gate-rtcp-shadow {
         type string;
         description "Is there a shadowed RTCP gate associated";
       }
       leaf gate-latch {
         type string;
         description "Install/uninstall a latch for this gate";
       }
       leaf gate-dscp {
         type string;
         description "DSCP for outgoing packets on this gate";
       }
       leaf gate-tman-policing {
         type string;
         description "Install/uninstall a traffic management policing for this gate";
       }
       leaf gate-sdr {
         type uint32;
         description "Sustainable data rate threshold for a gate";
       }
       leaf gate-pdr {
         type uint32;
         description "Peak data rate threshold for a gate";
       }
       leaf gate-mbs {
         type uint32;
         description "Maximum pdr burst size limit for a gate";
       }
       leaf rtcp-sdr {
         type uint32;
         description "SDR Sustainable data rate threshold of the RTCP stream";
       }
       leaf rtcp-pdr {
         type uint32;
         description "Peak data rate threshold of the RTCP stream";
       }
       leaf rtcp-mbs {
         type uint32;
         description "Maximum burst size limit of the RTCP stream";
       }
       leaf gate-fuf-policing {
         type string;
         description "Install/uninstall a fuf policer for this gate";
       }
       leaf gate-green-action {
         type string;
         description "Action to be application over green packets";
       }
       leaf gate-yellow-action {
         type string;
         description "Action to be application over yellow packets";
       }
       leaf gate-red-action {
         type string;
         description "Action to be application over red packets";
       }
       leaf gate-output-packets {
         type uint64;
         description "Packet-sent by gate statistics";
       }
       leaf gate-input-packets {
         type uint64;
         description "Packet-received by gate statistics";
       }
       leaf gate-dropped-packets {
         type uint64;
         description "Packet-dropped by gate statistics";
       }
       leaf gate-lost-rtp-packets {
         type uint64;
         description "Number of lost RTP packets lost";
       }
       leaf gate-fractional-lost-rtp-packets {
         type uint64;
         description "Calculated fractional lost RTP packets";
       }
       leaf gate-measured-rate {
         type uint32;
         description "Measured rate of traffic for gate in bytes/second";
       }
       container gate-fuf-statistics-information {
         leaf gate-fuf-policer-drop-count {
           type uint64;
           description "Number of dropped policer packets";
         }
       }
       container gate-srtp-stats-information {
         leaf gate-srtp-encrypt-packets {
           type uint32;
           description "Number of packets encrypted";
         }
         leaf gate-srtp-encrypt-octets {
           type uint32;
           description "Number of octets encrypted";
         }
         leaf gate-srtp-decrypt-packets {
           type uint32;
           description "Number of packets decrypted";
         }
         leaf gate-srtp-decrypt-octets {
           type uint32;
           description "Numbers of octets decrypted";
         }
         leaf gate-srtp-auth-fail-packets {
           type uint32;
           description "Number of packets dropped because of authentication failure";
         }
         leaf gate-srtp-auth-fail-octets {
           type uint32;
           description "Number of octets dropped because of authentication failure";
         }
         leaf gate-srtp-bad-packet-packets {
           type uint32;
           description "Number of packets dropped due to mal-formed packets";
         }
         leaf gate-srtp-replayed-packets {
           type uint32;
           description "Number of packets dropped because of replay check failure";
         }
         leaf gate-srtp-ctx-lookup-fail-packets {
           type uint32;
           description "Number of packets dropped because of context lookup failure";
         }
         leaf gate-srtp-pkt-setup-fail-packets {
           type uint32;
           description "Number of packets dropped because of packet setup failure";
         }
       }
       container gate-srtcp-stats-information {
         leaf gate-srtcp-encrypt-packets {
           type uint32;
           description "Number of packets encrypted";
         }
         leaf gate-srtcp-encrypt-octets {
           type uint32;
           description "Number of octets encrypted";
         }
         leaf gate-srtcp-decrypt-packets {
           type uint32;
           description "Number of packets decrypted";
         }
         leaf gate-srtcp-decrypt-octets {
           type uint32;
           description "Numbers of octets decrypted";
         }
         leaf gate-srtcp-auth-fail-packets {
           type uint32;
           description "Number of packets dropped because of authentication failure";
         }
         leaf gate-srtcp-auth-fail-octets {
           type uint32;
           description "Number of octets dropped because of authentication failure";
         }
         leaf gate-srtcp-bad-packet-packets {
           type uint32;
           description "Number of packets dropped due to mal-formed packets";
         }
         leaf gate-srtcp-replayed-packets {
           type uint32;
           description "Number of packets dropped because of replay check failure";
         }
         leaf gate-srtcp-ctx-lookup-fail-packets {
           type uint32;
           description "Number of packets dropped because of context lookup failure";
         }
         leaf gate-srtcp-pkt-setup-fail-packets {
           type uint32;
           description "Number of packets dropped because of packet setup failure";
         }
       }
       leaf gate-mirroring-state {
         type string;
         description "Whether session mirroring is active for this gate";
       }
       leaf gate-mirroring-correlation-number {
         type string;
         description "Session mirroring correlation number";
       }
       leaf gate-mirroring-target-id {
         type string;
         description "List of session mirroring destinations";
       }
       leaf gate-mirroring-direction {
         type string;
         description "Whether session mirroring is done before or after NAT";
       }
     }
     container service-pgcp-gates-count {
       leaf gateway-name {
         type string;
       }
       leaf gate-count {
         type uint32;
         description "Number of gates in the gateway";
       }
     }
   }
   grouping services-pgcpd-root-termination-block {
     leaf root-termination-information {
       type string;
       description "H248 root termination information";
     }
   }
   grouping bsg-statistics-calls-details-block {
     container bsg-statistics-calls {
       leaf bsg-start-time {
         type string;
       }
       list bsg-service-point-calls-details {
         leaf bsg-sp-name {
           type string;
           description "The service point name";
         }
         leaf service-interface {
           type string;
           description "The service interface hexadecimal representation";
         }
         leaf bsg-server-name {
           type string;
           description "The server name";
         }
         leaf bsg-sp-direction {
           type string;
           description "The service point direction";
         }
         leaf bsg-sp-failed-calls {
           type uint32;
           description "Counts all the failed calls";
         }
         leaf bsg-sp-completed-calls {
           type uint32;
           description "Counts all the completed calls";
         }
         leaf bsg-sp-active-calls {
           type uint32;
           description "Counts all the active calls";
         }
       }
     }
   }
   grouping bsg-statistics-calls-failed-details-block {
     container bsg-statistics-calls-failed {
       leaf bsg-start-time {
         type string;
       }
       list bsg-service-point-calls-failed-details {
         leaf bsg-sp-name {
           type string;
           description "The service point name";
         }
         leaf service-interface {
           type string;
           description "The service interface hexadecimal representation";
         }
         leaf bsg-server-name {
           type string;
           description "The server name";
         }
         leaf bsg-sp-direction {
           type string;
           description "The service point direction";
         }
         leaf bsg-sp-error-response-code {
           type uint32;
           description "Error response codes received during call setup that terminated the call";
         }
         leaf bsg-sp-internal-error {
           type uint32;
           description "BSG Internal errors during the call setup that terminated the call";
         }
         leaf bsg-sp-inactive-timeout {
           type uint32;
           description "Inactive timeout timer has expired and caused active call termination";
         }
         leaf bsg-sp-setup-media-failure {
           type uint32;
           description "Some media failure during call setup terminated the call";
         }
         leaf bsg-sp-established-call-media-inactivity {
           type uint32;
           description "A media inactivity was detected, causing the call to terminate";
         }
         leaf bsg-sp-cac-policy-rejection {
           type uint32;
           description "The call was terminated during setup due to CAC restrictions";
         }
         leaf bsg-sp-default-behavior-policy-rejection {
           type uint32;
           description "No matching accepting policy was match on the incoming call";
         }
         leaf bsg-sp-configured-behavior-policy-rejection {
           type uint32;
           description "The call was actively rejected by the policy";
         }
         leaf bsg-sp-transport-conflict-policy-rejection {
           type uint32;
           description "No matching egress service point was found";
         }
         leaf bsg-sp-protocol-error {
           type uint32;
           description "Some protocol error during call setup terminated the call";
         }
         leaf bsg-sp-setup-timeout {
           type uint32;
           description "Some timeout during call setup terminated the call";
         }
         leaf bsg-sp-transport-error {
           type uint32;
           description "Some transport error during call setup terminated the call";
         }
         leaf bsg-sp-canceled-calls {
           type uint32;
           description "Call was canceled";
         }
         leaf bsg-sp-media-abort {
           type uint32;
           description "A session abort notification received, causing the call to terminate";
         }
       }
     }
   }
   grouping bsg-statistics-denied-messages-details-block {
     container bsg-statistics-denied-messages {
       leaf overload-last-reset-time {
         type string;
         description "Last overload reset time";
       }
       list bsg-denied-messages-details {
         leaf bsg-denied-message {
           type string;
           description "Displays the time a message was denied";
         }
       }
     }
   }
   grouping bsg-status-information-block {
     leaf bsg-redundancy-state {
       type string;
       description "Shows bsg redundancy state";
     }
     list bsg-redundancy-pic-info {
       description "Shows PIC information";
       leaf bsg-redundancy-local-or-remote {
         type string;
         description "Local or remote pic";
       }
       leaf bsg-redundancy-pic-if-name {
         type string;
         description "Shows PIC interface name";
       }
       leaf bsg-redundancy-pic-ip {
         type string;
         description "Shows PIC IP address";
       }
       leaf bsg-redundancy-pic-rms-role {
         type string;
         description "Shows PIC RMS role";
       }
     }
     list bsg-redundancy-connection-info {
       description "Shows the connection information";
       leaf bsg-redundancy-conn-type {
         type string;
         description "Shows the connection type";
       }
       leaf bsg-redundancy-conn-status {
         type string;
         description "Shows the connection status";
       }
       leaf bsg-redundancy-conn-details {
         type string;
         description "Shows the connection details";
       }
       leaf bsg-redundancy-conn-messages {
         type string;
         description "Shows the number of Rx/Tx messages";
       }
     }
   }
   grouping bsg-name-resolution-cache-information-block {
     container bsg-nr-cache {
       list bsg-name-resolution-entry {
         leaf bsg-nr-entry-fqdn {
           type string;
           description "Domain name";
         }
         leaf bsg-nr-entry-type {
           type string;
           description "Record type";
         }
         leaf bsg-nr-entry-rdata {
           type string;
           description "Raw data";
         }
         leaf bsg-nr-entry-ttl-expiry {
           type uint32;
           description "Seconds to TTL expiry";
         }
         leaf bsg-nr-entry-blacklist-expiry {
           type uint32;
           description "Seconds to TTL expiry";
         }
       }
     }
   }
   grouping bsg-registrations-block {
     leaf bsg-registrations-start-time {
       type string;
       description "Statistics start time";
     }
     leaf bsg-registrations-active-registrations {
       type string;
       description "Number of active registrations";
     }
   }
   grouping bsg-registrations-realm-block {
     leaf bsg-registrations-realm-start-time {
       type string;
       description "Statistics start time";
     }
     leaf bsg-registrations-realm-name {
       type string;
       description "Name of realm";
     }
     leaf bsg-registrations-realm-active-registrations {
       type string;
       description "Number of active registrations";
     }
   }
   grouping bsg-address-of-records-block {
     list bsg-address-of-record {
       description "Address of record";
       leaf bsg-aor-name {
         type string;
         description "The address-of-record";
       }
       leaf bsg-aor-bindings-num-of-lu {
         type string;
         description "Number of binded contacts";
       }
       list bsg-address-of-record-bindings {
         description "Binding URI's";
         list bsg-address-of-record-binding {
           description "Binding URI's";
           leaf bsg-aor-bindings-uri {
             type string;
             description "The URI";
           }
           leaf bsg-aor-bindings-reg-realm {
             type string;
             description "The realm where the user registered from";
           }
           leaf bsg-aor-bindings-service-point {
             type string;
             description "The service-point where the user registered from";
           }
           leaf bsg-aor-bindings-first-reg-time {
             type string;
             description "The first registration time";
           }
           leaf bsg-aor-bindings-last-reg-time {
             type string;
             description "The last registration time";
           }
           leaf bsg-aor-bindings-expiration-time {
             type string;
             description "The expiration time";
           }
           leaf bsg-aor-bindings-lu {
             type string;
             description "The translated URI";
           }
           leaf bsg-aor-bindings-fe-nat-used {
             type string;
             description "Whether FE-NAT traversal logic is applied to this UE";
           }
           leaf bsg-aor-bindings-fe-nat-method {
             type string;
             description "Far End NAT traversal method";
           }
           leaf bsg-aor-bindings-fe-nat-ka-interval {
             type uint32;
             description "Far End NAT traversal keepalive interval";
           }
         }
       }
     }
   }
   grouping bsg-charging-status-block {
     leaf bsg-charging-name {
       type string;
       description "Charging Trigger Function - name";
     }
     leaf bsg-charging-release-number {
       type string;
       description "Charging Trigger Function - 3GPP release number";
     }
     leaf bsg-charging-operational-mode {
       type string;
       description "Charging Trigger Function - operational mode (session or event)";
     }
     list bsg-charging-status-cdf {
       description "Charging Trigger Function - CDF servers list";
       leaf bsg-charging-cdf-name {
         type string;
         description "Charging Data Function Server - name";
       }
       leaf bsg-charging-cdf-realm {
         type string;
         description "Charging Data Function Server - server's realm";
       }
       leaf bsg-charging-cdf-host {
         type string;
         description "Charging Data Function Server - server's host name";
       }
       leaf bsg-charging-cdf-priority {
         type uint32;
         description "Charging Data Function Server - server's priority";
       }
     }
   }
   grouping bsg-charging-statistics-block {
     leaf number-of-ctf-messages {
       type uint32;
       description "Number of charging-trigger messages";
     }
     leaf number-of-ctf-retries-messages {
       type uint32;
       description "Number of charging-trigger retries messages";
     }
     leaf number-of-ctf-replied-messages {
       type uint32;
       description "Number of charging-trigger replied messages";
     }
     leaf number-of-ctf-error-replied-messages {
       type uint32;
       description "Number of charging-trigger error reply messages";
     }
   }
   grouping service-sfw-flow-table-information-block {
     list sfw-per-service-set-flow-table {
       description "Flows sorted by service set";
       leaf interface-name {
         type string;
         description "Name of the adaptive services interface";
       }
       leaf service-set-name {
         type string;
         description "Name of the service set";
       }
       list service-sfw-flow-table {
         description "Stateful firewall flows";
         leaf-list service-sfw-flow-table.heading {
           type string;
           description "Stateful firewall flows";
         }
         list sfw-flow-entry {
           description "Flow brief information";
           leaf sfw-flow-protocol {
             type string;
             description "Flow protocol description";
           }
           leaf sfw-flow-source-ip {
             type string;
             description "Source IP address";
           }
           leaf sfw-flow-source-port {
             type int32;
             description "Source port address";
           }
           leaf sfw-flow-destination-ip {
             type string;
             description "Flow destination IP address";
           }
           leaf sfw-flow-destination-port {
             type string;
             description "Flow destination port";
           }
           leaf sfw-flow-state {
             type string;
             description "Flow state";
           }
           leaf sfw-flow-direction {
             type string;
             description "Flow direction";
           }
           leaf sfw-flow-frame-counter {
             type uint64;
             description "Number of frames transmitted";
           }
           leaf sfw-flow-gate-id {
             type uint64;
             description "PGCP gate-id";
           }
           leaf sfw-flow-table-byte-count {
             type uint64;
             description "Flow byte count";
           }
           leaf sfw-flow-table-tcp-window-size {
             type uint64;
             description "TCP protocol window size";
           }
           leaf sfw-flow-table-tcp-acknowledge {
             type uint64;
             description "TCP protocol acknowledge";
           }
           leaf sfw-flow-table-tcp-tickle {
             type uint64;
             description "Time between TCP tickles (seconds)";
           }
           leaf sfw-flow-table-role {
             type string;
             description "Role of flow in conversation";
           }
           leaf sfw-flow-table-timeout {
             type uint64;
             description "Timeout value of flow (seconds)";
           }
           leaf sfw-flow-table-protocol-detail {
             type string;
             description "Flow protocol detail information";
           }
           container sfw-flow-nat {
             description "NAT translation";
             leaf sfw-flow-nat-type {
               type string;
               description "Type of NAT translation";
             }
             leaf sfw-flow-nat-ip {
               type string;
               description "Original IP address";
             }
             leaf sfw-flow-nat-port {
               type string;
               description "Original port";
             }
             leaf sfw-flow-translated-ip {
               type string;
               description "Translated IP address";
             }
             leaf sfw-flow-translated-port {
               type string;
               description "Translated port";
             }
           }
         }
       }
     }
   }
   grouping service-msp-sess-count-information-block {
     list service-msp-sess-count {
       description "Stateful firewall sessions count";
       leaf interface-name {
         type string;
         description "Name of the adaptive services interface";
       }
       leaf service-set-name {
         type string;
         description "Name of the service set";
       }
       leaf sess-count {
         type uint32;
         description "Number of sessions in the service set";
       }
     }
   }
   grouping usf-service-softwire-table-information-block {
     list usf-softwire-per-service-set-flow-table {
       description "Flows sorted by service set";
       leaf interface-name {
         type string;
         description "Interface name";
       }
       leaf service-set-name {
         type string;
         description "Name of the service set";
       }
       list usf-service-softwire-table {
         description "Softwire flows";
         leaf-list usf-service-softwire-table.heading {
           type string;
           description "Softwire flows";
         }
         list usf-softwire-entry {
           description "Flow brief information";
           leaf usf-softwire-source-ip {
             type string;
             description "Softwire source IP address";
           }
           leaf usf-softwire-destination-ip {
             type string;
             description "Softwire destination IP address";
           }
           leaf usf-softwire-direction {
             type string;
             description "Softwire direction";
           }
           leaf usf-softwire-flow-count {
             type string;
             description "Number of flows in softwire";
           }
           leaf usf-softwire-table-timeout {
             type uint64;
             description "Timeout value of flow (seconds)";
           }
         }
       }
     }
   }
   grouping services-sessions-utilization-information-block {
     list services-sessions-utilization {
       description "Sessions utilization statistics";
       leaf interface-name {
         type string;
         description "Name of the adaptive services interface";
       }
       leaf session-count {
         type uint32;
         description "Session count";
       }
       leaf memory-percent {
         type uint32;
         description "Memory usage (percent)";
       }
       leaf session-setup-rate {
         type uint32;
         description "Session setup rate";
       }
       leaf session-setup-percent {
         type uint32;
         description "Setup load (percent)";
       }
       leaf session-drop-rate {
         type uint32;
         description "Session drop rate";
       }
       leaf session-teardown-rate {
         type uint32;
         description "Session teardown rate";
       }
       leaf cpu-load {
         type string;
         description "CPU load";
       }
     }
   }
   grouping service-msp-alg-conversation-information-block {
     leaf interface-name {
       type string;
       description "Name of the adaptive services interface";
     }
     container msp-alg-conv-all-entry {
       description "ALG conversations";
       leaf client-name {
         type string;
       }
       leaf client-state {
         type string;
       }
       leaf num-groups {
         type uint32;
       }
       leaf-list parent-sess-state {
         type string;
       }
       leaf-list parent-sess-id {
         type uint64;
       }
       leaf-list parent-flow-protocol {
         type string;
       }
       leaf-list parent-fflow-src-ip {
         type string;
       }
       leaf-list parent-fflow-src-port {
         type uint32;
       }
       leaf-list parent-fflow-dst-ip {
         type string;
       }
       leaf-list parent-fflow-dst-port {
         type uint32;
       }
       leaf-list parent-rflow-src-ip {
         type string;
       }
       leaf-list parent-rflow-src-port {
         type uint32;
       }
       leaf-list parent-rflow-dst-ip {
         type string;
       }
       leaf-list parent-rflow-dst-port {
         type uint32;
       }
       leaf-list child-sess-id {
         type uint64;
       }
       leaf-list child-flow-protocol {
         type string;
       }
       leaf-list child-fflow-src-ip {
         type string;
       }
       leaf-list child-fflow-src-port {
         type uint32;
       }
       leaf-list child-fflow-dst-ip {
         type string;
       }
       leaf-list child-fflow-dst-port {
         type uint32;
       }
       leaf-list child-rflow-src-ip {
         type string;
       }
       leaf-list child-rflow-src-port {
         type uint32;
       }
       leaf-list child-rflow-dst-ip {
         type string;
       }
       leaf-list child-rflow-dst-port {
         type uint32;
       }
       leaf-list group-id {
         type uint32;
       }
       leaf-list group-state {
         type string;
       }
       leaf-list num-resources {
         type uint32;
       }
       leaf-list resource-id {
         type uint32;
       }
       leaf-list resource-state {
         type string;
       }
       leaf-list num-sessions {
         type uint32;
       }
       leaf group-is-active {
         type string;
       }
       leaf parent-session-id {
         type uint64;
       }
       leaf group-timeout {
         type uint32;
       }
       leaf-list resource {
         type uint32;
       }
     }
     container msp-alg-conv-all-extensive-entry {
       description "ALG conversations extensive";
       leaf client-name {
         type string;
       }
       leaf client-state {
         type string;
       }
       leaf num-groups {
         type uint32;
       }
       leaf-list group-id {
         type uint32;
       }
       leaf-list group-state {
         type string;
       }
       leaf-list parent-sess-state {
         type string;
       }
       leaf-list parent-sess-id {
         type uint64;
       }
       leaf-list parent-flow-protocol {
         type string;
       }
       leaf-list parent-fflow-src-ip {
         type string;
       }
       leaf-list parent-fflow-src-port {
         type uint32;
       }
       leaf-list parent-fflow-dst-ip {
         type string;
       }
       leaf-list parent-fflow-dst-port {
         type uint32;
       }
       leaf-list parent-rflow-src-ip {
         type string;
       }
       leaf-list parent-rflow-src-port {
         type uint32;
       }
       leaf-list parent-rflow-dst-ip {
         type string;
       }
       leaf-list parent-rflow-dst-port {
         type uint32;
       }
       leaf-list num-resources {
         type uint32;
       }
       leaf-list resource-id {
         type uint32;
       }
       leaf-list resource-state {
         type string;
       }
       leaf-list num-sessions {
         type uint32;
       }
       leaf-list child-sess-id {
         type uint64;
       }
       leaf-list child-flow-protocol {
         type string;
       }
       leaf-list child-fflow-src-ip {
         type string;
       }
       leaf-list child-fflow-src-port {
         type uint32;
       }
       leaf-list child-fflow-dst-ip {
         type string;
       }
       leaf-list child-fflow-dst-port {
         type uint32;
       }
       leaf-list child-rflow-src-ip {
         type string;
       }
       leaf-list child-rflow-src-port {
         type uint32;
       }
       leaf-list child-rflow-dst-ip {
         type string;
       }
       leaf-list child-rflow-dst-port {
         type uint32;
       }
       leaf group-is-active {
         type string;
       }
       leaf parent-session-id {
         type uint64;
       }
       leaf group-timeout {
         type uint32;
       }
       leaf-list resource {
         type uint32;
       }
     }
     container msp-alg-conv-summary-entry {
       description "ALG conversation summary";
       leaf clients-active {
         type uint32;
       }
       leaf groups-active {
         type uint32;
       }
       leaf resources-active {
         type uint32;
       }
       leaf sessions-active {
         type uint32;
       }
     }
     container msp-alg-conv-groups-entry {
       description "ALG groups";
       leaf-list group-id {
         type uint32;
       }
       leaf group-is-active {
         type string;
       }
       leaf client-name {
         type string;
       }
       leaf-list num-resources {
         type uint32;
       }
       leaf-list resource-id {
         type uint32;
       }
       leaf parent-session-id {
         type uint64;
       }
       leaf group-timeout {
         type uint32;
       }
       leaf-list resource {
         type uint32;
       }
     }
     container msp-alg-conv-group-num-entry {
       description "ALG group information";
       leaf-list group-id {
         type uint32;
       }
       leaf group-is-active {
         type string;
       }
       leaf client-name {
         type string;
       }
       leaf parent-session-id {
         type uint64;
       }
       leaf group-timeout {
         type uint32;
       }
       leaf-list num-resources {
         type uint32;
       }
       leaf-list resource {
         type uint32;
       }
     }
     container msp-alg-conv-resources-entry {
       description "ALG resources";
       leaf-list resource-id {
         type uint32;
       }
       leaf resource-is-active {
         type string;
       }
       leaf-list group-id {
         type uint32;
       }
       leaf client-name {
         type string;
       }
       leaf-list num-sessions {
         type uint32;
       }
       leaf-list session-id {
         type uint64;
       }
       leaf-list session-ids {
         type uint64;
       }
       leaf num-holes {
         type uint32;
       }
       leaf src-ip-low {
         type string;
       }
       leaf src-ip-high {
         type string;
       }
       leaf src-port-low {
         type uint32;
       }
       leaf src-port-high {
         type uint32;
       }
       leaf dst-ip-low {
         type string;
       }
       leaf dst-ip-high {
         type string;
       }
       leaf dst-port-low {
         type uint32;
       }
       leaf dst-port-high {
         type uint32;
       }
       leaf translated-src-ip {
         type string;
       }
       leaf translated-src-port {
         type uint32;
       }
       leaf translated-dst-ip {
         type string;
       }
       leaf translated-dst-port {
         type uint32;
       }
       leaf proto {
         type uint32;
       }
       leaf ref-count {
         type uint32;
       }
     }
     container msp-alg-conv-resource-num-entry {
       description "ALG resource information";
       leaf-list resource-id {
         type uint32;
       }
       leaf resource-is-active {
         type string;
       }
       leaf-list num-sessions {
         type uint32;
       }
       leaf-list session-ids {
         type uint64;
       }
       leaf num-holes {
         type uint32;
       }
       leaf src-ip-low {
         type string;
       }
       leaf src-ip-high {
         type string;
       }
       leaf src-port-low {
         type uint32;
       }
       leaf src-port-high {
         type uint32;
       }
       leaf dst-ip-low {
         type string;
       }
       leaf dst-ip-high {
         type string;
       }
       leaf dst-port-low {
         type uint32;
       }
       leaf dst-port-high {
         type uint32;
       }
       leaf translated-src-ip {
         type string;
       }
       leaf translated-src-port {
         type uint32;
       }
       leaf translated-dst-ip {
         type string;
       }
       leaf translated-dst-port {
         type uint32;
       }
       leaf proto {
         type uint32;
       }
       leaf ref-count {
         type uint32;
       }
     }
   }
   grouping service-msp-alg-stats-information-block {
     leaf interface-name {
       type string;
       description "Name of the adaptive services interface";
     }
     container msp-alg-rsh-entry {
       description "RSH ALG stats";
       leaf rsh-invalid-pkts {
         type uint32;
       }
       leaf rsh-drop-pkts {
         type uint32;
       }
       leaf rsh-parse-fail-pkts {
         type uint32;
       }
       leaf rsh-freed-pkts {
         type uint32;
       }
     }
     container msp-alg-dns-entry {
       description "DNS ALG statistics";
       leaf dns-invalid-pkts {
         type uint32;
       }
       leaf dns-reply-pkts {
         type uint32;
       }
       leaf dns-oversize-pkts {
         type uint32;
       }
     }
     container msp-alg-pptp-entry {
       description "PPTP ALG statistics";
       leaf pptp-objects-active {
         type uint32;
       }
       leaf pptp-objects-total {
         type uint32;
       }
       leaf pptp-objects-error {
         type uint32;
       }
       leaf pptp-group-active {
         type uint32;
       }
       leaf pptp-group-total {
         type uint32;
       }
       leaf pptp-group-error {
         type uint32;
       }
       leaf pptp-packets-received {
         type uint32;
       }
       leaf pptp-packets-discarded {
         type uint32;
       }
       leaf pptp-packets-free {
         type uint32;
       }
       leaf pptp-ocrq-rcvd {
         type uint32;
       }
       leaf pptp-ocrq-discarded {
         type uint32;
       }
       leaf pptp-ocrp-rcvd {
         type uint32;
       }
       leaf pptp-ocrp-discarded {
         type uint32;
       }
       leaf pptp-wen-rcvd {
         type uint32;
       }
       leaf pptp-wen-discarded {
         type uint32;
       }
       leaf pptp-ccrq-rcvd {
         type uint32;
       }
       leaf pptp-cdsn-rcvd {
         type uint32;
       }
       leaf pptp-ccrq-discarded {
         type uint32;
       }
       leaf pptp-session-create {
         type uint32;
       }
       leaf pptp-session-destroy {
         type uint32;
       }
       leaf pptp-gate-create {
         type uint32;
       }
       leaf pptp-gate-hit {
         type uint32;
       }
       leaf pptp-gate-timeout {
         type uint32;
       }
       leaf pptp-nat-event {
         type uint32;
       }
       leaf pptp-nat-total {
         type uint32;
       }
       leaf pptp-nat-ok {
         type uint32;
       }
       leaf pptp-nat-pending {
         type uint32;
       }
       leaf pptp-nat-fail {
         type uint32;
       }
       leaf pptp-rm-total {
         type uint32;
       }
       leaf pptp-rm-ok {
         type uint32;
       }
       leaf pptp-rm-pending {
         type uint32;
       }
       leaf pptp-rm-fail {
         type uint32;
       }
       leaf pptp-nat-async-total {
         type uint32;
       }
       leaf pptp-nat-async-invalid {
         type uint32;
       }
       leaf pptp-nat-async-error1 {
         type uint32;
       }
       leaf pptp-nat-async-error2 {
         type uint32;
       }
       leaf pptp-asl-hole-ok {
         type uint32;
       }
       leaf pptp-asl-hole-error {
         type uint32;
       }
       leaf pptp-asl-first-hit {
         type uint32;
       }
       leaf pptp-asl-hole-timeout {
         type uint32;
       }
       leaf pptp-asl-invalid {
         type uint32;
       }
       leaf pptp-nat-ctx-free {
         type uint32;
       }
       leaf pptp-create-resource-error {
         type uint32;
       }
       leaf pptp-s2c-hole-error {
         type uint32;
       }
       leaf pptp-c2s-hole-error {
         type uint32;
       }
       leaf pptp-lnbrk-error {
         type uint32;
       }
       leaf pptp-mpool-error {
         type uint32;
       }
       leaf pptp-rm-client-error {
         type uint32;
       }
     }
     container msp-alg-rtsp-entry {
       description "RTSP ALG statistics";
       leaf rtsp-exceed-max-data-len {
         type uint32;
       }
       leaf rtsp-drop-packets {
         type uint32;
       }
       leaf rtsp-describe-msg-cnt {
         type uint32;
       }
       leaf rtsp-setup-msg-cnt {
         type uint32;
       }
       leaf rtsp-teardown-msg-cnt {
         type uint32;
       }
     }
     container msp-alg-ftp-entry {
       description "FTP ALG stats";
       leaf ftp-drop-pkts {
         type uint32;
       }
       leaf ftp-parse-fail-pkts {
         type uint32;
       }
       leaf ftp-bad-ip-pkts {
         type uint32;
       }
       leaf ftp-bad-port-pkts {
         type uint32;
       }
       leaf ftp-bad-cmd-pkts {
         type uint32;
       }
     }
     container msp-alg-talk-entry {
       description "TALK ALG stats";
       leaf talk-lookup-pkts {
         type uint32;
       }
       leaf talk-announce-pkts {
         type uint32;
       }
       leaf talk-delete-pkts {
         type uint32;
       }
     }
     container msp-alg-sql-entry {
       description "SQLNET ALG statistics";
       leaf sql-rcvd-pkts {
         type uint32;
       }
       leaf sql-parse-fail-pkts {
         type uint32;
       }
       leaf sql-freed-pkts {
         type uint32;
       }
       leaf sql-gate-fail-errs {
         type uint32;
       }
     }
     container msp-alg-dce-rpc-portmap-entry {
       description "DCE-RPC-PORTMAP ALG stats";
       leaf dce-rpc-lookup-request {
         type uint32;
       }
       leaf dce-rpc-map-request {
         type uint32;
       }
       leaf dce-rpc-lookup-reply {
         type uint32;
       }
       leaf dce-rpc-map-reply {
         type uint32;
       }
       leaf dce-rpc-fail-reply {
         type uint32;
       }
     }
     container msp-alg-dce-rpc-entry {
       description "DCE-RPC ALG stats";
       leaf dce-rpc-wrong-header {
         type uint32;
       }
       leaf dce-rpc-non-epm3 {
         type uint32;
       }
       leaf dce-rpc-type-mismatch {
         type uint32;
       }
       leaf dce-rpc-id-mismatch {
         type uint32;
       }
       leaf dce-rpc-call-mismatch {
         type uint32;
       }
       leaf dce-rpc-fragment-pkts {
         type uint32;
       }
       leaf dce-rpc-queue-pkts {
         type uint32;
       }
       leaf dce-rpc-drop-pkts {
         type uint32;
       }
       leaf dce-rpc-released-pkts {
         type uint32;
       }
     }
     container msp-alg-rpc-portmap-entry {
       description "RPC-PORTMAP ALG stats";
       leaf rpc-process-fail {
         type uint32;
       }
       leaf rpc-request {
         type uint32;
       }
       leaf rpc-call-dump {
         type uint32;
       }
       leaf rpc-call-callit {
         type uint32;
       }
       leaf rpc-reply-ok {
         type uint32;
       }
       leaf rpc-reply-dump {
         type uint32;
       }
       leaf rpc-reply-callit {
         type uint32;
       }
       leaf rpc-process-reply-deny {
         type uint32;
       }
       leaf rpc-process-reply-xid-mismatch {
         type uint32;
       }
       leaf rpc-pkt-ver-error {
         type uint32;
       }
       leaf rpc-pkt-not-rpcbind {
         type uint32;
       }
     }
     container msp-alg-rpc-entry {
       description "RPC ALG stats";
       leaf rpc-call-bind-version-2 {
         type uint32;
       }
       leaf rpc-call-bind-version-3 {
         type uint32;
       }
       leaf rpc-call-bind-version-4 {
         type uint32;
       }
       leaf rpc-call-bind-version-error {
         type uint32;
       }
       leaf rpc-reply-bind-version-2 {
         type uint32;
       }
       leaf rpc-reply-bind-version-3 {
         type uint32;
       }
       leaf rpc-reply-bind-version-4 {
         type uint32;
       }
       leaf rpc-reply-bind-version-error {
         type uint32;
       }
       leaf rpc-pkt-fragmented {
         type uint32;
       }
       leaf rpc-pkt-drop {
         type uint32;
       }
       leaf rpc-pkt-release {
         type uint32;
       }
     }
     container msp-alg-sip-entry {
       description "SIP ALG stats";
       leaf active-sip-call-count {
         type uint32;
         description "Total number of active SIP calls";
       }
       leaf sip-invite-count {
         type uint32;
         description "INVITE count";
       }
       leaf sip-invite-retransmit-count {
         type uint32;
         description "INVITE retransmits count";
       }
       leaf sip-register-count {
         type uint32;
         description "REGISTER count";
       }
       leaf sip-bye-count {
         type uint32;
         description "BYE count";
       }
       leaf sip-cancel-count {
         type uint32;
         description "CANCEL count";
       }
       leaf sip-subscribe-count {
         type uint32;
         description "SUBSCRIBE count";
       }
       leaf sip-notify-count {
         type uint32;
         description "NOTIFY count";
       }
       leaf sip-options-count {
         type uint32;
         description "OPTIONS count";
       }
       leaf sip-info-count {
         type uint32;
         description "INFO count";
       }
       leaf sip-update-count {
         type uint32;
         description "UPDATE count";
       }
       leaf sip-refer-count {
         type uint32;
         description "REFER count";
       }
       leaf sip-resp-ok-to-invite-count {
         type uint32;
         description "OK response to INVITE count";
       }
       leaf sip-resp-ok-to-non-invite-count {
         type uint32;
         description "OK response to non-INVITE count";
       }
       leaf sip-resp-1xx-count {
         type uint32;
         description "1xx response count";
       }
       leaf sip-redirection-3xx-resp-count {
         type uint32;
         description "3xx response count";
       }
       leaf sip-req-failure-4xx-resp-count {
         type uint32;
         description "4xx response count";
       }
       leaf sip-server-failure-5xx-resp-count {
         type uint32;
         description "5xx response count";
       }
       leaf sip-global-failure-6xx-resp-count {
         type uint32;
         description "6xx response count";
       }
       leaf sip-resp-all-retransmits-count {
         type uint32;
         description "Response (all) retransmits";
       }
       leaf sip-pkts-drop {
         type uint32;
         description "Total number of packets dropped";
       }
       leaf sip-unexpect-req-drop {
         type uint32;
         description "Number of unexpected requests dropped";
       }
       leaf sip-unexpect-res-drop {
         type uint32;
         description "Number of unexpected responses dropped";
       }
       leaf sip-dscp-marked {
         type uint32;
         description "Number of packets of DSCP marked";
       }
       leaf sip-dscp-marked-err {
         type uint32;
         description "Number of packets of DSCP marked error";
       }
       leaf sip-nat-err {
         type uint32;
         description "Number of NAT errors";
       }
       leaf sip-rr-hdr-exceed-max {
         type uint32;
         description "Number of RR headers exceeded maximum limits";
       }
       leaf sip-contact-hdr-exceed-max {
         type uint32;
         description "Number of contact headers exceeded maximum limits";
       }
       leaf sip-invite-drop-call-limit {
         type uint32;
         description "Number of invite dropped due to call limit";
       }
       leaf sip-msgs-not-processed {
         type uint32;
         description "Number of messages not processed by sip stack";
       }
       leaf sip-unknown-pkts-drop {
         type uint32;
         description "Number of unknown packets dropped";
       }
       leaf sip-decoding-error {
         type uint32;
         description "Number of decoding errors";
       }
       leaf sip-out-of-state {
         type uint32;
         description "Number of packets received in out of state";
       }
     }
     container msp-alg-h323-entry {
       description "H323 ALG stats";
       leaf h323-call-total {
         type uint32;
         description "H323 total calls";
       }
       leaf h323-call-active {
         type uint32;
         description "H323 active calls";
       }
       leaf h323-gate-install-fail {
         type uint32;
         description "H323 gate install failed";
       }
       leaf h323-pinhole-open-too-late {
         type uint32;
         description "H323 pinhole opened too late";
       }
       leaf h323-pinhole-hit-drop {
         type uint32;
         description "H323 pinhole hit dropped";
       }
       leaf h323-gate-timeout-fail {
         type uint32;
         description "H323 gate timeout failed";
       }
       leaf h323-drop-packet {
         type uint32;
         description "H323 packets dropped";
       }
       leaf h323-pkh-vctx-fail {
         type uint32;
         description "H323 get virtual ctx failed";
       }
       leaf h323-alloc-obj-fail {
         type uint32;
         description "H323 obj alloc failed";
       }
       leaf h323-alloc-grp-fail {
         type uint32;
         description "H323 group alloc failed";
       }
       leaf h323-alloc-ce-fail {
         type uint32;
         description "H323 ce alloc failed";
       }
       leaf h323-q931-decode-error {
         type uint32;
         description "H323 Q931 decode error";
       }
       leaf h323-h245-decode-error {
         type uint32;
         description "H323 H245 decode error";
       }
       leaf h323-q931-process-error {
         type uint32;
         description "H323 Q931 process error";
       }
       leaf h323-h245-process-error {
         type uint32;
         description "H323 H245 process error";
       }
       leaf h323-do-nat-fail {
         type uint32;
         description "H323 do nat failed";
       }
       leaf h323-do-rm-fail {
         type uint32;
         description "H323 do rm failed";
       }
       leaf h323-dscp-marked {
         type uint32;
         description "H323 dscp marked";
       }
       leaf h323-dscp-marked-err {
         type uint32;
         description "H323 dscp marked error";
       }
       leaf ras-alloc-obj-fail {
         type uint32;
         description "RAS obj alloc failed";
       }
       leaf ras-alloc-grp-fail {
         type uint32;
         description "RAS group alloc failed";
       }
       leaf ras-drop-packet {
         type uint32;
         description "RAS packets dropped";
       }
       leaf ras-packet-exist-err {
         type uint32;
         description "RAS packet exists in cookie error";
       }
       leaf ras-decode-error {
         type uint32;
         description "RAS decode error";
       }
       leaf ras-flood-error {
         type uint32;
         description "RAS flood error";
       }
       leaf ras-do-nat-fail {
         type uint32;
         description "RAS do nat failed";
       }
     }
     container msp-alg-tftp-entry {
       description "TFTP ALG stats";
       leaf tftp-total-invalid-pkts {
         type uint32;
         description "Number of Invalid packets";
       }
       leaf tftp-total-sessions {
         type uint32;
         description "Total number of sessions";
       }
       leaf tftp-active-sessions {
         type uint32;
         description "Number of active sessions";
       }
     }
     container msp-alg-ike-esp-entry {
       description "IKE ESP ALG stats";
       leaf ike-esp-sess-interest {
         type uint32;
         description "Number of session interests processed";
       }
       leaf ike-esp-sess-create {
         type uint32;
         description "Number of sessions created";
       }
       leaf ike-esp-sess-destroy {
         type uint32;
         description "Number of sessions destroyed";
       }
       leaf ike-esp-ctrl-sess-create {
         type uint32;
         description "Number of control sessions created";
       }
       leaf ike-esp-ctrl-sess-destroy {
         type uint32;
         description "Number of control sessions destroyed";
       }
       leaf ike-esp-data-sess-create {
         type uint32;
         description "Number of data sessions created";
       }
       leaf ike-esp-data-sess-destroy {
         type uint32;
         description "Number of data sessions destroyed";
       }
       leaf ike-esp-gate-create {
         type uint32;
         description "Number of gates created";
       }
       leaf ike-esp-gate-hit {
         type uint32;
         description "Number of gates hit";
       }
       leaf ike-esp-gate-timeout {
         type uint32;
         description "Number of gates timedout";
       }
     }
   }
   grouping service-msp-alg-sip-globals-information-block {
     leaf interface-name {
       type string;
       description "Name of the adaptive services interface";
     }
     container msp-alg-sip-globals-entry {
       description "Show SIP ALG Global configurations";
       leaf sip-max-no-calls {
         type uint32;
         description "Maximum number of calls allowed";
       }
       leaf sip-inactive-media-timeout {
         type uint32;
         description "Inactive media timeout";
       }
       leaf sip-max-call-timeout {
         type uint32;
         description "Maximum call timeout";
       }
       leaf sip-t1-interval {
         type uint32;
         description "T1 interval timeout";
       }
       leaf sip-t4-interval {
         type uint32;
         description "T4 interval timeout";
       }
       leaf sip-c-interval {
         type uint32;
         description "C interval timeout";
       }
     }
   }
   grouping service-ha-info-block {
     leaf interface-name {
       type string;
       description "Name of the adaptive services interface";
     }
     leaf ha-type {
       type string;
       description "Type of HA - Intra Chassis / Inter Chassis";
     }
     leaf ha-role {
       type string;
       description "Role of PIC in HA pair";
     }
     leaf ha-conn-status {
       type string;
       description "Connection status - Up/Down";
     }
     leaf ha-sync-type {
       type string;
       description "Sync Type";
     }
     leaf ha-local-ip {
       type string;
       description "Local IP address";
     }
     leaf ha-local-port {
       type int32;
       description "Local Port being used";
     }
     leaf ha-remote-ip {
       type string;
       description "Peer's IP address";
     }
     leaf ha-remote-port {
       type int32;
       description "Remote Port being used";
     }
   }
   grouping service-flow-analysis-information-block {
     container service-flow-analysis-entry {
       container flow-analysis-statistics-pic-info {
         leaf pic-name {
           type string;
           description "Services PIC Name";
         }
       }
       list flow-analysis-statistics-entry {
         description "Flow Analysis Statistics";
         leaf num-total-flows-active {
           type uint32;
           description "Number of Total Flows Active";
         }
         leaf num-total-tcp-flows-active {
           type uint32;
           description "Number of Total TCP Flows Active";
         }
         leaf num-total-udp-flows-active {
           type uint32;
           description "Number of Total UDP Flows Active";
         }
         leaf num-total-other-flows-active {
           type uint32;
           description "Number of Total Other Flows Active";
         }
         leaf num-total-predicted-flows-active {
           type uint32;
           description "Number of Total Predicted Flows Active";
         }
         leaf num-total-pred-discard-flows-active {
           type uint32;
           description "Number of Total Predicted Discard Flows Active";
         }
         leaf num-created-flows-per-sec {
           type uint32;
           description "Number of Created Flows per Second";
         }
         leaf num-deleted-flows-per-sec {
           type uint32;
           description "Number of Deleted Flows per Second";
         }
         leaf peak-total-flows-active {
           type uint32;
           description "Peak Total Flows Active";
         }
         leaf peak-total-tcp-flows-active {
           type uint32;
           description "Peak Total TCP Flows Active";
         }
         leaf peak-total-udp-flows-active {
           type uint32;
           description "Peak Total UDP Flows Active";
         }
         leaf peak-total-other-flows-active {
           type uint32;
           description "Peak Total Other Flows Active";
         }
         leaf peak-created-flows-per-second {
           type uint32;
           description "Peak Created Flows per Second";
         }
         leaf peak-deleted-flows-per-second {
           type uint32;
           description "Peak Deleted Flows per Second";
         }
         leaf pkts-received {
           type uint64;
           description "Packets received";
         }
         leaf pkts-transmitted {
           type uint64;
           description "Packets transmitted";
         }
         leaf slow-path-forward {
           type uint64;
           description "Slow Path Forward";
         }
         leaf slow-path-discard {
           type uint64;
           description "Slow Path Discard";
         }
         leaf slow-path-predicted-discard {
           type uint64;
           description "Slow Path Predicted Discard";
         }
       }
       container flow-analysis-num-flows-sec-samples-entry {
         leaf num-flows-sec-samples {
           type uint32;
         }
       }
       list flow-analysis-num-flows-sec-entry {
         description "Flow Rate Statistics";
         leaf flow-operation {
           type string;
         }
         leaf num-flows-sec-300000-plus {
           type uint32;
           description "Flow setup rate is 300k or above";
         }
         leaf num-flows-sec-250000-plus {
           type uint32;
           description "Flow setup rate is 250k or above";
         }
         leaf num-flows-sec-200000-plus {
           type uint32;
           description "Flow setup rate is 200k or above";
         }
         leaf num-flows-sec-160000-plus {
           type uint32;
           description "Flow setup rate is 160k or above";
         }
         leaf num-flows-sec-150000-plus {
           type uint32;
           description "Flow setup rate is 150k or above";
         }
         leaf num-flows-sec-50000-plus {
           type uint32;
         }
         leaf num-flows-sec-40000-50000 {
           type uint32;
         }
         leaf num-flows-sec-30000-40000 {
           type uint32;
         }
         leaf num-flows-sec-20000-30000 {
           type uint32;
         }
         leaf num-flows-sec-10000-20000 {
           type uint32;
         }
         leaf num-flows-sec-1000-10000 {
           type uint32;
         }
         leaf num-flows-sec-1000-minus {
           type uint32;
         }
       }
       list flow-analysis-protocol-lifetime-entry {
         description "Flow Analysis Protocol Lifetime Statistics";
         leaf flow-lifetime-240s-plus {
           type uint64;
         }
         leaf udp-flow-lifetime-240s-plus {
           type uint64;
         }
         leaf http-flow-lifetime-240s-plus {
           type uint64;
         }
         leaf flow-lifetime-120s-240s {
           type uint64;
         }
         leaf udp-flow-lifetime-120s-240s {
           type uint64;
         }
         leaf flow-lifetime-60s-120s {
           type uint64;
         }
         leaf udp-flow-lifetime-60s-120s {
           type uint64;
         }
         leaf flow-lifetime-30s-60s {
           type uint64;
         }
         leaf udp-flow-lifetime-30s-60s {
           type uint64;
         }
         leaf flow-lifetime-15s-30s {
           type uint64;
         }
         leaf udp-flow-lifetime-15s-30s {
           type uint64;
         }
         leaf flow-lifetime-5s-15s {
           type uint64;
         }
         leaf udp-flow-lifetime-5s-15s {
           type uint64;
         }
         leaf flow-lifetime-1s-5s {
           type uint64;
         }
         leaf udp-flow-lifetime-1s-5s {
           type uint64;
         }
         leaf flow-lifetime-1s-minus {
           type uint64;
         }
         leaf udp-flow-lifetime-1s-minus {
           type uint64;
         }
       }
     }
   }
   grouping service-subs-analysis-information-block {
     container subs-analysis-statistics-pic-info {
       leaf pic-name {
         type string;
         description "Services PIC Name";
       }
     }
     list subs-analysis-statistics-entry {
       description "Subscriber Analysis Statistics";
       leaf num-total-subs-active {
         type uint32;
         description "Number of Total Subscribers Active";
       }
       leaf num-created-subs-per-sec {
         type uint32;
         description "Number of Created Subscribers per Second";
       }
       leaf num-deleted-subs-per-sec {
         type uint32;
         description "Number of Deleted Subscribers per Second";
       }
       leaf peak-total-subs-active {
         type uint32;
         description "Peak Total Subscribers Active";
       }
       leaf peak-created-subs-per-second {
         type uint32;
         description "Peak Created Subscribers per Second";
       }
       leaf peak-deleted-subs-per-second {
         type uint32;
         description "Peak Deleted Subscribers per Second";
       }
     }
     container subs-analysis-num-subs-sec-samples-entry {
       leaf num-subs-sec-samples {
         type uint32;
       }
     }
     list subs-analysis-num-subs-sec-entry {
       description "Subscriber Rate Statistics";
       leaf subs-operation {
         type string;
       }
       leaf num-subs-sec-300000-plus {
         type uint32;
         description "Subscriber setup rate is 300k or above";
       }
       leaf num-subs-sec-250000-plus {
         type uint32;
         description "Subscriber setup rate is 250k or above";
       }
       leaf num-subs-sec-200000-plus {
         type uint32;
         description "Subscriber setup rate is 200k or above";
       }
       leaf num-subs-sec-150000-plus {
         type uint32;
         description "Subscriber setup rate is 150k or above";
       }
       leaf num-subs-sec-100000-plus {
         type uint32;
         description "Subscriber setup rate is 100k or above";
       }
       leaf num-subs-sec-50000-plus {
         type uint32;
         description "Subscriber setup rate is 50k or above";
       }
       leaf num-subs-sec-40000-plus {
         type uint32;
         description "Subscriber setup rate is > 40k or above";
       }
       leaf num-subs-sec-30000-plus {
         type uint32;
         description "Subscriber setup rate is > 30k or above";
       }
       leaf num-subs-sec-20000-plus {
         type uint32;
         description "Subscriber setup rate is > 20k or above";
       }
       leaf num-subs-sec-10000-plus {
         type uint32;
         description "Subscriber setup rate is > 10k or above";
       }
       leaf num-subs-sec-1000-plus {
         type uint32;
         description "Subscriber setup rate is > 1k or above";
       }
       leaf num-subs-sec-1000-minus {
         type uint32;
         description "Subscriber setup rate is < 1k";
       }
     }
   }
   grouping service-sfw-conversation-information-block {
     container sfw-per-service-set-conversation {
       description "Show conversations";
       leaf interface-name {
         type string;
         description "Name of the adaptive services interface";
       }
       leaf service-set-name {
         type string;
         description "Name of the service set";
       }
       list sfw-conversation {
         description "Stateful firewall conversations";
         leaf sfw-flow-table-conv-alg {
           type string;
           description "Application Protocol Gateway protocol";
         }
         leaf sfw-flow-table-conv-initiator {
           type int32;
           description "Number of initiator flows";
         }
         leaf sfw-flow-table-conv-responder {
           type int32;
           description "Number of responder flows";
         }
         list service-sfw-flow-table {
           description "Stateful firewall flows";
           leaf-list service-sfw-flow-table.heading {
             type string;
             description "Stateful firewall flows";
           }
           list sfw-flow-entry {
             description "Flow brief information";
             leaf sfw-flow-protocol {
               type string;
               description "Flow protocol description";
             }
             leaf sfw-flow-source-ip {
               type string;
               description "Source IP address";
             }
             leaf sfw-flow-source-port {
               type int32;
               description "Source port address";
             }
             leaf sfw-flow-destination-ip {
               type string;
               description "Flow destination IP address";
             }
             leaf sfw-flow-destination-port {
               type string;
               description "Flow destination port";
             }
             leaf sfw-flow-state {
               type string;
               description "Flow state";
             }
             leaf sfw-flow-direction {
               type string;
               description "Flow direction";
             }
             leaf sfw-flow-frame-counter {
               type uint64;
               description "Number of frames transmitted";
             }
             leaf sfw-flow-gate-id {
               type uint64;
               description "PGCP gate-id";
             }
             leaf sfw-flow-table-byte-count {
               type uint64;
               description "Flow byte count";
             }
             leaf sfw-flow-table-tcp-window-size {
               type uint64;
               description "TCP protocol window size";
             }
             leaf sfw-flow-table-tcp-acknowledge {
               type uint64;
               description "TCP protocol acknowledge";
             }
             leaf sfw-flow-table-tcp-tickle {
               type uint64;
               description "Time between TCP tickles (seconds)";
             }
             leaf sfw-flow-table-role {
               type string;
               description "Role of flow in conversation";
             }
             leaf sfw-flow-table-timeout {
               type uint64;
               description "Timeout value of flow (seconds)";
             }
             leaf sfw-flow-table-protocol-detail {
               type string;
               description "Flow protocol detail information";
             }
             container sfw-flow-nat {
               description "NAT translation";
               leaf sfw-flow-nat-type {
                 type string;
                 description "Type of NAT translation";
               }
               leaf sfw-flow-nat-ip {
                 type string;
                 description "Original IP address";
               }
               leaf sfw-flow-nat-port {
                 type string;
                 description "Original port";
               }
               leaf sfw-flow-translated-ip {
                 type string;
                 description "Translated IP address";
               }
               leaf sfw-flow-translated-port {
                 type string;
                 description "Translated port";
               }
             }
           }
         }
       }
     }
   }
   grouping service-sfw-sip-call-information-block {
     list sfw-per-service-set-sip-calls {
       description "Stateful firewall SIP calls sorted by service set";
       leaf interface-name {
         type string;
         description "Name of the adaptive services interface";
       }
       leaf service-set-name {
         type string;
         description "Name of the service set";
       }
       container sfw-sip-calls {
         list sfw-sip-call-entry {
           description "Session Initiation Protocol call";
           leaf sfw-sip-from {
             type string;
             description "SIP invite from";
           }
           leaf sfw-sip-to {
             type string;
             description "SIP invite to";
           }
           leaf sfw-sip-callid {
             type string;
             description "SIP call ID";
           }
           leaf sfw-sip-number-control-iflows {
             type int32;
             description "Number of SIP Control initiator flows";
           }
           leaf sfw-sip-number-control-rflows {
             type int32;
             description "Number of SIP control responder flows";
           }
           leaf sfw-sip-number-contact-iflows {
             type int32;
             description "Number of SIP contact initiator flows";
           }
           leaf sfw-sip-number-contact-rflows {
             type int32;
             description "Number of SIP contact responder flows";
           }
           leaf sfw-sip-number-media-iflows {
             type int32;
             description "Number of SIP media initiator flows";
           }
           leaf sfw-sip-number-media-rflows {
             type int32;
             description "Number of SIP media responder flows";
           }
           leaf sfw-flow-protocol {
             type string;
             description "Flow protocol description";
           }
           leaf sfw-flow-source-ip {
             type string;
             description "Source IP address";
           }
           leaf sfw-flow-source-port {
             type int32;
             description "Source port address";
           }
           leaf sfw-flow-destination-ip {
             type string;
             description "Flow destination IP address";
           }
           leaf sfw-flow-destination-port {
             type string;
             description "Flow destination port";
           }
           leaf sfw-flow-state {
             type string;
             description "Flow state";
           }
           leaf sfw-flow-direction {
             type string;
             description "Flow direction";
           }
           leaf sfw-flow-frame-counter {
             type uint64;
             description "Number of frames transmitted";
           }
           leaf sfw-flow-gate-id {
             type uint64;
             description "PGCP gate-id";
           }
           leaf sfw-flow-table-byte-count {
             type uint64;
             description "Flow byte count";
           }
           leaf sfw-flow-table-tcp-window-size {
             type uint64;
             description "TCP protocol window size";
           }
           leaf sfw-flow-table-tcp-acknowledge {
             type uint64;
             description "TCP protocol acknowledge";
           }
           leaf sfw-flow-table-tcp-tickle {
             type uint64;
             description "Time between TCP tickles (seconds)";
           }
           leaf sfw-flow-table-role {
             type string;
             description "Role of flow in conversation";
           }
           leaf sfw-flow-table-timeout {
             type uint64;
             description "Timeout value of flow (seconds)";
           }
           leaf sfw-flow-table-protocol-detail {
             type string;
             description "Flow protocol detail information";
           }
           leaf-list service-sfw-flow-table.heading {
             type string;
             description "Stateful firewall flows";
           }
         }
       }
     }
   }
   grouping service-sfw-statistics-information-block {
     container service-sfw-statistics-entry {
       leaf interface-name {
         type string;
         description "Name of the adaptive services interface";
       }
       list sfw-stats-service-set-entry {
         leaf total-flow-accepts {
           type uint64;
           description "Total packets accepted by new and existing flows";
         }
         leaf total-flow-discards {
           type uint64;
           description "Total packets discarded by new and existing flows";
         }
         leaf total-flow-rejects {
           type uint64;
           description "Total packets rejected by new and existing flows";
         }
         leaf total-drops {
           type uint64;
           description "Total packets dropped by protocol processing";
         }
         container new-flow-counters {
           leaf new-flow-accepts {
             type uint32;
             description "Packets accepted by new flows";
           }
           leaf new-flow-discards {
             type uint32;
             description "Packets discarded by new flows";
           }
           leaf new-flow-rejects {
             type uint32;
             description "Packets rejected by new flows";
           }
         }
         container existing-flow-counters {
           leaf existing-flow-accepts {
             type uint32;
             description "Packets accepted by existing accept flow";
           }
           leaf existing-flow-discards {
             type uint32;
             description "Packets discarded by existing drop flow";
           }
           leaf existing-flow-rejects {
             type uint32;
             description "Packets rejected by existing reject flow";
           }
         }
         container hairpinning-counters {
           leaf slow-path-hairpinned-packets {
             type uint32;
             description "Initiator packets for Hairpinning";
           }
           leaf fast-path-hairpinned-packets {
             type uint32;
             description "Packets recieved on existing Hairpinned flows";
           }
         }
         container drop_counters {
           leaf ip-option {
             type uint32;
             description "IP option drops";
           }
           leaf syn-defense {
             type uint32;
             description "Incomplete TCP handshakes";
           }
           leaf nat-ports-exhausted {
             type uint32;
             description "NAT ports exhausted";
           }
           leaf subs-flow-limit-exceeded {
             type uint32;
             description "Subscriber flow limit exceeded";
           }
         }
         container error-counters {
           leaf ip-errors {
             type uint32;
             description "IP processing errors";
           }
           leaf tcp-errors {
             type uint32;
             description "TCP processing errors";
           }
           leaf udp-errors {
             type uint32;
             description "UDP processing errors";
           }
           leaf icmp-errors {
             type uint32;
             description "ICMP processing errors";
           }
           leaf non-ip-packets {
             type uint32;
             description "Non-IP packets";
           }
           leaf alg-errors {
             type uint32;
             description "ALG processing errors";
           }
         }
         container ip-error-counters {
           leaf ip-length-error {
             type uint32;
             description "IP packet length inconsistencies";
           }
           leaf ip-header-length-error {
             type uint32;
             description "Minimum IP header length check failures";
           }
           leaf long-packet {
             type uint32;
             description "Reassembled packet exceeds maximum IP length (65,535 bytes)";
           }
           leaf illegal-destination-address {
             type uint32;
             description "Illegal destination address";
           }
           leaf illegal-source-address {
             type uint32;
             description "Illegal source address";
           }
           leaf ttl-zero {
             type uint32;
             description "IP packets received with a TTL value of 0";
           }
           leaf illegal-ip-protocol {
             type uint32;
             description "Illegal IP protocol number ";
           }
           leaf non-ipv6 {
             type uint32;
             description "Non-IPv6 packets";
           }
           leaf land-attack {
             type uint32;
             description "IP source address same as destination address";
           }
           leaf not-ip-packet {
             type uint32;
             description "Not IP Packet";
           }
           leaf non-ipv4 {
             type uint32;
             description "Non-IPv4 packets";
           }
           leaf bad-checksum {
             type uint32;
             description "Bad checksum";
           }
           leaf illegal-fragment-length {
             type uint32;
             description "Illegal IP fragment length";
           }
           leaf fragment-overlap {
             type uint32;
             description "IP fragment overlap";
           }
           leaf fragment-reassembly-timeout {
             type uint32;
             description "IP fragment reassembly timeout";
           }
           leaf fragment-limit-exceeded {
             type uint32;
             description "IP fragment limit exceeded";
           }
           leaf unknown {
             type uint32;
             description "Unknown errors";
           }
         }
         container tcp-error-counters {
           leaf tcp-header-length-error {
             type uint32;
             description "TCP header length inconsistencies";
           }
           leaf tcp-zero-port {
             type uint32;
             description "Source or destination port number is zero";
           }
           leaf illegal-sequence-number-flags {
             type uint32;
             description "Illegal sequence number and flags combinations";
           }
           leaf syn-attack {
             type uint32;
             description "SYN attack";
           }
           leaf non-syn-first-packet {
             type uint32;
             description "First packet not a SYN message";
           }
           leaf tcp-port-scan {
             type uint32;
             description "TCP port scan";
           }
           leaf bad-syn-cookie-response {
             type uint32;
             description "Bad SYN cookie response";
           }
           leaf tcp-recon-sequence-number-error {
             type uint32;
             description "TCP reconstructor sequence number error";
           }
           leaf tcp-recon-retransmits {
             type uint32;
             description "TCP reconstructor retransmissions";
           }
           leaf tcp-partially-opened-connection-timeout-syn-rcvd {
             type uint32;
             description "TCP partially opened connection timeout";
           }
           leaf tcp-partially-opened-connection-timeout-syn-ack-rcvd {
             type uint32;
             description "TCP partially opened connection timeout";
           }
           leaf tcp-partially-closed-connection-reuse {
             type uint32;
             description "TCP partially closed connection reuse";
           }
           leaf tcp-3way-error-client-sent-syn-ack {
             type uint32;
             description "TCP 3-way error - client sent SYN+ACK";
           }
           leaf tcp-3way-error-server-sent-ack {
             type uint32;
             description "TCP 3-way error - server sent ACK";
           }
           leaf tcp-3way-error-syn-seq-num-retrans-mismatch {
             type uint32;
             description "TCP 3-way error - SYN seq number retransmission mismatch";
           }
           leaf tcp-3way-error-rst-seq-num-mismatch {
             type uint32;
             description "TCP 3-way error - RST seq number mismatch";
           }
           leaf tcp-3way-error-fin-received {
             type uint32;
             description "TCP 3-way error - FIN received";
           }
           leaf tcp-3way-error-invalid-flags {
             type uint32;
             description "TCP 3-way error - invalid TCP flag combination";
           }
           leaf tcp-3way-error-syn-no-flow-initiator {
             type uint32;
             description "TCP 3-way error - SYN recvd but no client flows";
           }
           leaf tcp-3way-error-first-packet-syn-ack {
             type uint32;
             description "TCP 3-way error - first packet SYN+ACK";
           }
           leaf tcp-3way-error-first-packet-fin-ack {
             type uint32;
             description "TCP 3-way error - first packet FIN+ACK";
           }
           leaf tcp-3way-error-first-packet-fin {
             type uint32;
             description "TCP 3-way error - first packet FIN";
           }
           leaf tcp-3way-error-first-packet-rst {
             type uint32;
             description "TCP 3-way error - first packet RST";
           }
           leaf tcp-3way-error-first-packet-ack {
             type uint32;
             description "TCP 3-way error - first packet ack";
           }
           leaf tcp-3way-error-first-packet-invalid-flags {
             type uint32;
             description "TCP 3-way error - first packet ack";
           }
           leaf tcp-close-error-no-final-ack {
             type uint32;
             description "TCP close error - no final ack";
           }
           leaf tcp-resumed-flow {
             type uint32;
             description "TCP Resumed Flow";
           }
         }
         container udp-error-counters {
           leaf udp-header-length-error {
             type uint32;
             description "IP data length is less than minimum UDP header length (8 bytes)";
           }
           leaf udp-zero-port {
             type uint32;
             description "Source or destination port number is zero";
           }
           leaf udp-port-scan {
             type uint32;
             description "UDP port scan (ICMP error seen for UDP flow)";
           }
         }
         container icmp-error-counters {
           leaf icmp-length-error {
             type uint32;
             description "IP data length less than minimum ICMP header length (8 bytes)";
           }
           leaf icmp-error-length-error {
             type uint32;
             description "ICMP error length inconsistencies";
           }
           leaf ping-duplicate-sequence-number {
             type uint32;
             description "Duplicate ping sequence number";
           }
           leaf ping-mismatched-sequence-number {
             type uint32;
             description "Mismatched ping sequence number";
           }
           leaf icmp-error-no-matching-flow {
             type uint32;
             description "No matching flow for ICMP error packet";
           }
         }
         container alg-error-counters {
           leaf alg-bootp-errors {
             type uint32;
             description "ALG BOOTP errors";
           }
           leaf alg-dce-rpc-errors {
             type uint32;
             description "ALG DCE-RPC errors";
           }
           leaf alg-dce-rpc-portmap-errors {
             type uint32;
             description "ALG DCE-RPC portmap errors";
           }
           leaf alg-dns-errors {
             type uint32;
             description "ALG DNS errors";
           }
           leaf alg-exec-errors {
             type uint32;
             description "ALG exec errors";
           }
           leaf alg-ftp-errors {
             type uint32;
             description "ALG FTP errors";
           }
           leaf alg-h323-errors {
             type uint32;
             description "ALG H323 errors";
           }
           leaf alg-icmp-errors {
             type uint32;
             description "ALG ICMP errors";
           }
           leaf alg-iiop-errors {
             type uint32;
             description "ALG IIOP errors";
           }
           leaf alg-login-errors {
             type uint32;
             description "ALG login errors";
           }
           leaf alg-netbios-errors {
             type uint32;
             description "ALG NetBIOS errors";
           }
           leaf alg-netshow-errors {
             type uint32;
             description "ALG NetShow errors";
           }
           leaf alg-realaudio-errors {
             type uint32;
             description "ALG Real Audio errors";
           }
           leaf alg-rpc-errors {
             type uint32;
             description "ALG RPC errors";
           }
           leaf alg-rpc-portmap-errors {
             type uint32;
             description "ALG RPC portmap errors";
           }
           leaf alg-rtsp-errors {
             type uint32;
             description "ALG Real-Time Streaming Protocol errors";
           }
           leaf alg-shell-errors {
             type uint32;
             description "ALG shell errors";
           }
           leaf alg-sip-errors {
             type uint32;
             description "ALG Session Initiation Protocol errors";
           }
           leaf alg-snmp-errors {
             type uint32;
             description "ALG SNMP errors";
           }
           leaf alg-sqlnet-errors {
             type uint32;
             description "ALG SQLNet errors";
           }
           leaf alg-tftp-errors {
             type uint32;
             description "ALG TFTP errors";
           }
           leaf alg-traceroute-errors {
             type uint32;
             description "ALG traceroute errors";
           }
         }
         container sip-alg-counters {
           container total-counters {
             leaf total-messages {
               type uint32;
               description "Total SIP messages";
             }
             leaf call-segments {
               type uint32;
               description "SIP call segments";
             }
           }
           container parser-counters {
             leaf syntax-errors {
               type uint32;
               description "SIP syntax errors";
             }
             leaf content-errors {
               type uint32;
               description "SIP message content errors";
             }
             leaf unknown-methods {
               type uint32;
               description "SIP unknown methods";
             }
           }
           container message-counters {
             leaf response-provisional {
               type uint32;
               description "Number of provisional responses";
             }
             leaf response-invite-ok {
               type uint32;
               description "Number of 'OK' responses to INVITE messages";
             }
             leaf response-non-invite-ok {
               type uint32;
               description "Number of 'OK' responses to messages other than INVITE";
             }
             leaf response-redir {
               type uint32;
               description "Number of redirection (3xx) responses";
             }
             leaf response-request-failure {
               type uint32;
               description "Number of request failure (4xx) responses";
             }
             leaf response-server-failure {
               type uint32;
               description "Number of server failure (5xx) responses";
             }
             leaf response-global-failure {
               type uint32;
               description "Number of global failure (6xx) responses";
             }
             leaf response-invalid {
               type uint32;
               description "Number of invalid responses";
             }
             leaf response-retransmits {
               type uint32;
               description "Number of response retransmissions";
             }
             leaf register-new {
               type uint32;
               description "Number of REGISTER messages";
             }
             leaf invite-new {
               type uint32;
               description "Number of new INVITE messages";
             }
             leaf invite-retransmits {
               type uint32;
               description "Number of INVITE message retransmissions";
             }
             leaf reinvites {
               type uint32;
               description "Number of ReINVITE messages";
             }
             leaf cancel-valid {
               type uint32;
               description "Number of valid CANCEL messages";
             }
             leaf cancel-invalid {
               type uint32;
               description "Number of invalid CANCEL messages";
             }
             leaf ack-valid {
               type uint32;
               description "Number of valid ACK messages";
             }
             leaf ack-invalid {
               type uint32;
               description "Number of invalid ACK messages";
             }
             leaf ack-retransmits {
               type uint32;
               description "Number of ACK message retransmissions";
             }
             leaf bye-valid {
               type uint32;
               description "Number of valid BYE messages";
             }
             leaf bye-invalid {
               type uint32;
               description "Number of invalid BYE messages";
             }
             leaf subscribe-valid {
               type uint32;
               description "Number of valid SUBSCRIBE messages";
             }
             leaf subscribe-invalid {
               type uint32;
               description "Number of invalid SUBSCRIBE messages";
             }
             leaf notify-valid {
               type uint32;
               description "Number of valid NOTIFY messages";
             }
             leaf notify-invalid {
               type uint32;
               description "Number of invalid NOTIFY messages";
             }
             leaf message-valid {
               type uint32;
               description "Number of valid MESSAGE messages";
             }
             leaf message-invalid {
               type uint32;
               description "Number of invalid MESSAGE messages";
             }
             leaf options-valid {
               type uint32;
               description "Number of valid OPTIONS messages";
             }
             leaf options-invalid {
               type uint32;
               description "Number of invalid OPTIONS messages";
             }
             leaf info-valid {
               type uint32;
               description "Number of valid INFO messages";
             }
             leaf info-invalid {
               type uint32;
               description "Number of invalid INFO messages";
             }
             leaf update-valid {
               type uint32;
               description "Number of valid UPDATE messages";
             }
             leaf update-invalid {
               type uint32;
               description "Number of invalid UPDATE messages";
             }
             leaf refer-valid {
               type uint32;
               description "Number of valid REFER messages";
             }
             leaf refer-invalid {
               type uint32;
               description "Number of invalid REFER messages";
             }
           }
         }
         container drop-flows {
           leaf max-ingress-drop-flows {
             type string;
             description "Maximum ingress drop flows allowed";
           }
           leaf max-egress-drop-flows {
             type string;
             description "Maximum egress drop flows allowed";
           }
           container drop-flows-counters {
             leaf current-ingress-drop-flows {
               type int32;
               description "Current ingress drop flows count";
             }
             leaf current-egress-drop-flows {
               type int32;
               description "Current egress drop flows count";
             }
             leaf ingress-drop-flowlimit-drops {
               type uint32;
               description "Drops because ingress drop flow limit is reached";
             }
             leaf egress-drop-flowlimit-drops {
               type uint32;
               description "Drops because egress drop flow limit is reached";
             }
           }
         }
         leaf service-set-name {
           type string;
           description "Name of the service set";
         }
         leaf alg-name {
           type string;
           description "Name of the ALG";
         }
         leaf sip-active-call-count {
           type uint32;
           description "Number of active SIP calls in the service set";
         }
         leaf sip-active-reg-count {
           type uint32;
           description "Number of active SIP registrations in the service set";
         }
       }
     }
   }
   grouping service-softwire-table-information-block {
     list softwire-per-service-set-flow-table {
       description "Flows sorted by service set";
       leaf interface-name {
         type string;
         description "Name of the adaptive services interface";
       }
       leaf service-set-name {
         type string;
         description "Name of the service set";
       }
       list service-softwire-table {
         description "Softwire flows";
         leaf-list service-softwire-table.heading {
           type string;
           description "Softwire flows";
         }
         list softwire-entry {
           description "Flow brief information";
           leaf softwire-source-ip {
             type string;
             description "Softwire source IP address";
           }
           leaf softwire-destination-ip {
             type string;
             description "Softwire destination IP address";
           }
           leaf softwire-direction {
             type string;
             description "Softwire direction";
           }
           leaf softwire-flow-count {
             type string;
             description "Number of flows in softwire";
           }
           leaf softwire-table-timeout {
             type uint64;
             description "Timeout value of flow (seconds)";
           }
         }
         list sfw-flow-entry {
           description "Flow brief information";
           container sfw-flow-nat {
             description "NAT translation";
             leaf sfw-flow-nat-type {
               type string;
               description "Type of NAT translation";
             }
             leaf sfw-flow-nat-ip {
               type string;
               description "Original IP address";
             }
             leaf sfw-flow-nat-port {
               type string;
               description "Original port";
             }
             leaf sfw-flow-translated-ip {
               type string;
               description "Translated IP address";
             }
             leaf sfw-flow-translated-port {
               type string;
               description "Translated port";
             }
           }
         }
       }
     }
   }
   grouping service-softwire-flow-table-information-block {
     list softwire-per-service-set-flow-table {
       description "Flows sorted by service set";
       leaf interface-name {
         type string;
         description "Name of the adaptive services interface";
       }
       leaf service-set-name {
         type string;
         description "Name of the service set";
       }
       list service-softwire-table {
         description "Softwire flows";
         leaf-list service-softwire-table.heading {
           type string;
           description "Softwire flows";
         }
         list softwire-entry {
           description "Flow brief information";
           leaf softwire-source-ip {
             type string;
             description "Softwire source IP address";
           }
           leaf softwire-destination-ip {
             type string;
             description "Softwire destination IP address";
           }
           leaf softwire-direction {
             type string;
             description "Softwire direction";
           }
           leaf softwire-flow-count {
             type string;
             description "Number of flows in softwire";
           }
           leaf softwire-table-timeout {
             type uint64;
             description "Timeout value of flow (seconds)";
           }
         }
         list sfw-flow-entry {
           description "Flow brief information";
           leaf sfw-flow-protocol {
             type string;
             description "Flow protocol description";
           }
           leaf sfw-flow-source-ip {
             type string;
             description "Source IP address";
           }
           leaf sfw-flow-source-port {
             type int32;
             description "Source port address";
           }
           leaf sfw-flow-destination-ip {
             type string;
             description "Flow destination IP address";
           }
           leaf sfw-flow-destination-port {
             type string;
             description "Flow destination port";
           }
           leaf sfw-flow-state {
             type string;
             description "Flow state";
           }
           leaf sfw-flow-direction {
             type string;
             description "Flow direction";
           }
           leaf sfw-flow-frame-counter {
             type uint64;
             description "Number of frames transmitted";
           }
           leaf sfw-flow-gate-id {
             type uint64;
             description "PGCP gate-id";
           }
           container sfw-flow-nat {
             description "NAT translation";
             leaf sfw-flow-nat-type {
               type string;
               description "Type of NAT translation";
             }
             leaf sfw-flow-nat-ip {
               type string;
               description "Original IP address";
             }
             leaf sfw-flow-nat-port {
               type string;
               description "Original port";
             }
             leaf sfw-flow-translated-ip {
               type string;
               description "Translated IP address";
             }
             leaf sfw-flow-translated-port {
               type string;
               description "Translated port";
             }
           }
           container sw-flow-nat-entry {
             description "NAT translation";
             leaf sfw-flow-nat-sw-nat-type {
               type string;
               description "Type of NAT translation";
             }
             leaf sfw-flow-nat-ip {
               type string;
               description "Original IP address";
             }
             leaf sfw-flow-nat-port {
               type string;
               description "Original port";
             }
             leaf sfw-flow-translated-ip {
               type string;
               description "Translated IP address";
             }
             leaf sfw-flow-translated-port {
               type string;
               description "Translated port";
             }
           }
         }
       }
     }
   }
   grouping service-softwire-statistics-information-block {
     container service-softwire-dslite-statistics-entry {
       leaf srv-pic-name {
         type string;
         description "Services PIC Name";
       }
       leaf softwire-created {
         type uint32;
         description "Number of Softwires Created";
       }
       leaf softwire-created-for-reverse-packet {
         type uint32;
         description "Number of Softwires Created for EIF/HP packets";
       }
       leaf softwire-deleted {
         type uint32;
         description "Number of Softwires Deleted";
       }
       leaf flows-created {
         type uint32;
         description "Number of Flows Created";
       }
       leaf flows-deleted {
         type uint32;
         description "Number of Flows Deleted";
       }
       leaf slow-path {
         type uint32;
         description "Slow Path Packets Processed";
       }
       leaf slow-path-reverse-packet {
         type uint32;
         description "Slow Path Packets Processed for EIF/HP";
       }
       leaf fast-path {
         type uint32;
         description "Fast Path Packets Processed";
       }
       leaf fast-path-encap {
         type uint32;
         description "Fast Path Packets Encapsulated";
       }
       leaf softwire-eif-rule-accepts {
         type uint32;
         description "Softwire EIF accepts";
       }
       leaf rule-match-succeeded {
         type uint32;
         description "Rule Match Succeeded";
       }
       leaf rule-match-failed {
         type uint32;
         description "Rule Match Failed";
       }
       leaf ipv6-packets-fragmented {
         type uint32;
         description "IPv6 Packets Fragmented";
       }
       leaf ipv4-client-fragments {
         type uint32;
         description "IPv4 Client Fragments";
       }
       leaf ipv4-server-first-fragments {
         type uint32;
         description "IPv4 Server First Fragments";
       }
       leaf ipv4-server-more-fragments {
         type uint32;
         description "IPv4 Server More Fragments";
       }
       leaf ipv4-server-last-fragments {
         type uint32;
         description "IPv4 Server Last Fragments";
       }
       leaf softwire-icmpv4-sent {
         type uint32;
         description "ICMPv4 Packets sent";
       }
       leaf softwire-icmpv4-err-sent {
         type uint32;
         description "ICMPv4 Error Packets sent";
       }
       leaf softwire-icmpv6-sent {
         type uint32;
         description "ICMPv6 Packets sent";
       }
       leaf softwire-icmpv6-drop {
         type uint32;
         description "Dropped ICMPv6 packets destined to AFTR";
       }
       leaf flow-creation-failed-retry {
         type uint32;
         description "Flow Creation Failed - Retry";
       }
       leaf flow-creation-failed-retry-for-reverse-packet {
         type uint32;
         description "Flow Creation Failed - Retry for EIF/HP";
       }
       leaf slow-path-failed-retry {
         type uint32;
         description "Slow Path Failed - Retry";
       }
       leaf softwire-creation-failed {
         type uint32;
         description "Softwire Creation Failed";
       }
       leaf softwire-creation-failed-for-reverse-packet {
         type uint32;
         description "Softwire Creation Failed for EIF/HP";
       }
       leaf flow-creation-failed {
         type uint32;
         description "Flow Creation Failed";
       }
       leaf flow-creation-failed-for-reverse-packet {
         type uint32;
         description "Flow Creation Failed for EIF/HP";
       }
       leaf slow-path-failed {
         type uint32;
         description "Slow Path Failed";
       }
       leaf packet-not-ipv4-in-ipv6 {
         type uint32;
         description "Packet not IPv4 in IPv6";
       }
       leaf ipv6-fragmentation-error {
         type uint32;
         description "IPv6 Fragmentation Error";
       }
       leaf softwire-creation-failed-ipv6-next-header-offset {
         type uint32;
         description "Softwire Creation Failed - IPv6 Next Header Offset";
       }
       leaf decap-failed-packet-not-ipv4 {
         type uint32;
         description "Decapsulated Packet not IPv4";
       }
       leaf decap-failed-ipv6-next-header-offset {
         type uint32;
         description "Decap Failed - IPv6 Next Header Offset";
       }
       leaf decap-failed-ipv4-l3-integrity {
         type uint32;
         description "Decap Failed - IPv4 L3 Integrity";
       }
       leaf decap-failed-ipv4-l4-integrity {
         type uint32;
         description "Decap Failed - IPv4 L4 Integrity";
       }
       leaf decap-failed-ipv6-frag-no-mem {
         type uint32;
         description "Decap Failed - IPv4 Frag Out of Memory";
       }
       leaf no-softwire-id {
         type uint32;
         description "No Softwire ID";
       }
       leaf no-flow-extension {
         type uint32;
         description "No Flow Extension";
       }
       leaf flow-limit-exceeded {
         type uint32;
         description "Flow Limit Exceeded";
       }
       leaf session-limit-exceeded {
         type uint32;
         description "Session Limit Exceeded";
       }
       leaf slow-path-gratuitous-packet {
         type uint32;
         description "Slow Path for Gratuitous Packet";
       }
       leaf packet-not-ipv6-in-ipv4 {
         type uint32;
         description "Packet not IPv6 in IPv4";
       }
       leaf decap-packet-not-ipv6 {
         type uint32;
         description "Decapsulated Packet not IPv6";
       }
       leaf no-space-for-outer-header {
         type uint32;
         description "Encapsulation Failed - No space for Outer Header";
       }
       leaf icmpv4-dropped-packets {
         type uint32;
         description "ICMPv4 Dropped Packets";
       }
     }
     container service-softwire-6rd-statistics-entry {
       leaf srv-pic-name {
         type string;
         description "Services PIC Name";
       }
       leaf softwire-created {
         type uint32;
         description "Number of Softwires Created";
       }
       leaf softwire-deleted {
         type uint32;
         description "Number of Softwires Deleted";
       }
       leaf flows-created {
         type uint32;
         description "Number of Flows Created";
       }
       leaf flows-deleted {
         type uint32;
         description "Number of Flows Deleted";
       }
       leaf slow-path {
         type uint32;
         description "Slow Path Packets Processed";
       }
       leaf slow-path-gratuitous-packet {
         type uint32;
         description "Slow Path for Gratuitous Packet";
       }
       leaf fast-path {
         type uint32;
         description "Fast Path Packets Processed";
       }
       leaf fast-path-encap {
         type uint32;
         description "Fast Path Packets Encapsulated";
       }
       leaf rule-match-succeeded {
         type uint32;
         description "Rule Match Succeeded";
       }
       leaf rule-match-failed {
         type uint32;
         description "Rule Match Failed";
       }
       leaf flow-creation-failed-retry {
         type uint32;
         description "Flow Creation Failed - Retry";
       }
       leaf slow-path-failed-retry {
         type uint32;
         description "Slow Path Failed - Retry";
       }
       leaf softwire-creation-failed {
         type uint32;
         description "Softwire Creation Failed";
       }
       leaf flow-creation-failed {
         type uint32;
         description "Flow Creation Failed";
       }
       leaf slow-path-failed {
         type uint32;
         description "Slow Path Failed";
       }
       leaf packet-not-ipv6-in-ipv4 {
         type uint32;
         description "Packet not IPv6 in IPv4";
       }
       leaf softwire-creation-failed-ipv6-next-header-offset {
         type uint32;
         description "Softwire Creation Failed - IPv6 Next Header Offset";
       }
       leaf decap-packet-not-ipv6 {
         type uint32;
         description "Decapsulated Packet not IPv6";
       }
       leaf no-space-for-outer-header {
         type uint32;
         description "Encapsulation Failed - No space for Outer Header";
       }
       leaf no-softwire-id {
         type uint32;
         description "No Softwire ID";
       }
       leaf no-flow-extension {
         type uint32;
         description "No Flow Extension";
       }
       leaf icmpv4-dropped-packets {
         type uint32;
         description "ICMPv4 Dropped Packets";
       }
     }
     container msp-softwire-plugin-statistics-entry {
       leaf svcs-interface-name {
         type string;
         description "Name of the services interface";
       }
       leaf sw-total-session-interest {
         type int32;
         description "Total Session Interest events";
       }
       leaf sw-total-session-destroy {
         type int32;
         description "Total Session Destroy events";
       }
       leaf sw-total-public-events {
         type int32;
         description "Total Public request events";
       }
       leaf sw-session-accepts {
         type int32;
         description "Total Session Accepts";
       }
       leaf sw-session-discards {
         type int32;
         description "Total Session Discards";
       }
       leaf sw-session-ignores {
         type int32;
         description "Total Session Ignores";
       }
       leaf sw-sess-ext-alloc-failures {
         type int32;
         description "Total Softwire session extension memory alloc failures";
       }
       leaf sw-sess-ext-set-failures {
         type int32;
         description "Total Softwire session extension set failures";
       }
       leaf sw-session-created {
         type int32;
         description "Total Softwire Sessions created";
       }
       leaf sw-session-deleted {
         type int32;
         description "Total Softwire Sessions deleted";
       }
       leaf sw-session-create-for-reverse-pkts {
         type int32;
         description "Total Softwire sessions created for reverse V4 sessions";
       }
       leaf sw-session-create-failures-for-reverse-pkts {
         type int32;
         description "Total Softwire session creation failures for reverse V4 sessions";
       }
       leaf sw-rule-match-success {
         type int32;
         description "Softwire rule match success";
       }
       leaf sw-rule-match-failures {
         type int32;
         description "Softwire rule match failures";
       }
       leaf sw-session-limit-exceeded {
         type int32;
         description "Total Session limit exceeded errors";
       }
       leaf sw-ipv6-packets-fragmented {
         type int32;
         description "IPv6 Packets Fragmented";
       }
       leaf sw-total-pkts-processed {
         type int32;
         description "Total Packets processed by Softwire";
       }
       leaf sw-encap-pkts {
         type int32;
         description "Total Packets encapsulated";
       }
       leaf sw-decap-pkts {
         type int32;
         description "Total Packets decapsulated";
       }
       leaf sw-encap-errors {
         type int32;
         description "Packet encapsulation errors";
       }
       leaf sw-decap-errors {
         type int32;
         description "Packet decapsulation errors";
       }
       leaf sw-encap-reinject-errors {
         type int32;
         description "Encapsulated packet re-inject failed errors";
       }
       leaf sw-decap-reinject-errors {
         type int32;
         description "Decapsulated packet re-inject failed errors";
       }
       leaf sw-dslite-icmpv4-echo-reply-sent {
         type int32;
         description "Total ICMPv4 ECHO reply messages sent";
       }
       leaf sw-dslite-icmpv4-ttl-exceed-msg-sent {
         type int32;
         description "Total ICMPv4 TTL exceeded messages sent";
       }
       leaf sw-dslite-icmpv6-echo-req-recvd {
         type int32;
         description "Total ICMPv6 ECHO request received to AFTR";
       }
       leaf sw-dslite-icmpv6-echo-reply-sent {
         type int32;
         description "Total ICMPv6 ECHO reply sent from AFTR";
       }
       leaf sw-dslite-icmpv6-echo-req-process-err {
         type int32;
         description "Total ICMPv6 ECHO requests to AFTR process failures";
       }
       leaf sw-dslite-pkt-to-aftrv6-drop {
         type int32;
         description "Total untunnelled packets destined to AFTR V6 dropped";
       }
       leaf sw-untunnelled-pkts {
         type int32;
         description "Total Untunnelled packets ignored by Softwire";
       }
       leaf sw-policy-add-errors {
         type int32;
         description "Softwire policy addition failures";
       }
       leaf sw-policy-del-errors {
         type int32;
         description "Softwire policy deletion failures";
       }
       leaf sw-policy-mem-alloc-failures {
         type int32;
         description "Memory allocation failed for Softwire policy";
       }
       leaf sw-dslite-icmpv4-ttl-exceed-process-errors {
         type int32;
         description "ICMPv4 TTL exceeded message processing failures";
       }
     }
   }
   grouping inline-service-sw-statistics-information-block {
     container inline-sw-6rd-statistics-entry {
       leaf srv-pic-name {
         type string;
         description "Services PIC Name";
       }
       leaf sc-icmpv4-echo-reqs {
         type uint64;
         description "ICMPv4 echo requests to softwire concentrator";
       }
       leaf sc-icmpv4-echo-resp {
         type uint64;
         description "ICMPv4 echo responses from softwire concentrator";
       }
       leaf sc-icmpv4-drops {
         type uint64;
         description "Dropped ICMPv4 messages destined to softwire concentrator";
       }
       leaf sc-trace-rcvd {
         type uint64;
         description "Trace route UDP packets to softwire concentrator";
       }
       leaf sc-icmpv4-port-unreachable-errors {
         type uint64;
         description "ICMPv4 Port unreachable errors sent from softwire concentrator";
       }
       leaf sc-otherv4-drops {
         type uint64;
         description "Other IPv4 packet drops destined to softwire concentrator";
       }
       leaf v6rd-decap-pkts {
         type uint64;
         description "Number of decapped packets";
       }
       leaf v6rd-decap-bytes {
         type uint64;
         description "Number of decapped bytes";
       }
       leaf v6rd-encap-pkts {
         type uint64;
         description "Number of encapped packets";
       }
       leaf v6rd-encap-bytes {
         type uint64;
         description "Number of encapped bytes";
       }
       leaf v6rd-decap-errors {
         type uint64;
         description "Number of packets dropped due to decap errors";
       }
       leaf v6rd-decap-errors-bytes {
         type uint64;
         description "Number of bytes dropped due to decap errors";
       }
       leaf v6rd-decap-frag-errors {
         type uint64;
         description "Number of packets dropped due to decap fragment errors";
       }
       leaf v6rd-decap-frag-errors-bytes {
         type uint64;
         description "Number of bytes dropped due to decap fragment errors";
       }
       leaf v6rd-decap-spoof-errors {
         type uint64;
         description "Number of packets dropped due to decap spoof attacks";
       }
       leaf v6rd-decap-spoof-errors-bytes {
         type uint64;
         description "Number of bytes dropped due to decap spoof attacks";
       }
       leaf v6rd-v4-mtu-errors {
         type uint64;
         description "Number of packets dropped due to IPv4 MTU exceeded errors";
       }
       leaf v6rd-v4-mtu-errors-bytes {
         type uint64;
         description "Number of bytes dropped due to IPv4 MTU exceeded errors";
       }
       leaf sc-ipv4-frag-drops {
         type uint64;
         description "Dropped IP4 fragments destined to softwire concentrator";
       }
       leaf sc-udp-pkts-rcvd {
         type uint64;
         description "UDP packets destined to softwire concentrator";
       }
       leaf sc-icmpv4-errors-sent {
         type uint64;
         description "ICMPv4 errors sent from softwire concentrator";
       }
       leaf sc-icmpv4-errors-send-errors {
         type uint64;
         description "Errors while sending ICMPv4 errors from softwire concentrator";
       }
       leaf sc-out-of-memory-errors {
         type uint64;
         description "Out of memory errors";
       }
       leaf v6rd-encap-errors {
         type uint64;
         description "Number of packets dropped due to encap errors";
       }
       leaf v6rd-inactive-sc-errors {
         type uint64;
         description "Number of packets dropped due to inactive softwire concentrator";
       }
       leaf v6rd-encap-errors-bytes {
         type uint64;
         description "Number of bytes dropped due to encap errors";
       }
       leaf v6rd-inactive-sc-errors-bytes {
         type uint64;
         description "Number of bytes dropped due to inactive softwire concentrator";
       }
       leaf sc-mape-icmpv6-echo-reqs {
         type uint64;
         description "MAPE ICMPv6 echo requests to softwire concentrator";
       }
       leaf sc-mape-icmpv6-echo-resp {
         type uint64;
         description "MAPE ICMPv6 echo responses from softwire concentrator";
       }
       leaf sc-mape-icmpv6-drops {
         type uint64;
         description "MAPE dropped ICMPv6 messages destined to softwire concentrator";
       }
       leaf mape-v6-decap-pkts {
         type uint64;
         description "MAPE Number of decapped packets";
       }
       leaf mape-v6-decap-bytes {
         type uint64;
         description "MAPE Number of decapped bytes";
       }
       leaf mape-icmp-decap-errors {
         type uint64;
         description "MAPE Number of ICMP packets dropped due to decap errors";
       }
       leaf mape-icmp-decap-errors-bytes {
         type uint64;
         description "MAPE Number of ICMP bytes dropped due to decap errors";
       }
       leaf mape-decap-spoof-errors {
         type uint64;
         description "Number of packets dropped due to decap spoof attacks";
       }
       leaf mape-decap-spoof-errors-bytes {
         type uint64;
         description "Number of bytes dropped due to decap spoof attacks";
       }
       leaf mape-v6-reass-pkts {
         type uint64;
         description "MAPE Number of v6 reassembled packets";
       }
       leaf mape-v6-reass-bytes {
         type uint64;
         description "MAPE Number of v6 reassembled bytes";
       }
       leaf mape-v6-frag-errors {
         type uint64;
         description "MAPE Number of v6 fragment packets dropped due to errors";
       }
       leaf mape-v6-frag-errors-bytes {
         type uint64;
         description "MAPE Number of v6 fragment bytes dropped due to errors";
       }
       leaf mape-v6-unsupp-proto {
         type uint64;
         description "MAPE Number of unsupported protocol packets dropped";
       }
       leaf mape-v6-unsupp-proto-bytes {
         type uint64;
         description "MAPE Number of bytes dropped due to decap errors";
       }
       leaf mape-v4-encap-pkts {
         type uint64;
         description "MAPE Number of encapped packets";
       }
       leaf mape-v4-encap-bytes {
         type uint64;
         description "MAPE Number of encapped bytes";
       }
       leaf mape-icmp-encap-errors {
         type uint64;
         description "MAPE Number of ICMP packets dropped due to encap errors";
       }
       leaf mape-icmp-encap-errors-bytes {
         type uint64;
         description "MAPE Number of ICMP bytes dropped due to encap errors";
       }
       leaf mape-v6-tunnel-mtu-errors {
         type uint64;
         description "MAPE Number of packets dropped due to IPv6 MTU exceeded errors";
       }
       leaf mape-v6-tunnel-mtu-errors-bytes {
         type uint64;
         description "MAPE Number of bytes dropped due to v6 mtu exceeded errors";
       }
       leaf mape-v4-reass-pkts {
         type uint64;
         description "MAPE Number of v4 reassembled packets";
       }
       leaf mape-v4-reass-bytes {
         type uint64;
         description "MAPE Number of v4 reassembled bytes";
       }
       leaf mape-v4-frag-errors {
         type uint64;
         description "MAPE Number of v4 fragment packets dropped due to errors";
       }
       leaf mape-v4-frag-errors-bytes {
         type uint64;
         description "MAPE Number of v4 fragment bytes dropped due to errors";
       }
       leaf sc-mape-other-drops {
         type uint64;
         description "MAPE other packet drops destined to softwire concentrator";
       }
       leaf sc-mapt-icmpv64-pass {
         type uint64;
         description "MAPT ICMPv6 paks translated to ICMPv4";
       }
       leaf sc-mapt-icmpv46-pass {
         type uint64;
         description "MAPT ICMPv4 paks translated to ICMPv6";
       }
       leaf sc-mapt-icmpv46-discard {
         type uint64;
         description "MAPT ICMPv4 drops in hostpath";
       }
       leaf sc-mapt-icmpv64-discard {
         type uint64;
         description "MAPT ICMPv6 drops in hostpath";
       }
       leaf sc-mapt-v64-pass-pkts {
         type uint64;
         description "MAPT ipv6 pkts translated to v4";
       }
       leaf sc-mapt-v64-pass-bytes {
         type uint64;
         description "MAPT ipv6 translated to v4";
       }
       leaf sc-mapt-v64-spoof-disc-pkts {
         type uint64;
         description "MAPT ipv6 spoof dropped pkts";
       }
       leaf sc-mapt-v64-spoof-disc-bytes {
         type uint64;
         description "MAPT ipv6 spoof dropped bytes";
       }
       leaf sc-mapt-v64-frag-disc-pkts {
         type uint64;
         description "MAPT ipv6 fragments dropped ";
       }
       leaf sc-mapt-v64-frag-disc-bytes {
         type uint64;
         description "MAPT ipv6 fragments dropped bytes";
       }
       leaf sc-mapt-v64-unsupp-disc-pkts {
         type uint64;
         description "MAPT ipv6 unsupported dropped pkts";
       }
       leaf sc-mapt-v64-unsupp-disc-bytes {
         type uint64;
         description "MAPT ipv6 unsupported dropped bytes";
       }
       leaf sc-mapt-v46-pass-pkts {
         type uint64;
         description "MAPT ipv4 pkts translated to v6";
       }
       leaf sc-mapt-v46-pass-bytes {
         type uint64;
         description "MAPT ipv4 translated to v6";
       }
       leaf sc-mapt-v46-mtuexc-disc-pkts {
         type uint64;
         description "MAPT ipv6 mtu-exceeded dropped pkts";
       }
       leaf sc-mapt-v46-mtuexc-disc-bytes {
         type uint64;
         description "MAPT ipv6 mtu-exceeded dropped bytes";
       }
       leaf sc-mapt-v46-frag-disc-pkts {
         type uint64;
         description "MAPT ipv4 fragments dropped ";
       }
       leaf sc-mapt-v46-frag-disc-bytes {
         type uint64;
         description "MAPT ipv4 fragments dropped bytes";
       }
       leaf sc-mapt-v46-unsupp-disc-pkts {
         type uint64;
         description "MAPT ipv4 unsupported dropped pkts";
       }
       leaf sc-mapt-v46-unsupp-disc-bytes {
         type uint64;
         description "MAPT ipv4 unsupported dropped bytes";
       }
     }
     container inline-sw-mape-statistics-entry {
       leaf srv-pic-name {
         type string;
         description "Services PIC Name";
       }
       leaf sc-mape-icmpv6-echo-reqs {
         type uint64;
         description "MAPE ICMPv6 echo requests to softwire concentrator";
       }
       leaf sc-mape-icmpv6-echo-resp {
         type uint64;
         description "MAPE ICMPv6 echo responses from softwire concentrator";
       }
       leaf sc-mape-icmpv6-drops {
         type uint64;
         description "MAPE dropped ICMPv6 messages destined to softwire concentrator";
       }
       leaf mape-v6-decap-pkts {
         type uint64;
         description "MAPE Number of decapped packets";
       }
       leaf mape-v6-decap-bytes {
         type uint64;
         description "MAPE Number of decapped bytes";
       }
       leaf mape-icmp-decap-errors {
         type uint64;
         description "MAPE Number of ICMP packets dropped due to decap errors";
       }
       leaf mape-icmp-decap-errors-bytes {
         type uint64;
         description "MAPE Number of ICMP bytes dropped due to decap errors";
       }
       leaf mape-decap-spoof-errors {
         type uint64;
         description "Number of packets dropped due to decap spoof attacks";
       }
       leaf mape-decap-spoof-errors-bytes {
         type uint64;
         description "Number of bytes dropped due to decap spoof attacks";
       }
       leaf mape-v6-reass-pkts {
         type uint64;
         description "MAPE Number of v6 reassembled packets";
       }
       leaf mape-v6-reass-bytes {
         type uint64;
         description "MAPE Number of v6 reassembled bytes";
       }
       leaf mape-v6-frag-errors {
         type uint64;
         description "MAPE Number of v6 fragment packets dropped due to errors";
       }
       leaf mape-v6-frag-errors-bytes {
         type uint64;
         description "MAPE Number of v6 fragment bytes dropped due to errors";
       }
       leaf mape-v6-unsupp-proto {
         type uint64;
         description "MAPE Number of unsupported protocol packets dropped";
       }
       leaf mape-v6-unsupp-proto-bytes {
         type uint64;
         description "MAPE Number of bytes dropped due to decap errors";
       }
       leaf mape-v4-encap-pkts {
         type uint64;
         description "MAPE Number of encapped packets";
       }
       leaf mape-v4-encap-bytes {
         type uint64;
         description "MAPE Number of encapped bytes";
       }
       leaf mape-icmp-encap-errors {
         type uint64;
         description "MAPE Number of ICMP packets dropped due to encap errors";
       }
       leaf mape-icmp-encap-errors-bytes {
         type uint64;
         description "MAPE Number of ICMP bytes dropped due to encap errors";
       }
       leaf mape-v6-tunnel-mtu-errors {
         type uint64;
         description "MAPE Number of packets dropped due to IPv6 MTU exceeded errors";
       }
       leaf mape-v6-tunnel-mtu-errors-bytes {
         type uint64;
         description "MAPE Number of bytes dropped due to v6 mtu exceeded errors";
       }
       leaf mape-v4-reass-pkts {
         type uint64;
         description "MAPE Number of v4 reassembled packets";
       }
       leaf mape-v4-reass-bytes {
         type uint64;
         description "MAPE Number of v4 reassembled bytes";
       }
       leaf mape-v4-frag-errors {
         type uint64;
         description "MAPE Number of v4 fragment packets dropped due to errors";
       }
       leaf mape-v4-frag-errors-bytes {
         type uint64;
         description "MAPE Number of v4 fragment bytes dropped due to errors";
       }
       leaf sc-mape-other-drops {
         type uint64;
         description "MAPE other packet drops destined to softwire concentrator";
       }
     }
     container inline-sw-mapt-statistics-entry {
       leaf srv-pic-name {
         type string;
         description "Services PIC Name";
       }
       leaf sc-mapt-icmpv64-pass {
         type uint64;
         description "MAPT ICMPv6 paks translated to ICMPv4";
       }
       leaf sc-mapt-icmpv46-pass {
         type uint64;
         description "MAPT ICMPv4 paks translated to ICMPv6";
       }
       leaf sc-mapt-icmpv46-discard {
         type uint64;
         description "MAPT ICMPv4 drops in hostpath";
       }
       leaf sc-mapt-icmpv64-discard {
         type uint64;
         description "MAPT ICMPv6 drops in hostpath";
       }
       leaf sc-mapt-v64-pass-pkts {
         type uint64;
         description "MAPT ipv6 pkts translated to v4";
       }
       leaf sc-mapt-v64-pass-bytes {
         type uint64;
         description "MAPT ipv6 translated to v4";
       }
       leaf sc-mapt-v64-spoof-disc-pkts {
         type uint64;
         description "MAPT ipv6 spoof dropped pkts";
       }
       leaf sc-mapt-v64-spoof-disc-bytes {
         type uint64;
         description "MAPT ipv6 spoof dropped bytes";
       }
       leaf sc-mapt-v64-frag-disc-pkts {
         type uint64;
         description "MAPT ipv6 fragments dropped ";
       }
       leaf sc-mapt-v64-frag-disc-bytes {
         type uint64;
         description "MAPT ipv6 fragments dropped bytes";
       }
       leaf sc-mapt-v64-unsupp-disc-pkts {
         type uint64;
         description "MAPT ipv6 unsupported dropped pkts";
       }
       leaf sc-mapt-v64-unsupp-disc-bytes {
         type uint64;
         description "MAPT ipv6 unsupported dropped bytes";
       }
       leaf sc-mapt-v46-pass-pkts {
         type uint64;
         description "MAPT ipv4 pkts translated to v6";
       }
       leaf sc-mapt-v46-pass-bytes {
         type uint64;
         description "MAPT ipv4 translated to v6";
       }
       leaf sc-mapt-v46-mtuexc-disc-pkts {
         type uint64;
         description "MAPT ipv6 mtu-exceeded dropped pkts";
       }
       leaf sc-mapt-v46-mtuexc-disc-bytes {
         type uint64;
         description "MAPT ipv6 mtu-exceeded dropped bytes";
       }
       leaf sc-mapt-v46-frag-disc-pkts {
         type uint64;
         description "MAPT ipv4 fragments dropped ";
       }
       leaf sc-mapt-v46-frag-disc-bytes {
         type uint64;
         description "MAPT ipv4 fragments dropped bytes";
       }
       leaf sc-mapt-v46-unsupp-disc-pkts {
         type uint64;
         description "MAPT ipv4 unsupported dropped pkts";
       }
       leaf sc-mapt-v46-unsupp-disc-bytes {
         type uint64;
         description "MAPT ipv4 unsupported dropped bytes";
       }
     }
   }
   grouping inline-nat-statistics-information-block {
     container inline-nat-statistics-entry {
       leaf srv-pic-name {
         type string;
         description "Services PIC Name";
       }
       leaf si-nat-ipv4-received {
         type uint64;
         description "Number of IPv4 packets received";
       }
       leaf si-nat-icmpv4-errors-pass {
         type uint64;
         description "Number of ICMPv4 error packets pass through";
       }
       leaf si-nat-icmpv4-errors-local {
         type uint64;
         description "Number of ICMPv4 error packets locally generated";
       }
       leaf si-nat-ipv4-dropped {
         type uint64;
         description "Number of dropped IPv4 packets";
       }
       leaf si-nat-ipv6-received {
         type uint64;
         description "Number of IPv6 packets received";
       }
       leaf si-nat-icmpv6-errors-pass-nptv6 {
         type uint64;
         description "Number of ICMPv6 error packets pass through for NPTv6";
       }
       leaf si-nat-icmpv6-errors-local-nptv6 {
         type uint64;
         description "Number of ICMPv6 error packets locally generated for NPTv6";
       }
       leaf si-nat-ipv6-dropped {
         type uint64;
         description "Number of dropped IPv6 packets";
       }
       leaf si-nat-ipv4-pkts {
         type uint64;
         description "Number of NATed IPv4 packets";
       }
       leaf si-nat-ipv4-bytes {
         type uint64;
         description "Number of NATed IPv4 bytes";
       }
       leaf si-denat-ipv4-pkts {
         type uint64;
         description "Number of deNATed IPv4 packets";
       }
       leaf si-denat-ipv4-bytes {
         type uint64;
         description "Number of deNATed IPv4 bytes";
       }
       leaf si-ipv4-error-pkts {
         type uint64;
         description "Number of IPv4 error packets";
       }
       leaf si-ipv4-error-bytes {
         type uint64;
         description "Number of IPv4 error bytes";
       }
       leaf si-ipv4-skipped-pkts {
         type uint64;
         description "Number of IPv4 skipped packets";
       }
       leaf si-ipv4-skipped-bytes {
         type uint64;
         description "Number of IPv4 skipped bytes";
       }
       leaf si-nat-ipv6-pkts {
         type uint64;
         description "Number of NATed IPv6 packets";
       }
       leaf si-nat-ipv6-bytes {
         type uint64;
         description "Number of NATed IPv6 bytes";
       }
       leaf si-denat-ipv6-pkts {
         type uint64;
         description "Number of deNATed IPv6 packets";
       }
       leaf si-denat-ipv6-bytes {
         type uint64;
         description "Number of deNATed IPv6 bytes";
       }
       leaf si-ipv6-error-pkts {
         type uint64;
         description "Number of IPv6 error packets";
       }
       leaf si-ipv6-error-bytes {
         type uint64;
         description "Number of IPv6 error bytes";
       }
       leaf si-ipv6-skipped-pkts {
         type uint64;
         description "Number of IPv6 skipped packets";
       }
       leaf si-ipv6-skipped-bytes {
         type uint64;
         description "Number of IPv6 skipped bytes";
       }
     }
   }
   grouping inline-ip-reass-statistics-information-block {
     container inline-ip-reass-statistics-entry {
       leaf si-ip-reass-total-fragments-rcvd {
         type uint32;
         description "Total number of fragments received";
       }
       leaf si-ip-reass-first-fragments-rcvd {
         type uint32;
         description "Number of first fragments received";
       }
       leaf si-ip-reass-inter-fragments-rcvd {
         type uint32;
         description "Number of intermediate fragments received";
       }
       leaf si-ip-reass-last-fragments-rcvd {
         type uint32;
         description "Number of last fragments received";
       }
       leaf si-ip-reass-packets-reassembled {
         type uint32;
         description "Total number of packets reassembled";
       }
       leaf si-ip-reass-full-reassem-success {
         type uint32;
         description "Total number of packets fully reassembled";
       }
       leaf si-ip-reass-partial-reassem-success {
         type uint32;
         description "Number of packets partially reassembled";
       }
       leaf si-ip-reass-packets-pending-reassembly {
         type uint32;
         description "Total number of packets pending reassembly";
       }
       leaf si-ip-reass-total-dropped-reasons {
         type uint32;
         description "Total number of various fragment-drop reasons";
       }
       leaf si-ip-reass-no-buffers {
         type uint32;
         description "No buffers available";
       }
       leaf si-ip-reass-exceeded-max-frag-supported {
         type uint32;
         description "Exceeded maximum fragments received for the packet";
       }
       leaf si-ip-reass-exceeded-packet-length {
         type uint32;
         description "Exceeded length for the packet";
       }
       leaf si-ip-reass-record-insert-error {
         type uint32;
         description "Record insert error";
       }
       leaf si-ip-reass-record-in-use {
         type uint32;
         description "Record entry marked for delete or undergoing reassembly";
       }
       leaf si-ip-reass-dupl-first-frag {
         type uint32;
         description "Duplicate first fragment received";
       }
       leaf si-ip-reass-dupl-last-frag {
         type uint32;
         description "Duplicate last fragment received";
       }
       leaf si-ip-reass-miss-first-frag {
         type uint32;
         description "Missing first fragment";
       }
       leaf si-ip-reass-total-reass-error-reasons {
         type uint32;
         description "Total number of errors incurred during reassembly";
       }
       leaf si-ip-reass-fragment-not-found {
         type uint32;
         description "Packet entries for which fragments were not found";
       }
       leaf si-ip-reass-asic-errors {
         type uint32;
         description "Asic errors like mq write or read errors";
       }
       leaf si-ip-reass-aged-out-packets {
         type uint32;
         description "Total number of aged out packets";
       }
       leaf si-ip-reass-packets-reassembled-fragcnt {
         type uint32;
         description "Total number of fragments successfully reassembled to form packets";
       }
       leaf si-ip-reass-total-dropped-errors-fragcnt {
         type uint32;
         description "Total number of fragments dropped due to various fragment-drop reasons and reassembly error reasons";
       }
       leaf si-ip-reass-no-buffers-fragcnt {
         type uint32;
         description "Fragments dropped for no buffers availability";
       }
       leaf si-ip-reass-exceeded-max-frag-supported-fragcnt {
         type uint32;
         description "Fragments dropped for exceeding maximum fragments received for the packet";
       }
       leaf si-ip-reass-exceeded-packet-length-fragcnt {
         type uint32;
         description "Fragments dropped for exceeding length for the packet";
       }
       leaf si-ip-reass-record-insert-error-fragcnt {
         type uint32;
         description "Fragments dropped for record insert errors";
       }
       leaf si-ip-reass-record-in-use-fragcnt {
         type uint32;
         description "Fragments dropped for record entry marked for delete or undergoing reassembly";
       }
       leaf si-ip-reass-dupl-first-frag-fragcnt {
         type uint32;
         description "Fragments dropped for duplicate first fragment received";
       }
       leaf si-ip-reass-dupl-last-frag-fragcnt {
         type uint32;
         description "Fragments dropped for duplicate last fragment received";
       }
       leaf si-ip-reass-miss-first-frag-fragcnt {
         type uint32;
         description "Fragments dropped for missing first fragment";
       }
       leaf si-ip-reass-fragment-not-found-fragcnt {
         type uint32;
         description "Fragments dropped due to entries for which fragments were not found";
       }
       leaf si-ip-reass-asic-errors-fragcnt {
         type uint32;
         description "Fragments dropped due to asic errors";
       }
       leaf si-ip-reass-aged-out-packets-fragcnt {
         type uint32;
         description "Fragments dropped due to aged out packets";
       }
       leaf si-ip-reass-total-fragments-rcvd-rate {
         type uint32;
         description "Current rate of total fragments received";
       }
       leaf si-ip-reass-first-fragments-rcvd-rate {
         type uint32;
         description "Current rate of first fragments received";
       }
       leaf si-ip-reass-inter-fragments-rcvd-rate {
         type uint32;
         description "Current rate of intermediate fragments received";
       }
       leaf si-ip-reass-last-fragments-rcvd-rate {
         type uint32;
         description "Current rate of last fragments received";
       }
       leaf si-ip-reass-packets-reassembled-rate {
         type uint32;
         description "Current rate of packets reassembled";
       }
       leaf si-ip-reass-full-reassem-success-rate {
         type uint32;
         description "Current rate of packets fully reassembled";
       }
       leaf si-ip-reass-partial-reassem-success-rate {
         type uint32;
         description "Current rate of packets partially reassembled";
       }
       leaf si-ip-reass-packets-pending-reassembly-rate {
         type uint32;
         description "Current rate of packets pending reassembly";
       }
       leaf si-ip-reass-total-dropped-reasons-rate {
         type uint32;
         description "Current rate of various fragment-drop reasons";
       }
       leaf si-ip-reass-no-buffers-rate {
         type uint32;
         description "Current rate of fragment-drop reason for no buffers availability";
       }
       leaf si-ip-reass-exceeded-max-frag-supported-rate {
         type uint32;
         description "Current rate of fragment-drop reason for exceeding maximum fragments received for the packet";
       }
       leaf si-ip-reass-exceeded-packet-length-rate {
         type uint32;
         description "Current rate of fragment-drop reason for exceeding length for the packet";
       }
       leaf si-ip-reass-record-insert-error-rate {
         type uint32;
         description "Current rate fragment-drop reason for record insert errors";
       }
       leaf si-ip-reass-record-in-use-rate {
         type uint32;
         description "Current rate of fragment-drop reason for record entry marked for delete or undergoing reassembly";
       }
       leaf si-ip-reass-dupl-first-frag-rate {
         type uint32;
         description "Current rate of fragment-drop reason for duplicate first fragment received";
       }
       leaf si-ip-reass-dupl-last-frag-rate {
         type uint32;
         description "Current rate of fragment-drop reason for duplicate last fragment received";
       }
       leaf si-ip-reass-miss-first-frag-rate {
         type uint32;
         description "Current rate of fragment-drop reason for missing first fragment";
       }
       leaf si-ip-reass-total-reass-error-reasons-rate {
         type uint32;
         description "Current rate of errors incurred during reassembly";
       }
       leaf si-ip-reass-fragment-not-found-rate {
         type uint32;
         description "Current rate of packet entry errors for which fragments were not found";
       }
       leaf si-ip-reass-asic-errors-rate {
         type uint32;
         description "Current rate of asic errors";
       }
       leaf si-ip-reass-aged-out-packets-rate {
         type uint32;
         description "Current rate of aged out packets";
       }
       leaf si-ip-reass-packets-reassembled-fragcnt-rate {
         type uint32;
         description "Current rate of fragments successfully reassembled to form packets";
       }
       leaf si-ip-reass-total-dropped-errors-fragcnt-rate {
         type uint32;
         description "Current rate of fragments dropped due to various fragment-drop reasons and reassembly error reasons";
       }
       leaf si-ip-reass-no-buffers-fragcnt-rate {
         type uint32;
         description "Current rate of fragments dropped for no buffers availability";
       }
       leaf si-ip-reass-exceeded-max-frag-supported-fragcnt-rate {
         type uint32;
         description "Current rate of fragments dropped for exceeding maximum fragments received for the packet";
       }
       leaf si-ip-reass-exceeded-packet-length-fragcnt-rate {
         type uint32;
         description "Current rate of fragments dropped for exceeding length for the packet";
       }
       leaf si-ip-reass-record-insert-error-fragcnt-rate {
         type uint32;
         description "Current rate of fragments dropped for record insert errors";
       }
       leaf si-ip-reass-record-in-use-fragcnt-rate {
         type uint32;
         description "Current rate of fragments dropped for record entry marked for delete or undergoing reassembly";
       }
       leaf si-ip-reass-dupl-first-frag-fragcnt-rate {
         type uint32;
         description "Current rate of fragments dropped for duplicate first fragment received";
       }
       leaf si-ip-reass-dupl-last-frag-fragcnt-rate {
         type uint32;
         description "Current rate of fragments dropped for duplicate last fragment received";
       }
       leaf si-ip-reass-miss-first-frag-fragcnt-rate {
         type uint32;
         description "Current rate of fragments dropped for missing first fragment";
       }
       leaf si-ip-reass-fragment-not-found-fragcnt-rate {
         type uint32;
         description "Current rate of fragments dropped due to entries for which fragments were not found";
       }
       leaf si-ip-reass-asic-errors-fragcnt-rate {
         type uint32;
         description "Current rate of fragments dropped due to asic errors";
       }
       leaf si-ip-reass-aged-out-packets-fragcnt-rate {
         type uint32;
         description "Current rate of fragments dropped due to aged out packets";
       }
       leaf si-ip-reass-fpc-slot {
         type uint32;
         description "FPC slot";
       }
       leaf si-ip-reass-pfe-slot {
         type uint32;
         description "PFE slot";
       }
       leaf si-ip-reass-header {
         type string;
         description "Part of the header";
       }
       leaf si-ip-reass-intf {
         type string;
         description "SI Interface name";
       }
     }
   }
   grouping inline-ipv6-reass-statistics-information-block {
     container inline-ip-reass-statistics-entry {
       leaf si-ip-reass-total-fragments-rcvd {
         type uint32;
         description "Total number of fragments received";
       }
       leaf si-ip-reass-first-fragments-rcvd {
         type uint32;
         description "Number of first fragments received";
       }
       leaf si-ip-reass-inter-fragments-rcvd {
         type uint32;
         description "Number of intermediate fragments received";
       }
       leaf si-ip-reass-last-fragments-rcvd {
         type uint32;
         description "Number of last fragments received";
       }
       leaf si-ip-reass-packets-reassembled {
         type uint32;
         description "Total number of packets reassembled";
       }
       leaf si-ip-reass-full-reassem-success {
         type uint32;
         description "Total number of packets fully reassembled";
       }
       leaf si-ip-reass-partial-reassem-success {
         type uint32;
         description "Number of packets partially reassembled";
       }
       leaf si-ip-reass-packets-pending-reassembly {
         type uint32;
         description "Total number of packets pending reassembly";
       }
       leaf si-ip-reass-total-dropped-reasons {
         type uint32;
         description "Total number of various fragment-drop reasons";
       }
       leaf si-ip-reass-no-buffers {
         type uint32;
         description "No buffers available";
       }
       leaf si-ip-reass-exceeded-max-frag-supported {
         type uint32;
         description "Exceeded maximum fragments received for the packet";
       }
       leaf si-ip-reass-exceeded-packet-length {
         type uint32;
         description "Exceeded length for the packet";
       }
       leaf si-ip-reass-record-insert-error {
         type uint32;
         description "Record insert error";
       }
       leaf si-ip-reass-record-in-use {
         type uint32;
         description "Record entry marked for delete or undergoing reassembly";
       }
       leaf si-ip-reass-dupl-first-frag {
         type uint32;
         description "Duplicate first fragment received";
       }
       leaf si-ip-reass-dupl-last-frag {
         type uint32;
         description "Duplicate last fragment received";
       }
       leaf si-ip-reass-miss-first-frag {
         type uint32;
         description "Missing first fragment";
       }
       leaf si-ip-reass-total-reass-error-reasons {
         type uint32;
         description "Total number of errors incurred during reassembly";
       }
       leaf si-ip-reass-fragment-not-found {
         type uint32;
         description "Packet entries for which fragments were not found";
       }
       leaf si-ip-reass-asic-errors {
         type uint32;
         description "Asic errors like mq write or read errors";
       }
       leaf si-ip-reass-aged-out-packets {
         type uint32;
         description "Total number of aged out packets";
       }
       leaf si-ip-reass-packets-reassembled-fragcnt {
         type uint32;
         description "Total number of fragments successfully reassembled to form packets";
       }
       leaf si-ip-reass-total-dropped-errors-fragcnt {
         type uint32;
         description "Total number of fragments dropped due to various fragment-drop reasons and reassembly error reasons";
       }
       leaf si-ip-reass-no-buffers-fragcnt {
         type uint32;
         description "Fragments dropped for no buffers availability";
       }
       leaf si-ip-reass-exceeded-max-frag-supported-fragcnt {
         type uint32;
         description "Fragments dropped for exceeding maximum fragments received for the packet";
       }
       leaf si-ip-reass-exceeded-packet-length-fragcnt {
         type uint32;
         description "Fragments dropped for exceeding length for the packet";
       }
       leaf si-ip-reass-record-insert-error-fragcnt {
         type uint32;
         description "Fragments dropped for record insert errors";
       }
       leaf si-ip-reass-record-in-use-fragcnt {
         type uint32;
         description "Fragments dropped for record entry marked for delete or undergoing reassembly";
       }
       leaf si-ip-reass-dupl-first-frag-fragcnt {
         type uint32;
         description "Fragments dropped for duplicate first fragment received";
       }
       leaf si-ip-reass-dupl-last-frag-fragcnt {
         type uint32;
         description "Fragments dropped for duplicate last fragment received";
       }
       leaf si-ip-reass-miss-first-frag-fragcnt {
         type uint32;
         description "Fragments dropped for missing first fragment";
       }
       leaf si-ip-reass-fragment-not-found-fragcnt {
         type uint32;
         description "Fragments dropped due to entries for which fragments were not found";
       }
       leaf si-ip-reass-asic-errors-fragcnt {
         type uint32;
         description "Fragments dropped due to asic errors";
       }
       leaf si-ip-reass-aged-out-packets-fragcnt {
         type uint32;
         description "Fragments dropped due to aged out packets";
       }
       leaf si-ip-reass-total-fragments-rcvd-rate {
         type uint32;
         description "Current rate of total fragments received";
       }
       leaf si-ip-reass-first-fragments-rcvd-rate {
         type uint32;
         description "Current rate of first fragments received";
       }
       leaf si-ip-reass-inter-fragments-rcvd-rate {
         type uint32;
         description "Current rate of intermediate fragments received";
       }
       leaf si-ip-reass-last-fragments-rcvd-rate {
         type uint32;
         description "Current rate of last fragments received";
       }
       leaf si-ip-reass-packets-reassembled-rate {
         type uint32;
         description "Current rate of packets reassembled";
       }
       leaf si-ip-reass-full-reassem-success-rate {
         type uint32;
         description "Current rate of packets fully reassembled";
       }
       leaf si-ip-reass-partial-reassem-success-rate {
         type uint32;
         description "Current rate of packets partially reassembled";
       }
       leaf si-ip-reass-packets-pending-reassembly-rate {
         type uint32;
         description "Current rate of packets pending reassembly";
       }
       leaf si-ip-reass-total-dropped-reasons-rate {
         type uint32;
         description "Current rate of various fragment-drop reasons";
       }
       leaf si-ip-reass-no-buffers-rate {
         type uint32;
         description "Current rate of fragment-drop reason for no buffers availability";
       }
       leaf si-ip-reass-exceeded-max-frag-supported-rate {
         type uint32;
         description "Current rate of fragment-drop reason for exceeding maximum fragments received for the packet";
       }
       leaf si-ip-reass-exceeded-packet-length-rate {
         type uint32;
         description "Current rate of fragment-drop reason for exceeding length for the packet";
       }
       leaf si-ip-reass-record-insert-error-rate {
         type uint32;
         description "Current rate fragment-drop reason for record insert errors";
       }
       leaf si-ip-reass-record-in-use-rate {
         type uint32;
         description "Current rate of fragment-drop reason for record entry marked for delete or undergoing reassembly";
       }
       leaf si-ip-reass-dupl-first-frag-rate {
         type uint32;
         description "Current rate of fragment-drop reason for duplicate first fragment received";
       }
       leaf si-ip-reass-dupl-last-frag-rate {
         type uint32;
         description "Current rate of fragment-drop reason for duplicate last fragment received";
       }
       leaf si-ip-reass-miss-first-frag-rate {
         type uint32;
         description "Current rate of fragment-drop reason for missing first fragment";
       }
       leaf si-ip-reass-total-reass-error-reasons-rate {
         type uint32;
         description "Current rate of errors incurred during reassembly";
       }
       leaf si-ip-reass-fragment-not-found-rate {
         type uint32;
         description "Current rate of packet entry errors for which fragments were not found";
       }
       leaf si-ip-reass-asic-errors-rate {
         type uint32;
         description "Current rate of asic errors";
       }
       leaf si-ip-reass-aged-out-packets-rate {
         type uint32;
         description "Current rate of aged out packets";
       }
       leaf si-ip-reass-packets-reassembled-fragcnt-rate {
         type uint32;
         description "Current rate of fragments successfully reassembled to form packets";
       }
       leaf si-ip-reass-total-dropped-errors-fragcnt-rate {
         type uint32;
         description "Current rate of fragments dropped due to various fragment-drop reasons and reassembly error reasons";
       }
       leaf si-ip-reass-no-buffers-fragcnt-rate {
         type uint32;
         description "Current rate of fragments dropped for no buffers availability";
       }
       leaf si-ip-reass-exceeded-max-frag-supported-fragcnt-rate {
         type uint32;
         description "Current rate of fragments dropped for exceeding maximum fragments received for the packet";
       }
       leaf si-ip-reass-exceeded-packet-length-fragcnt-rate {
         type uint32;
         description "Current rate of fragments dropped for exceeding length for the packet";
       }
       leaf si-ip-reass-record-insert-error-fragcnt-rate {
         type uint32;
         description "Current rate of fragments dropped for record insert errors";
       }
       leaf si-ip-reass-record-in-use-fragcnt-rate {
         type uint32;
         description "Current rate of fragments dropped for record entry marked for delete or undergoing reassembly";
       }
       leaf si-ip-reass-dupl-first-frag-fragcnt-rate {
         type uint32;
         description "Current rate of fragments dropped for duplicate first fragment received";
       }
       leaf si-ip-reass-dupl-last-frag-fragcnt-rate {
         type uint32;
         description "Current rate of fragments dropped for duplicate last fragment received";
       }
       leaf si-ip-reass-miss-first-frag-fragcnt-rate {
         type uint32;
         description "Current rate of fragments dropped for missing first fragment";
       }
       leaf si-ip-reass-fragment-not-found-fragcnt-rate {
         type uint32;
         description "Current rate of fragments dropped due to entries for which fragments were not found";
       }
       leaf si-ip-reass-asic-errors-fragcnt-rate {
         type uint32;
         description "Current rate of fragments dropped due to asic errors";
       }
       leaf si-ip-reass-aged-out-packets-fragcnt-rate {
         type uint32;
         description "Current rate of fragments dropped due to aged out packets";
       }
       leaf si-ip-reass-fpc-slot {
         type uint32;
         description "FPC slot";
       }
       leaf si-ip-reass-pfe-slot {
         type uint32;
         description "PFE slot";
       }
       leaf si-ip-reass-header {
         type string;
         description "Part of the header";
       }
       leaf si-ip-reass-intf {
         type string;
         description "SI Interface name";
       }
     }
   }
   grouping service-ids-flow-table-information-block {
     container ids-show-summary {
       description "IDS table summary";
       leaf interface-name {
         type string;
         description "Name of the adaptive services interface";
       }
       leaf ids-total-entries {
         type uint64;
         description "Total number of filled entries in IDS table";
       }
       leaf ids-total-failed-insertions {
         type uint64;
         description "Total number of failed IDS table entry insertions";
       }
       leaf ids-total-events {
         type uint64;
         description "Total number of events (closed flows and anomalies)";
       }
     }
     list ids-per-service-set-flow-table {
       description "IDS table sorted by service set";
       leaf interface-name {
         type string;
         description "Name of the adaptive services interface";
       }
       leaf service-set-name {
         type string;
         description "Name of the service set";
       }
       leaf ids-sort-order {
         type string;
         description "IDS table sorting order";
       }
       container ids-flow-table {
         description "IDS table sorted by service set";
         leaf ids-flow-table.heading {
           type string;
           description "IDS table sorted by service set";
         }
         list ids-flow-entry {
           description "IDS terse information";
           leaf ids-flow-source-ip {
             type jt:ipaddr;
             description "Source IP address";
           }
           leaf ids-flow-destination-ip {
             type jt:ipaddr;
             description "Destination IP address";
           }
           leaf ids-flow-time {
             type string;
             description "Time from last event";
           }
           leaf ids-flow-flags {
             type string;
             description "S - SYN cookie enabled, F - Forced entry";
           }
           leaf ids-flow-count {
             type string;
             description "Value depend from request (packet number, bytes, and so on)";
           }
           leaf ids-flow-application {
             type string;
             description "Application name";
           }
           list ids-anomaly-entry {
             leaf ids-anomaly-description {
               type string;
               description "Anomaly description";
             }
             leaf ids-anomaly-count {
               type string;
               description "Number of anomalies for current type";
             }
             leaf ids-anomaly-rate {
               type string;
               description "Rate of anomalies (events per second)";
             }
             leaf ids-anomaly-elapsed {
               type string;
               description "Elapsed time from last event";
             }
           }
           leaf ids-flow-long-flags {
             type string;
             description "SYN cookie enabled, Forced entry";
           }
           leaf ids-bytes-count {
             type string;
             description "Number of bytes";
           }
           leaf ids-packets-count {
             type string;
             description "Number of packets";
           }
           leaf ids-flows-count {
             type string;
             description "Number of flows";
           }
           leaf ids-anomalies-count {
             type string;
             description "Number of anomalies";
           }
         }
       }
     }
   }
   grouping service-identification-statistics-information-block {
     container service-identification-statistics {
       description "Statistics for the service-identification service";
       leaf interface-name {
         type string;
         description "Name of the adaptive services interface";
       }
       leaf interfaces {
         type uint32;
         description "Total number of interfaces summarized";
       }
       leaf packets {
         type uint64;
         description "Total packets processed by service";
       }
       leaf bytes {
         type uint64;
         description "Total bytes for all packets processed by the service-identification service";
       }
       leaf errored-packets {
         type uint64;
         description "Packets errored by the service-identification service in processing";
       }
       leaf errored-bytes {
         type uint64;
         description "Total bytes for all packets errored by the service-identification service";
       }
       leaf header-examination-packets {
         type uint64;
         description "Packets processed by header examination";
       }
       leaf header-examination-bytes {
         type uint64;
         description "Total bytes for all packets processed by header examination";
       }
       leaf header-examination-flow {
         type uint64;
         description "Total flows examined by header examination";
       }
       leaf header-examination-flow-matched {
         type uint64;
         description "Total flows that matched a header examination rule";
       }
       leaf header-examination-protocol-required {
         type uint64;
         description "Flows identified as requiring protocol inspection";
       }
       leaf header-examination-http-protocol-required {
         type uint64;
         description "Flows identified as possible HTTP flows by header examination rules";
       }
       leaf header-examination-wap-protocol-required {
         type uint64;
         description "Flows identified as possible WAP flows by header examination rules";
       }
       leaf protocol-inspected-flow {
         type uint64;
         description "Total flows that have been protocol inspected";
       }
       leaf protocol-inspection-flow {
         type uint32;
         description "Total flows currently undergoing protocol inspection";
       }
       leaf protocol-inspection-packets {
         type uint64;
         description "Packets processed by protocol inspection";
       }
       leaf protocol-inspection-bytes {
         type uint64;
         description "Total bytes for all packets processed by protocol inspection";
       }
       leaf protocol-inspection-flow-protocol-identified {
         type uint64;
         description "Total flows that have been protocol-identified by protocol inspection";
       }
       leaf protocol-inspection-http-uri {
         type uint64;
         description "HTTP URI by protocol inspection";
       }
       leaf protocol-inspection-http-uri-matched {
         type uint64;
         description "HTTP URI that matched a URI rule";
       }
       leaf protocol-inspection-wap-uri {
         type uint64;
         description "WAP URI by protocol inspection";
       }
       leaf protocol-inspection-wap-uri-matched {
         type uint64;
         description "WAP URI that matched a URI rule";
       }
       leaf wap-transaction-created {
         type uint64;
         description "WAP transaction sessions created";
       }
       leaf wap-transaction-maximum {
         type int32;
         description "Peak WAP transaction sessions";
       }
       leaf wap-transaction-freed {
         type uint64;
         description "WAP transaction sessions freed";
       }
       leaf wap-transaction-idle-freed {
         type uint64;
         description "WAP transaction sessions freed by idle clean-up";
       }
       leaf http-transaction-created {
         type uint64;
         description "HTTP transaction sessions created";
       }
       leaf http-transaction-maximum {
         type int32;
         description "Peak HTTP transaction sessions";
       }
       leaf http-transaction-freed {
         type uint64;
         description "HTTP transaction sessions freed";
       }
       leaf http-transaction-idle-freed {
         type uint64;
         description "HTTP transaction sessions freed by idle clean-up";
       }
       leaf packet-processing-error {
         type uint64;
         description "Total for all packet-processing errors";
       }
       leaf errored-packets-tcp-malformed {
         type uint64;
         description "TCP packets errored because they were malformed";
       }
       leaf errored-packets-http-transaction-in-error {
         type uint64;
         description "HTTP packets errored because the transaction is in error";
       }
       leaf errored-packets-wap-invalid-transaction {
         type uint64;
         description "WAP packets errored for referencing an invalid transaction";
       }
       leaf errored-packets-wap-transaction-in-error {
         type uint64;
         description "WAP packets errored because the transaction is in error";
       }
       leaf uri-processing-error {
         type uint64;
         description "Total for all URI processing errors";
       }
       leaf uri-error-failed-to-process {
         type uint64;
         description "Failures to process a URI due to internal error";
       }
       leaf uri-error-too-long {
         type uint64;
         description "Failures to process a URI due to maximum length exceeded";
       }
       leaf transaction-error-failed-to-parse {
         type uint64;
         description "Failures to parse a transaction";
       }
       leaf uri-error-no-system-resources {
         type uint64;
         description "Failures to process a transaction or URI due to lack of resources";
       }
       leaf header-examination-failed-configuration {
         type uint64;
         description "Number of header examinations failing due to configuration error";
       }
       leaf uri-examination-failed-configuration {
         type uint64;
         description "Number of URI examinations failing due to configuration error";
       }
     }
   }
   grouping header-redirect-set-statistics-information-block {
     leaf interface-name {
       type string;
       description "Name of the adaptive services interface";
     }
     leaf interfaces {
       type uint32;
       description "Total number of interfaces summarized";
     }
     list header-redirect-set-statistics {
       description "Statistics for the header redirect sets";
       leaf header-redirect-set-name {
         type string;
         description "Name of the header redirect set";
       }
       leaf cause-roaming {
         type uint32;
         description "Number of redirects due to roaming";
       }
       leaf cause-time-of-day {
         type uint32;
         description "Number of redirects due to time of day";
       }
       leaf cause-quality-of-service {
         type uint32;
         description "Number of redirects due to QoS";
       }
       leaf cause-volume-expired {
         type uint32;
         description "Number of redirects due to expiration of volume limit";
       }
       leaf cause-cost-warning {
         type uint32;
         description "Number of redirects due to cost warning limit";
       }
       leaf cause-not-allowed {
         type uint32;
         description "Number of redirects due to disallowed service class";
       }
       leaf cause-unsubscribed {
         type uint32;
         description "Number of redirects due to unsubscribed service class";
       }
       leaf cause-credit-expiry {
         type uint32;
         description "Number of redirects due to expiration of credit";
       }
       leaf cause-unknown {
         type uint32;
         description "Number of redirects due to unknown reason";
       }
       leaf cause-default {
         type uint32;
         description "Number of redirects due to default reason match";
       }
     }
   }
   grouping uri-redirect-set-statistics-information-block {
     leaf interface-name {
       type string;
       description "Name of the adaptive services interface";
     }
     leaf interfaces {
       type uint32;
       description "Total number of interfaces summarized";
     }
     list uri-redirect-set-statistics {
       description "Statistics for the URI redirect sets";
       leaf uri-redirect-set-name {
         type string;
         description "Name of header redirect set";
       }
       leaf cause-roaming {
         type uint32;
         description "Number of redirects due to roaming";
       }
       leaf cause-time-of-day {
         type uint32;
         description "Number of redirects due to time of day";
       }
       leaf cause-quality-of-service {
         type uint32;
         description "Number of redirects due to QoS";
       }
       leaf cause-volume-expired {
         type uint32;
         description "Number of redirects due to expiration of volume limit";
       }
       leaf cause-cost-warning {
         type uint32;
         description "Number of redirects due to cost warning limit";
       }
       leaf cause-not-allowed {
         type uint32;
         description "Number of redirects due to disallowed service class";
       }
       leaf cause-unsubscribed {
         type uint32;
         description "Number of redirects due to unsubscribed service class";
       }
       leaf cause-credit-expiry {
         type uint32;
         description "Number of redirects due to expiration of credit";
       }
       leaf cause-unknown {
         type uint32;
         description "Number of redirects due to unknown reason";
       }
       leaf cause-default {
         type uint32;
         description "Number of redirects due to default reason match";
       }
     }
   }
   grouping flow-table-statistics-information-block {
     container flow-table-statistics {
       description "Statistics for one or more flow tables";
       leaf interface-name {
         type string;
         description "Name of the adaptive services interface";
       }
       leaf flow-tables {
         type uint32;
         description "Total number of flow tables being summarized";
       }
       leaf flow {
         type uint32;
         description "Total number of flows in the table";
       }
       leaf flow-peak {
         type uint32;
         description "Sampled peak number of flows in the table";
       }
       leaf flow-tcp {
         type uint32;
         description "Total number of TCP flows in the table";
       }
       leaf flow-tcp-peak {
         type uint32;
         description "Sampled peak number of TCP flows in the table";
       }
       leaf flow-udp {
         type uint32;
         description "Total number of UDP flows in the table";
       }
       leaf flow-udp-peak {
         type uint32;
         description "Peak number of UDP flows in the table";
       }
       leaf flow-created {
         type uint64;
         description "Total flows created";
       }
       leaf flow-freed {
         type uint64;
         description "Total flows freed";
       }
       leaf flow-freed-idle {
         type uint64;
         description "Total flows freed by idle flow detection";
       }
       leaf flow-tcp-created {
         type uint64;
         description "Total TCP flows created";
       }
       leaf flow-tcp-freed {
         type uint64;
         description "Total TCP flows freed";
       }
       leaf flow-tcp-freed-idle {
         type uint64;
         description "Total TCP flows freed by idle detection";
       }
       leaf flow-udp-created {
         type uint64;
         description "Total UDP flows created";
       }
       leaf flow-udp-freed {
         type uint64;
         description "Total UDP flows freed";
       }
       leaf flow-udp-freed-idle {
         type uint64;
         description "Total UDP flows freed by idle detection";
       }
       leaf flow-packets-processed {
         type uint64;
         description "Total packets processed by flow table";
       }
       leaf flow-bytes-processed {
         type uint64;
         description "Total bytes for all packets processed by flow table";
       }
       leaf flow-packets-errored {
         type uint64;
         description "Total packets errored by flow table processing";
       }
       leaf flow-byte-errored {
         type uint64;
         description "Total bytes for all packets errored by flow table processing";
       }
       leaf flow-tcp-packets-processed {
         type uint64;
         description "Total TCP packets processed";
       }
       leaf flow-tcp-bytes-processed {
         type uint64;
         description "Total bytes for all processed TCP packets";
       }
       leaf flow-tcp-packets-errored {
         type uint64;
         description "Total TCP packets errored in processing";
       }
       leaf flow-tcp-bytes-errored {
         type uint64;
         description "Total bytes for all TCP packets errored in processing";
       }
       leaf flow-tcp-packets-errored-bad-flow {
         type uint64;
         description "Total TCP packets errored due to referencing an invalid flow";
       }
       leaf flow-udp-packets-processed {
         type uint64;
         description "Total UDP packets processed";
       }
       leaf flow-udp-bytes-processed {
         type uint64;
         description "Total bytes for all processed UDP packets";
       }
       leaf flow-udp-packets-errored {
         type uint64;
         description "Total UDP packets errored in processing";
       }
       leaf flow-udp-bytes-errored {
         type uint64;
         description "Total bytes for all UDP packets errored in processing";
       }
       leaf flow-udp-packets-errored-bad-flow {
         type uint64;
         description "Total UDP packets errored due to referencing an invalid flow";
       }
       leaf flow-icmp-packets-processed {
         type uint64;
         description "Total ICMP packets";
       }
       leaf flow-icmp-bytes-processed {
         type uint64;
         description "Total bytes for all processed ICMP packets";
       }
       leaf flow-icmp-packets-errored {
         type uint64;
         description "Total ICMP packets errored in processing";
       }
       leaf flow-icmp-bytes-errored {
         type uint64;
         description "Total bytes for all ICMP packets errored in processing";
       }
       leaf flow-icmp-packets-errored-bad-flow {
         type uint64;
         description "Total ICMP packets errored due to referencing an invalid flow";
       }
     }
   }
   grouping soft-gre-tunnel-database-block {
     leaf soft-gre-tunnel-database.heading {
       type string;
       description "Dynamic GRE tunnel database sorted by tunnel group";
     }
     list soft-gre-tunnel-entry {
       description "Soft GRE tunnel information";
       leaf soft-gre-tunnel-interface-name {
         type string;
         description "Tunnel Interface Name";
       }
       leaf soft-gre-tunnel-remote-ip {
         type string;
         description "Remote IP address of tunnel";
       }
       leaf soft-gre-tunnel-local-ip {
         type string;
         description "Local IP address of tunnel";
       }
       leaf soft-gre-tunnel-subscriber-count {
         type string;
         description "Subscriber count";
       }
       leaf soft-gre-tunnel-group-name {
         type string;
         description "Tunnel Group Name";
       }
       leaf soft-gre-tunnel-routing-instance {
         type string;
         description "Tunnel Routing instance";
       }
       leaf soft-gre-tunnel-create-time {
         type string;
         description "Creation time";
       }
       leaf soft-gre-tunnel-up-time {
         type string;
         description "Up time";
       }
       leaf soft-gre-tunnel-idle-time {
         type string;
         description "Idle time";
       }
       leaf soft-gre-tunnel-statistics-since {
         type string;
         description "Statistics since the displayed time";
       }
       leaf soft-gre-tunnel-data-tx-packets {
         type string;
         description "Data transmit packets";
       }
       leaf soft-gre-tunnel-data-tx-bytes {
         type string;
         description "Data transmit bytes";
       }
       leaf soft-gre-tunnel-data-rx-packets {
         type string;
         description "Data receive packets";
       }
       leaf soft-gre-tunnel-data-rx-bytes {
         type string;
         description "Data receive bytes";
       }
     }
   }
   grouping service-l2tp-destination-information-block {
     container l2tp-destination-table {
       description "Destination table";
       leaf l2tp-destination-table.heading {
         type string;
         description "Destination table";
       }
       list l2tp-destination-entry {
         description "L2TP destination information";
         leaf l2tp-destination-local-name {
           type string;
           description "Name of destination local end";
         }
         leaf l2tp-destination-remote-ip {
           type string;
           description "Remote IP address of destination";
         }
         leaf l2tp-destination-tunnel-count {
           type string;
           description "Destination tunnel count";
         }
         leaf l2tp-destination-session-count {
           type string;
           description "Destination session count";
         }
         leaf l2tp-destination-state {
           type string;
           description "Destination state";
         }
         leaf l2tp-destination-switched-session-count {
           type string;
           description "Destination switched session count";
         }
         leaf l2tp-destination-local-ip {
           type string;
           description "Local IP address of session";
         }
         leaf l2tp-destination-lockout-state {
           type string;
           description "Destination Lockout State";
         }
         leaf l2tp-destination-transport {
           type string;
           description "Destination transport";
         }
         leaf l2tp-destination-logical-system {
           type string;
           description "Logical System";
         }
         leaf l2tp-destination-router-instance {
           type string;
           description "Router instance";
         }
         leaf l2tp-destination-access-line-information {
           type string;
           description "Tunnel Access Line Information";
         }
         leaf l2tp-destination-connection-speed-update {
           type string;
           description "Tunnel Connection Speed Updates";
         }
         leaf l2tp-control-tx-packets {
           type string;
           description "Control transmit packets";
         }
         leaf l2tp-control-tx-bytes {
           type string;
           description "Control transmit bytes";
         }
         leaf l2tp-control-rx-packets {
           type string;
           description "Control receive packets";
         }
         leaf l2tp-control-rx-bytes {
           type string;
           description "Control receive bytes";
         }
         leaf l2tp-data-tx-packets {
           type string;
           description "Data transmit packets";
         }
         leaf l2tp-data-tx-bytes {
           type string;
           description "Data transmit bytes";
         }
         leaf l2tp-data-rx-packets {
           type string;
           description "Data receive packets";
         }
         leaf l2tp-data-rx-bytes {
           type string;
           description "Data receive bytes";
         }
         leaf l2tp-error-tx-packets {
           type string;
           description "Error transmit packets";
         }
         leaf l2tp-error-rx-packets {
           type string;
           description "Error receive packets";
         }
         leaf lcp-echo-req-tx-packets {
           type string;
           description "Lcp echo requests transmitted";
         }
         leaf lcp-echo-req-rx-packets {
           type string;
           description "Lcp echo requests received";
         }
         leaf lcp-echo-rep-tx-packets {
           type string;
           description "Lcp echo replies transmitted";
         }
         leaf lcp-echo-rep-rx-packets {
           type string;
           description "Lcp echo replies recieved";
         }
         leaf lcp-echo-req-timeout {
           type string;
           description "Lcp echo requests timedout";
         }
         leaf lcp-tx-echo-req-error {
           type string;
           description "Lcp echo request errors";
         }
         leaf lcp-tx-echo-rep-error {
           type string;
           description "Lcp echo reply errors";
         }
         leaf lcp-rx-echo-req-error {
           type string;
           description "Lcp echo request errors";
         }
         leaf lcp-rx-echo-rep-error {
           type string;
           description "Lcp echo request errors";
         }
         leaf l2tp-destination-tunnel-total {
           type string;
           description "Destination tunnel total";
         }
         leaf l2tp-destination-tunnel-active {
           type string;
           description "Destination tunnel active";
         }
         leaf l2tp-destination-tunnel-failed {
           type string;
           description "Destination tunnel failed";
         }
         leaf l2tp-destination-session-total {
           type string;
           description "Destination session total";
         }
         leaf l2tp-destination-session-active {
           type string;
           description "Destination session active";
         }
         leaf l2tp-destination-session-failed {
           type string;
           description "Destination session failed";
         }
         leaf l2tp-destination-maximum-tunnels {
           type string;
           description "Maximum number of tunnels per destination";
         }
       }
     }
   }
   grouping service-l2tp-destination-lockout-information-block {
     leaf l2tp-destination-lockout-count {
       type string;
       description "Count of L2TP lockout destinations";
     }
     leaf l2tp-destination-time-remaining {
       type string;
       description "Time remaining in lockout state (seconds)";
     }
     leaf l2tp-destination-lockout-session-count {
       type string;
       description "Session count at the time of Lockout";
     }
     list l2tp-destination-lockout-entry {
       description "L2TP destination lockout entry information";
       leaf l2tp-destination-local-name {
         type string;
         description "Name of destination local end";
       }
       leaf l2tp-destination-time-remaining {
         type string;
         description "Time remaining in lockout state (seconds)";
       }
       leaf l2tp-destination-lockout-session-count {
         type string;
         description "Session count at the time of Lockout";
       }
     }
   }
   grouping service-l2tp-tunnel-information-block {
     list l2tp-per-tunnel-group-tunnel-table {
       description "Tunnel table sorted by tunnel group";
       leaf interface-name {
         type string;
         description "Name of the adaptive services interface";
       }
       leaf tunnel-group-name {
         type string;
         description "Name of the tunnel group";
       }
       container l2tp-tunnel-table {
         description "L2TP tunnel table sorted by tunnel group";
         leaf l2tp-tunnel-table.heading {
           type string;
           description "L2TP tunnel table sorted by tunnel group";
         }
         list l2tp-tunnel-entry {
           description "L2TP tunnel information";
           leaf l2tp-tunnel-local-id {
             type string;
             description "Local ID of tunnel";
           }
           leaf l2tp-tunnel-remote-id {
             type string;
             description "Remote ID of tunnel";
           }
           leaf l2tp-tunnel-remote-ip {
             type string;
             description "Remote IP address of tunnel";
           }
           leaf l2tp-tunnel-session-count {
             type string;
             description "Tunnel session count";
           }
           leaf l2tp-tunnel-state {
             type string;
             description "Tunnel state";
           }
           leaf l2tp-tunnel-switched-session-count {
             type string;
             description "Tunnel session count";
           }
           leaf l2tp-tunnel-name {
             type string;
             description "Tunnel Name/Tunnel-Assignment-Id";
           }
           leaf l2tp-tunnel-local-ip {
             type string;
             description "Local IP address of session";
           }
           leaf l2tp-tunnel-admin-state {
             type string;
             description "Tunnel admin state";
           }
           leaf l2tp-tunnel-local-name {
             type string;
             description "Name of tunnel local end";
           }
           leaf l2tp-tunnel-remote-name {
             type string;
             description "Name of tunnel remote end";
           }
           leaf l2tp-tunnel-prm {
             type string;
             description "Tunnel Effective Peer Resync Mechanism";
           }
           leaf l2tp-tunnel-npm {
             type string;
             description "Tunnel Nas Port Method";
           }
           leaf l2tp-tunnel-logical-system {
             type string;
             description "Tunnel Logical System";
           }
           leaf l2tp-tunnel-routing-instance {
             type string;
             description "Tunnel Routing instance";
           }
           leaf session-out-of-resource-result-code-override {
             type string;
             description "Override session-out-of-resource result codes with code admin in CDN message at LNS";
           }
           leaf l2tp-statistics-since {
             type string;
             description "Statistics since the displayed time";
           }
           leaf l2tp-control-tx-packets {
             type string;
             description "Control transmit packets";
           }
           leaf l2tp-control-tx-bytes {
             type string;
             description "Control transmit bytes";
           }
           leaf l2tp-control-rx-packets {
             type string;
             description "Control receive packets";
           }
           leaf l2tp-control-rx-bytes {
             type string;
             description "Control receive bytes";
           }
           leaf l2tp-data-tx-packets {
             type string;
             description "Data transmit packets";
           }
           leaf l2tp-data-tx-bytes {
             type string;
             description "Data transmit bytes";
           }
           leaf l2tp-data-rx-packets {
             type string;
             description "Data receive packets";
           }
           leaf l2tp-data-rx-bytes {
             type string;
             description "Data receive bytes";
           }
           leaf l2tp-error-tx-packets {
             type string;
             description "Error transmit packets";
           }
           leaf l2tp-error-rx-packets {
             type string;
             description "Error receive packets";
           }
           leaf lcp-echo-req-tx-packets {
             type string;
             description "Lcp echo requests transmitted";
           }
           leaf lcp-echo-req-rx-packets {
             type string;
             description "Lcp echo requests received";
           }
           leaf lcp-echo-rep-tx-packets {
             type string;
             description "Lcp echo replies transmitted";
           }
           leaf lcp-echo-rep-rx-packets {
             type string;
             description "Lcp echo replies recieved";
           }
           leaf lcp-echo-req-timeout {
             type string;
             description "Lcp echo requests timedout";
           }
           leaf lcp-tx-echo-req-error {
             type string;
             description "Lcp echo request errors";
           }
           leaf lcp-tx-echo-rep-error {
             type string;
             description "Lcp echo reply errors";
           }
           leaf lcp-rx-echo-req-error {
             type string;
             description "Lcp echo request errors";
           }
           leaf lcp-rx-echo-rep-error {
             type string;
             description "Lcp echo request errors";
           }
           leaf l2tp-tunnel-maximum-sessions {
             type string;
             description "Maximum number of sessions per tunnel";
           }
           leaf l2tp-tunnel-window-size {
             type string;
             description "Tunnel window size";
           }
           leaf l2tp-tunnel-hello-interval {
             type string;
             description "Tunnel hello interval";
           }
           leaf l2tp-create-time {
             type string;
             description "Creation time";
           }
           leaf l2tp-up-time {
             type string;
             description "Up time";
           }
           leaf l2tp-idle-time {
             type string;
             description "Idle time";
           }
           leaf l2tp-tunnel-tos-reflect {
             type string;
             description "Tunnel ToS Reflect";
           }
           leaf l2tp-tunnel-interface-name {
             type string;
             description "Tunnel Interface Name";
           }
           leaf l2tp-tunnel-group-name {
             type string;
             description "Tunnel Group Name";
           }
           leaf l2tp-session-limit-group-name {
             type string;
             description "Session Limit Group Name";
           }
           leaf l2tp-session-limit-group-tunnel-group {
             type string;
             description "Tunnel group";
           }
         }
       }
     }
   }
   grouping service-l2tp-session-information-block {
     list l2tp-per-tunnel-session-table {
       description "Session table sorted by tunnel";
       leaf interface-name {
         type string;
         description "Name of the adaptive services interface";
       }
       leaf tunnel-group-name {
         type string;
         description "Name of the tunnel group";
       }
       leaf l2tp-tunnel-local-id {
         type string;
         description "Local ID of tunnel";
       }
       list l2tp-session-table {
         leaf-list l2tp-session-table.heading {
           type string;
           description "L2TP session table sorted by tunnel ID";
         }
         list l2tp-session-entry {
           leaf l2tp-session-local-id {
             type string;
             description "Local ID of session";
           }
           leaf l2tp-session-remote-id {
             type string;
             description "Remote ID of session";
           }
           leaf l2tp-session-interface-unit {
             type string;
             description "Session interface unit";
           }
           leaf l2tp-session-state {
             type string;
             description "Session state";
           }
           leaf l2tp-session-bundle-id {
             type string;
             description "Session bundle ID";
           }
           leaf l2tp-session-user-name {
             type string;
             description "Session user name";
           }
           leaf l2tp-session-interface-name {
             type string;
             description "PPP Interface Name";
           }
           leaf l2tp-session-admin-state {
             type string;
             description "Session administrative state";
           }
           leaf l2tp-session-mode {
             type string;
             description "Session mode";
           }
           leaf l2tp-session-local-ip {
             type string;
             description "Local IP address of session";
           }
           leaf l2tp-session-remote-ip {
             type string;
             description "Remote IP address of session";
           }
           leaf l2tp-session-local-name {
             type string;
             description "Name of session local end";
           }
           leaf l2tp-session-remote-name {
             type string;
             description "Name of session remote end";
           }
           leaf l2tp-tunnel-switch-profile-name {
             type string;
             description "Name of Tunnel switch profile";
           }
           leaf l2tp-statistics-since {
             type string;
             description "Statistics since the displayed time";
           }
           leaf l2tp-control-tx-packets {
             type string;
             description "Control transmit packets";
           }
           leaf l2tp-control-tx-bytes {
             type string;
             description "Control transmit bytes";
           }
           leaf l2tp-control-rx-packets {
             type string;
             description "Control receive packets";
           }
           leaf l2tp-control-rx-bytes {
             type string;
             description "Control receive bytes";
           }
           leaf l2tp-data-tx-packets {
             type string;
             description "Data transmit packets";
           }
           leaf l2tp-data-tx-bytes {
             type string;
             description "Data transmit bytes";
           }
           leaf l2tp-data-rx-packets {
             type string;
             description "Data receive packets";
           }
           leaf l2tp-data-rx-bytes {
             type string;
             description "Data receive bytes";
           }
           leaf l2tp-error-tx-packets {
             type string;
             description "Error transmit packets";
           }
           leaf l2tp-error-rx-packets {
             type string;
             description "Error receive packets";
           }
           leaf lcp-echo-req-tx-packets {
             type string;
             description "Lcp echo requests transmitted";
           }
           leaf lcp-echo-req-rx-packets {
             type string;
             description "Lcp echo requests received";
           }
           leaf lcp-echo-rep-tx-packets {
             type string;
             description "Lcp echo replies transmitted";
           }
           leaf lcp-echo-rep-rx-packets {
             type string;
             description "Lcp echo replies recieved";
           }
           leaf lcp-echo-req-timeout {
             type string;
             description "Lcp echo requests timedout";
           }
           leaf lcp-tx-echo-req-error {
             type string;
             description "Lcp echo request errors";
           }
           leaf lcp-tx-echo-rep-error {
             type string;
             description "Lcp echo reply errors";
           }
           leaf lcp-rx-echo-req-error {
             type string;
             description "Lcp echo request errors";
           }
           leaf lcp-rx-echo-rep-error {
             type string;
             description "Lcp echo request errors";
           }
           leaf l2tp-session-peer-ip {
             type string;
             description "IP address assigned to peer for the session";
           }
           leaf l2tp-session-own-ip {
             type string;
             description "Local own IP address assigned to session";
           }
           leaf l2tp-session-local-mru {
             type string;
             description "Session local MRU";
           }
           leaf l2tp-session-remote-mru {
             type string;
             description "Session remote MRU";
           }
           leaf l2tp-session-tx-speed {
             type string;
             description "Session transmit speed";
           }
           leaf l2tp-session-tx-speed-source {
             type string;
             description "Session transmit speed source";
           }
           leaf l2tp-session-rx-speed {
             type string;
             description "Session receive speed";
           }
           leaf l2tp-session-rx-speed-source {
             type string;
             description "Session receive speed source";
           }
           leaf l2tp-session-nas-port-type {
             type string;
             description "Session receive nas port type";
           }
           leaf l2tp-session-nas-port {
             type string;
             description "Session receive nas port";
           }
           leaf l2tp-session-bearer-type {
             type string;
             description "Session bearer type";
           }
           leaf l2tp-session-framing-type {
             type string;
             description "Session framing type";
           }
           leaf l2tp-session-lcp-renegotiation {
             type string;
             description "Session LCP renegotiation";
           }
           leaf l2tp-session-authentication {
             type string;
             description "Session authentication";
           }
           leaf l2tp-session-interface-id {
             type string;
             description "Session interface ID";
           }
           leaf l2tp-session-call-serial-number {
             type string;
             description "Session call serial number";
           }
           leaf l2tp-session-policer-bandwidth {
             type string;
             description "Session policer bandwidth";
           }
           leaf l2tp-session-policer-burstsize {
             type string;
             description "Session policer burst size";
           }
           leaf l2tp-session-policer-exclude-bandwidth {
             type string;
             description "Session policer exclude bandwidth";
           }
           leaf l2tp-session-firewall-filter {
             type string;
             description "Session firewall filter name";
           }
           leaf l2tp-session-encapsulation-overhead {
             type string;
             description "Session encapsulation overhead";
           }
           leaf l2tp-session-cell-overhead {
             type string;
             description "Session cell overhead";
           }
           leaf l2tp-create-time {
             type string;
             description "Creation time";
           }
           leaf l2tp-up-time {
             type string;
             description "Up time";
           }
           leaf l2tp-idle-time {
             type string;
             description "Idle time";
           }
           leaf l2tp-session-tos-reflect {
             type string;
             description "Session ToS Reflect";
           }
           leaf l2tp-session-create-time {
             type string;
             description "Session create time";
           }
         }
       }
     }
   }
   grouping service-l2tp-client-information-block {
     container l2tp-client-table {
       description "L2TP client table";
       leaf l2tp-client-table.heading {
         type string;
         description "L2TP client table";
       }
       list l2tp-client-entry {
         description "L2TP client information";
         leaf l2tp-client-name {
           type string;
           description "Name of the remote client";
         }
         leaf l2tp-client-tunnel-count {
           type int32;
           description "Number of active tunnels";
         }
         leaf l2tp-client-session-count {
           type int32;
           description "Number of active sessions";
         }
         leaf l2tp-client-tunnel-group {
           type string;
           description "Tunnel group";
         }
         leaf l2tp-client-session-limit-group {
           type string;
           description "Session limit group";
         }
       }
     }
   }
   grouping service-l2tp-tunnel-group-information-block {
     container l2tp-tunnel-group-table {
       description "L2TP tunnel-group table";
       leaf l2tp-tunnel-group-table.heading {
         type string;
         description "L2TP tunnel-group table";
       }
       list l2tp-tunnel-group-entry {
         description "L2TP tunnel-group information";
         leaf l2tp-tunnel-group-name {
           type string;
           description "Tunnel Group Name";
         }
         leaf l2tp-tunnel-group-tunnel-count {
           type int32;
           description "Number of active tunnels";
         }
         leaf l2tp-tunnel-group-session-count {
           type int32;
           description "Number of active sessions";
         }
       }
     }
   }
   grouping service-l2tp-session-limit-group-information-block {
     container l2tp-session-limit-group-table {
       description "Session limit group table";
       leaf l2tp-session-limit-group-table.heading {
         type string;
         description "Session limit group table";
       }
       list l2tp-session-limit-group-entry {
         description "Session group limit information";
         leaf l2tp-session-limit-group-name {
           type string;
           description "Session Limit Group Name";
         }
         leaf l2tp-session-limit-group-tunnel-count {
           type int32;
           description "Number of active tunnels in a group";
         }
         leaf l2tp-session-limit-group-session-count {
           type int32;
           description "Number of active sessions in a group";
         }
         leaf l2tp-session-limit-group-max-session-count {
           type int32;
           description "Number of maximum sessions in a group";
         }
       }
     }
   }
   grouping service-l2tp-tunnel-switch-information-block {
     list per-tunnel-switch-profile-lts-session-table {
       description "LTS session table sorted by tunnel switch profile";
       leaf l2tp-tunnel-switch-profile-name {
         type string;
         description "Name of Tunnel switch profile";
       }
       list lts-session-table {
         leaf-list lts-session-table.heading {
           type string;
           description "LTS session table sorted by tunnel switch profile name";
         }
         list lts-session-entry {
           leaf lns-session-local-id {
             type int32;
             description "Local session id of LNS session ";
           }
           leaf lac-session-local-id {
             type int32;
             description "Local session id of LAC session ";
           }
           leaf lns-session-state {
             type string;
             description "LNS session state";
           }
           leaf lac-session-state {
             type string;
             description "LAC session state";
           }
           leaf service-interface-name {
             type string;
             description "Service interface";
           }
           leaf tunnel-switch-profile-name {
             type string;
             description "Tunnel switch profile name";
           }
         }
       }
     }
   }
   grouping service-l2tp-disconnect-cause-summary-block {
     leaf user-request-count {
       type string;
       description "User request count";
     }
     leaf loss-of-service-count {
       type string;
       description "Loss of service count";
     }
     leaf idle-timeout-count {
       type string;
       description "Idle timeout count";
     }
     leaf session-timeout-count {
       type string;
       description "Session timeout count";
     }
     leaf admin-disconnect-count {
       type string;
       description "Admin disconnect count";
     }
     leaf port-error-count {
       type string;
       description "Port error count";
     }
     leaf nas-error-count {
       type string;
       description "Nas error count";
     }
     leaf port-suspended-count {
       type string;
       description "Port suspended count";
     }
     leaf service-unavailable-count {
       type string;
       description "Service unavailable count";
     }
     leaf user-error-count {
       type string;
       description "User error count";
     }
     leaf authentication-failure-count {
       type string;
       description "Authentication failure count";
     }
   }
   grouping services-l2tp-multilink-information-block {
     list l2tp-multilink-entry {
       description "L2TP multilink information";
       leaf l2tp-multilink-bundle-id {
         type string;
         description "Bundle ID";
       }
       leaf l2tp-multilink-bundle-num-links {
         type string;
         description "Number of links in a bundle";
       }
       leaf l2tp-multilink-bundle-endpoint {
         type string;
         description "Bundle endpoint";
       }
       list l2tp-multilink-links {
         list l2tp-session-entry {
           leaf l2tp-session-local-id {
             type string;
             description "Local ID of session";
           }
           leaf l2tp-session-remote-id {
             type string;
             description "Remote ID of session";
           }
           leaf l2tp-session-interface-unit {
             type string;
             description "Session interface unit";
           }
           leaf l2tp-session-state {
             type string;
             description "Session state";
           }
           leaf l2tp-session-bundle-id {
             type string;
             description "Session bundle ID";
           }
           leaf l2tp-session-user-name {
             type string;
             description "Session user name";
           }
           leaf l2tp-session-interface-name {
             type string;
             description "PPP Interface Name";
           }
           leaf l2tp-session-admin-state {
             type string;
             description "Session administrative state";
           }
           leaf l2tp-session-mode {
             type string;
             description "Session mode";
           }
           leaf l2tp-session-local-ip {
             type string;
             description "Local IP address of session";
           }
           leaf l2tp-session-remote-ip {
             type string;
             description "Remote IP address of session";
           }
           leaf l2tp-session-local-name {
             type string;
             description "Name of session local end";
           }
           leaf l2tp-session-remote-name {
             type string;
             description "Name of session remote end";
           }
           leaf l2tp-tunnel-switch-profile-name {
             type string;
             description "Name of Tunnel switch profile";
           }
           leaf l2tp-statistics-since {
             type string;
             description "Statistics since the displayed time";
           }
           leaf l2tp-control-tx-packets {
             type string;
             description "Control transmit packets";
           }
           leaf l2tp-control-tx-bytes {
             type string;
             description "Control transmit bytes";
           }
           leaf l2tp-control-rx-packets {
             type string;
             description "Control receive packets";
           }
           leaf l2tp-control-rx-bytes {
             type string;
             description "Control receive bytes";
           }
           leaf l2tp-data-tx-packets {
             type string;
             description "Data transmit packets";
           }
           leaf l2tp-data-tx-bytes {
             type string;
             description "Data transmit bytes";
           }
           leaf l2tp-data-rx-packets {
             type string;
             description "Data receive packets";
           }
           leaf l2tp-data-rx-bytes {
             type string;
             description "Data receive bytes";
           }
           leaf l2tp-error-tx-packets {
             type string;
             description "Error transmit packets";
           }
           leaf l2tp-error-rx-packets {
             type string;
             description "Error receive packets";
           }
           leaf lcp-echo-req-tx-packets {
             type string;
             description "Lcp echo requests transmitted";
           }
           leaf lcp-echo-req-rx-packets {
             type string;
             description "Lcp echo requests received";
           }
           leaf lcp-echo-rep-tx-packets {
             type string;
             description "Lcp echo replies transmitted";
           }
           leaf lcp-echo-rep-rx-packets {
             type string;
             description "Lcp echo replies recieved";
           }
           leaf lcp-echo-req-timeout {
             type string;
             description "Lcp echo requests timedout";
           }
           leaf lcp-tx-echo-req-error {
             type string;
             description "Lcp echo request errors";
           }
           leaf lcp-tx-echo-rep-error {
             type string;
             description "Lcp echo reply errors";
           }
           leaf lcp-rx-echo-req-error {
             type string;
             description "Lcp echo request errors";
           }
           leaf lcp-rx-echo-rep-error {
             type string;
             description "Lcp echo request errors";
           }
           leaf l2tp-session-peer-ip {
             type string;
             description "IP address assigned to peer for the session";
           }
           leaf l2tp-session-own-ip {
             type string;
             description "Local own IP address assigned to session";
           }
           leaf l2tp-session-local-mru {
             type string;
             description "Session local MRU";
           }
           leaf l2tp-session-remote-mru {
             type string;
             description "Session remote MRU";
           }
           leaf l2tp-session-tx-speed {
             type string;
             description "Session transmit speed";
           }
           leaf l2tp-session-tx-speed-source {
             type string;
             description "Session transmit speed source";
           }
           leaf l2tp-session-rx-speed {
             type string;
             description "Session receive speed";
           }
           leaf l2tp-session-rx-speed-source {
             type string;
             description "Session receive speed source";
           }
           leaf l2tp-session-nas-port-type {
             type string;
             description "Session receive nas port type";
           }
           leaf l2tp-session-nas-port {
             type string;
             description "Session receive nas port";
           }
           leaf l2tp-session-bearer-type {
             type string;
             description "Session bearer type";
           }
           leaf l2tp-session-framing-type {
             type string;
             description "Session framing type";
           }
           leaf l2tp-session-lcp-renegotiation {
             type string;
             description "Session LCP renegotiation";
           }
           leaf l2tp-session-authentication {
             type string;
             description "Session authentication";
           }
           leaf l2tp-session-interface-id {
             type string;
             description "Session interface ID";
           }
           leaf l2tp-session-call-serial-number {
             type string;
             description "Session call serial number";
           }
           leaf l2tp-session-policer-bandwidth {
             type string;
             description "Session policer bandwidth";
           }
           leaf l2tp-session-policer-burstsize {
             type string;
             description "Session policer burst size";
           }
           leaf l2tp-session-policer-exclude-bandwidth {
             type string;
             description "Session policer exclude bandwidth";
           }
           leaf l2tp-session-firewall-filter {
             type string;
             description "Session firewall filter name";
           }
           leaf l2tp-session-encapsulation-overhead {
             type string;
             description "Session encapsulation overhead";
           }
           leaf l2tp-session-cell-overhead {
             type string;
             description "Session cell overhead";
           }
           leaf l2tp-create-time {
             type string;
             description "Creation time";
           }
           leaf l2tp-up-time {
             type string;
             description "Up time";
           }
           leaf l2tp-idle-time {
             type string;
             description "Idle time";
           }
           leaf l2tp-session-tos-reflect {
             type string;
             description "Session ToS Reflect";
           }
           leaf l2tp-session-create-time {
             type string;
             description "Session create time";
           }
         }
       }
       leaf l2tp-multilink-bundle-mrru-input {
         type string;
         description "Input MRRU";
       }
       leaf l2tp-multilink-bundle-mrru-output {
         type string;
         description "Output MRRU";
       }
       leaf l2tp-statistics-since {
         type string;
         description "Statistics since the displayed time";
       }
       leaf l2tp-control-tx-packets {
         type string;
         description "Control transmit packets";
       }
       leaf l2tp-control-tx-bytes {
         type string;
         description "Control transmit bytes";
       }
       leaf l2tp-control-rx-packets {
         type string;
         description "Control receive packets";
       }
       leaf l2tp-control-rx-bytes {
         type string;
         description "Control receive bytes";
       }
       leaf l2tp-data-tx-packets {
         type string;
         description "Data transmit packets";
       }
       leaf l2tp-data-tx-bytes {
         type string;
         description "Data transmit bytes";
       }
       leaf l2tp-data-rx-packets {
         type string;
         description "Data receive packets";
       }
       leaf l2tp-data-rx-bytes {
         type string;
         description "Data receive bytes";
       }
       leaf l2tp-error-tx-packets {
         type string;
         description "Error transmit packets";
       }
       leaf l2tp-error-rx-packets {
         type string;
         description "Error receive packets";
       }
       leaf lcp-echo-req-tx-packets {
         type string;
         description "Lcp echo requests transmitted";
       }
       leaf lcp-echo-req-rx-packets {
         type string;
         description "Lcp echo requests received";
       }
       leaf lcp-echo-rep-tx-packets {
         type string;
         description "Lcp echo replies transmitted";
       }
       leaf lcp-echo-rep-rx-packets {
         type string;
         description "Lcp echo replies recieved";
       }
       leaf lcp-echo-req-timeout {
         type string;
         description "Lcp echo requests timedout";
       }
       leaf lcp-tx-echo-req-error {
         type string;
         description "Lcp echo request errors";
       }
       leaf lcp-tx-echo-rep-error {
         type string;
         description "Lcp echo reply errors";
       }
       leaf lcp-rx-echo-req-error {
         type string;
         description "Lcp echo request errors";
       }
       leaf lcp-rx-echo-rep-error {
         type string;
         description "Lcp echo request errors";
       }
       leaf l2tp-multilink-bundle-mrru {
         type string;
         description "Peer MRRU";
       }
       leaf l2tp-multilink-bundle-droptime {
         type string;
         description "Fragment Drop Timeout";
       }
       leaf l2tp-multilink-bundle-maxfrag {
         type string;
         description "Maximum Fragment Size";
       }
       leaf l2tp-multilink-bundle-minfrag {
         type string;
         description "Min Fragment Size for Equal load";
       }
       leaf l2tp-multilink-bundle-minmru {
         type string;
         description "Min Link MRU";
       }
       leaf l2tp-multilink-bundle-maxqlen {
         type string;
         description "Max OUTQ len";
       }
       leaf l2tp-multilink-bundle-tx-packets {
         type string;
         description "Output Packets";
       }
       leaf l2tp-multilink-bundle-tx-frags {
         type string;
         description "Transmitted Frags";
       }
       leaf l2tp-multilink-bundle-txseq {
         type string;
         description "Next transmit sequence";
       }
       leaf l2tp-multilink-bundle-rx-packets {
         type string;
         description "Reassembled packets";
       }
       leaf l2tp-multilink-bundle-rx-frags {
         type string;
         description "Input frags";
       }
       leaf l2tp-multilink-bundle-rxseq {
         type string;
         description "Next fragment in fragwheel";
       }
       leaf l2tp-multilink-bundle-mseq {
         type string;
         description "Minimum sequence number";
       }
       leaf l2tp-multilink-bundle-rx-maxdiff {
         type string;
         description "Max forward seq diff";
       }
       leaf l2tp-multilink-bundle-rx-reass {
         type string;
         description "No. of reassembled packets";
       }
       leaf l2tp-multilink-bundle-rx-copyfrag {
         type string;
         description "Copy frame";
       }
       list l2tp-multilink-bundle-links {
         leaf l2tp-multilink-bundle-links-number {
           type string;
           description "Link Number";
         }
         leaf l2tp-multilink-bundle-links-ml-seq {
           type string;
           description "Last sequence received on link";
         }
         leaf l2tp-multilink-bundle-links-ml-mru {
           type string;
           description "Max Receive unit";
         }
         leaf l2tp-multilink-bundle-links-ml-encap {
           type string;
           description "L2 Encapsulation size";
         }
         leaf l2tp-multilink-bundle-links-ml-qlen {
           type string;
           description "Output queue length";
         }
         leaf l2tp-multilink-bundle-links-ml-context {
           type string;
           description "User supplied context";
         }
       }
     }
   }
   grouping service-l2tp-summary-information-block {
     container l2tp-summary-table {
       description "L2TP summary";
       leaf l2tp-administrative-state {
         type string;
         description "Global Administrative state";
       }
       leaf l2tp-failover-preference-level {
         type string;
         description "Failover within a preference level";
       }
       leaf l2tp-weighted-load-balancing {
         type string;
         description "Weighted load balancing";
       }
       leaf l2tp-destination-equal-load-balancing {
         type string;
         description "Destination equal load balancing";
       }
       leaf l2tp-tunnel-authentication-challenge {
         type string;
         description "Tunnel authentication challenge";
       }
       leaf l2tp-calling-number-avp {
         type string;
         description "Calling number avp";
       }
       leaf l2tp-failover-protocol {
         type string;
         description "Failover protocol";
       }
       leaf l2tp-failover-resync {
         type string;
         description "Failover Resync Mechanism";
       }
       leaf l2tp-tx-connect-speed-method {
         type string;
         description "Tx connect speed method";
       }
       leaf l2tp-rx-speed-avp-when-equal {
         type string;
         description "Rx connect speed AVP when tx equals rx speed";
       }
       leaf l2tp-tunnel-assignment-id-format {
         type string;
         description "Tunnel assignment id format";
       }
       leaf l2tp-tunnel-minimum-retransmission-timeout {
         type string;
         description "Min Retransmission timeout for control packets";
       }
       leaf l2tp-tunnel-retranmission-count-established {
         type string;
         description "Max Retransmission count for Established tunnels";
       }
       leaf l2tp-tunnel-retranmission-count-not-established {
         type string;
         description "Max Retransmission count for Not Established tunnels";
       }
       leaf l2tp-tunnel-idle-timeout {
         type string;
         description "Tunnel idle timeout value in seconds";
       }
       leaf l2tp-tunnel-tx-address-change {
         type string;
         description "Tx Address Change";
       }
       leaf l2tp-destruct-timeout {
         type string;
         description "The destruct timeout in seconds";
       }
       leaf l2tp-destination-lockout-timeout {
         type string;
         description "The destination lockout timeout in seconds";
       }
       leaf l2tp-reassembly-service-set {
         type string;
         description "Reassembly Service Set";
       }
       leaf l2tp-max-packet-process-count {
         type string;
         description "Max packets processed per iteration";
       }
       leaf l2tp-access-line-information {
         type string;
         description "Access Line information";
       }
       leaf l2tp-connection-speed-updates {
         type string;
         description "Connection Speed Updates";
       }
       leaf l2tp-enable-ipv6-services-for-lac {
         type string;
         description "IPv6 Services for LAC Sessions";
       }
       leaf l2tp-destinations {
         type uint32;
         description "Total number of L2TP destinations";
       }
       leaf l2tp-tunnels {
         type uint32;
         description "Total number of L2TP tunnels";
       }
       leaf l2tp-sessions {
         type uint32;
         description "Total number of L2TP sessions";
       }
       leaf l2tp-switched-sessions {
         type uint32;
         description "Total number of L2TP switched sessions";
       }
       leaf l2tp-control-tx-packets {
         type string;
         description "Control transmit packets";
       }
       leaf l2tp-control-rx-packets {
         type string;
         description "Control receive packets";
       }
       leaf l2tp-control-memory-bytes {
         type string;
         description "L2TP control memory (bytes)";
       }
       leaf l2tp-data-tx-packets {
         type string;
         description "Data transmit packets";
       }
       leaf l2tp-data-rx-packets {
         type string;
         description "Data receive packets";
       }
       leaf l2tp-data-memory-bytes {
         type uint64;
         description "L2TP data memory (bytes)";
       }
       leaf l2tp-error-tx-packets {
         type string;
         description "Error transmit packets";
       }
       leaf l2tp-error-rx-packets {
         type string;
         description "Error receive packets";
       }
       leaf l2tp-lcp-echo-requests-transmitted {
         type string;
         description "Total Lcp echo requests transmitted";
       }
       leaf l2tp-lcp-echo-requests-recieved {
         type string;
         description "Total Lcp echo requests recieved";
       }
       leaf l2tp-lcp-echo-responses-transmitted {
         type string;
         description "Total Lcp echo replies transmitted";
       }
       leaf l2tp-lcp-echo-responses-recieved {
         type string;
         description "Total Lcp echo replies received";
       }
       leaf l2tp-lcp-echo-timedout {
         type string;
         description "Total Lcp echo timeouts";
       }
       leaf l2tp-lcp-tx-echo-request-errors {
         type string;
         description "Total Lcp Transmit echo request errors";
       }
       leaf l2tp-lcp-tx-echo-response-errors {
         type string;
         description "Total Lcp Transmit echo reply errors";
       }
       leaf l2tp-lcp-rx-echo-request-errors {
         type string;
         description "Total Lcp Recieve echo request errors";
       }
       leaf l2tp-lcp-rx-echo-response-errors {
         type string;
         description "Total Lcp Recieve echo reply errors";
       }
       leaf l2tp-interface-name {
         type string;
         description "Name of interface to show summary information";
       }
       leaf l2tp-interface-control-tx-packets {
         type string;
         description "Control transmit packets sorted by interface";
       }
       leaf l2tp-interface-control-rx-packets {
         type string;
         description "Control receive packets sorted by interface";
       }
       leaf l2tp-interface-data-tx-packets {
         type string;
         description "Data transmit packets sorted by interface";
       }
       leaf l2tp-interface-data-rx-packets {
         type string;
         description "Data receive packets sorted by interface";
       }
       leaf l2tp-interface-error-tx-packets {
         type string;
         description "Error transmit packets sorted by interface";
       }
       leaf l2tp-interface-error-rx-packets {
         type string;
         description "Error receive packets sorted by interface";
       }
       leaf l2tp-interface-lcp-echo-requests-transmitted {
         type string;
         description "Lcp echo requests transmitted on interface";
       }
       leaf l2tp-interface-lcp-echo-requests-recieved {
         type string;
         description "Lcp echo requests recieved on interface";
       }
       leaf l2tp-interface-lcp-echo-responses-transmitted {
         type string;
         description "Lcp echo replies transmitted on interface";
       }
       leaf l2tp-interface-lcp-echo-responses-recieved {
         type string;
         description "Lcp echo replies received on interface";
       }
       leaf l2tp-interface-lcp-echo-timedout {
         type string;
         description "Lcp echo timeouts on interface";
       }
       leaf l2tp-interface-lcp-tx-echo-request-errors {
         type string;
         description "Lcp Transmit echo request errors on interface";
       }
       leaf l2tp-interface-lcp-tx-echo-response-errors {
         type string;
         description "Lcp Transmit echo reply errors on interface";
       }
       leaf l2tp-interface-lcp-rx-echo-request-errors {
         type string;
         description "Lcp Recieve echo request errors on interface";
       }
       leaf l2tp-interface-lcp-rx-echo-response-errors {
         type string;
         description "Lcp Recieve echo reply errors on interface";
       }
     }
   }
   grouping services-l2tp-radius-authentication-accounting-servers-information-block {
     list radius-authentication-server-information-entry {
       description "RADIUS authentication server information entry sorted by IP address";
       leaf radius-server-ip-address {
         type jt:ipaddr;
         description "Server IP address";
       }
       leaf radius-server-state {
         type string;
         description "Server state";
       }
       leaf radius-server-udp-port {
         type uint32;
         description "Server UDP port";
       }
       leaf radius-server-retry-count {
         type uint32;
         description "Server retry count";
       }
       leaf radius-server-timeout {
         type uint32;
         description "Server timeout value in seconds";
       }
       leaf radius-server-pending-requests {
         type uint32;
         description "Server number of requests pending";
       }
       leaf radius-server-maximum-sessions {
         type uint32;
         description "Server maximum allowed sessions";
       }
       leaf radius-server-dead-time {
         type uint32;
         description "Server dead time value in seconds";
       }
       leaf radius-server-secret-type {
         type string;
         description "Server secret type";
       }
     }
     list radius-accounting-server-information-entry {
       description "RADIUS accounting server information entry sorted by IP address";
       leaf radius-server-ip-address {
         type jt:ipaddr;
         description "Server IP address";
       }
       leaf radius-server-state {
         type string;
         description "Server state";
       }
       leaf radius-server-udp-port {
         type uint32;
         description "Server UDP port";
       }
       leaf radius-server-retry-count {
         type uint32;
         description "Server retry count";
       }
       leaf radius-server-timeout {
         type uint32;
         description "Server timeout value in seconds";
       }
       leaf radius-server-pending-requests {
         type uint32;
         description "Server number of requests pending";
       }
       leaf radius-server-maximum-sessions {
         type uint32;
         description "Server maximum allowed sessions";
       }
       leaf radius-server-dead-time {
         type uint32;
         description "Server dead time value in seconds";
       }
       leaf radius-server-secret-type {
         type string;
         description "Server secret type";
       }
     }
   }
   grouping services-l2tp-radius-authentication-accounting-statistics-information-block {
     list radius-authentication-statistic-information-entry {
       description "RADIUS authentication statistic entry sorted by IP address";
       leaf radius-server-statistics-entry-header {
         type string;
         description "Server statistics entry header";
       }
       leaf radius-server-profile-name {
         type string;
         description "Server profile access name";
       }
       leaf radius-server-ip-address {
         type jt:ipaddr;
         description "Server IP address";
       }
       leaf radius-server-udp-port {
         type uint32;
         description "Server UDP port";
       }
       leaf radius-statistic-access-requests {
         type uint32;
         description "Access requests count";
       }
       leaf radius-statistic-rollover-requests {
         type uint32;
         description "Rollover requests count";
       }
       leaf radius-statistic-retransmissions {
         type uint32;
         description "Retransmissions count";
       }
       leaf radius-statistic-access-accepts {
         type uint32;
         description "Access accepts count";
       }
       leaf radius-statistic-access-rejects {
         type uint32;
         description "Access rejects count";
       }
       leaf radius-statistic-access-challenges {
         type uint32;
         description "Access challenges count";
       }
       leaf radius-statistic-malformed-responses {
         type uint32;
         description "Malformed responses count";
       }
       leaf radius-statistic-bad-authenticators {
         type uint32;
         description "Bad authenticators count";
       }
       leaf radius-statistic-requests-pending {
         type uint32;
         description "Requests pending count";
       }
       leaf radius-statistic-request-timeouts {
         type uint32;
         description "Request timeouts count";
       }
       leaf radius-statistic-unknown-responses {
         type uint32;
         description "Unknown responses count";
       }
       leaf radius-statistic-packets-dropped {
         type uint32;
         description "Packets dropped count";
       }
     }
     list radius-accounting-statistic-information-entry {
       description "RADIUS accounting statistic entry sorted by IP address";
       leaf radius-server-statistics-entry-header {
         type string;
         description "Server statistics entry header";
       }
       leaf radius-server-profile-name {
         type string;
         description "Server profile access name";
       }
       leaf radius-server-ip-address {
         type jt:ipaddr;
         description "Server IP address";
       }
       leaf radius-server-udp-port {
         type uint32;
         description "Server UDP port";
       }
       leaf radius-statistic-requests {
         type uint32;
         description "Requests count";
       }
       leaf radius-statistic-start-requests {
         type uint32;
         description "Start requests count";
       }
       leaf radius-statistic-interim-requests {
         type uint32;
         description "Interim requests count";
       }
       leaf radius-statistic-stop-requests {
         type uint32;
         description "Stop requests count";
       }
       leaf radius-statistic-rollover-requests {
         type uint32;
         description "Rollover requests count";
       }
       leaf radius-statistic-retransmissions {
         type uint32;
         description "Retransmissions count";
       }
       leaf radius-statistic-responses {
         type uint32;
         description "Responses count";
       }
       leaf radius-statistic-start-responses {
         type uint32;
         description "Start responses count";
       }
       leaf radius-statistic-interim-responses {
         type uint32;
         description "Interim responses count";
       }
       leaf radius-statistic-stop-responses {
         type uint32;
         description "Stop responses count";
       }
       leaf radius-statistic-malformed-responses {
         type uint32;
         description "Malformed responses count";
       }
       leaf radius-statistic-bad-authenticators {
         type uint32;
         description "Bad authenticators count";
       }
       leaf radius-statistic-requests-pending {
         type uint32;
         description "Requests pending count";
       }
       leaf radius-statistic-request-timeouts {
         type uint32;
         description "Request timeouts count";
       }
       leaf radius-statistic-unknown-responses {
         type uint32;
         description "Unknown responses count";
       }
       leaf radius-statistic-packets-dropped {
         type uint32;
         description "Packets dropped count";
       }
     }
   }
   grouping services-l2tp-radius-authentication-servers-information-block {
     list radius-authentication-server-information-entry {
       description "RADIUS authentication server information entry sorted by IP address";
       leaf radius-server-ip-address {
         type jt:ipaddr;
         description "Server IP address";
       }
       leaf radius-server-state {
         type string;
         description "Server state";
       }
       leaf radius-server-udp-port {
         type uint32;
         description "Server UDP port";
       }
       leaf radius-server-retry-count {
         type uint32;
         description "Server retry count";
       }
       leaf radius-server-timeout {
         type uint32;
         description "Server timeout value in seconds";
       }
       leaf radius-server-pending-requests {
         type uint32;
         description "Server number of requests pending";
       }
       leaf radius-server-maximum-sessions {
         type uint32;
         description "Server maximum allowed sessions";
       }
       leaf radius-server-dead-time {
         type uint32;
         description "Server dead time value in seconds";
       }
       leaf radius-server-secret-type {
         type string;
         description "Server secret type";
       }
     }
   }
   grouping services-l2tp-radius-authentication-statistics-information-block {
     list radius-authentication-statistic-information-entry {
       description "RADIUS authentication statistic entry sorted by IP address";
       leaf radius-server-statistics-entry-header {
         type string;
         description "Server statistics entry header";
       }
       leaf radius-server-profile-name {
         type string;
         description "Server profile access name";
       }
       leaf radius-server-ip-address {
         type jt:ipaddr;
         description "Server IP address";
       }
       leaf radius-server-udp-port {
         type uint32;
         description "Server UDP port";
       }
       leaf radius-statistic-access-requests {
         type uint32;
         description "Access requests count";
       }
       leaf radius-statistic-rollover-requests {
         type uint32;
         description "Rollover requests count";
       }
       leaf radius-statistic-retransmissions {
         type uint32;
         description "Retransmissions count";
       }
       leaf radius-statistic-access-accepts {
         type uint32;
         description "Access accepts count";
       }
       leaf radius-statistic-access-rejects {
         type uint32;
         description "Access rejects count";
       }
       leaf radius-statistic-access-challenges {
         type uint32;
         description "Access challenges count";
       }
       leaf radius-statistic-malformed-responses {
         type uint32;
         description "Malformed responses count";
       }
       leaf radius-statistic-bad-authenticators {
         type uint32;
         description "Bad authenticators count";
       }
       leaf radius-statistic-requests-pending {
         type uint32;
         description "Requests pending count";
       }
       leaf radius-statistic-request-timeouts {
         type uint32;
         description "Request timeouts count";
       }
       leaf radius-statistic-unknown-responses {
         type uint32;
         description "Unknown responses count";
       }
       leaf radius-statistic-packets-dropped {
         type uint32;
         description "Packets dropped count";
       }
     }
   }
   grouping services-l2tp-radius-accounting-servers-information-block {
     list radius-accounting-server-information-entry {
       description "RADIUS accounting server information entry sorted by IP address";
       leaf radius-server-ip-address {
         type jt:ipaddr;
         description "Server IP address";
       }
       leaf radius-server-state {
         type string;
         description "Server state";
       }
       leaf radius-server-udp-port {
         type uint32;
         description "Server UDP port";
       }
       leaf radius-server-retry-count {
         type uint32;
         description "Server retry count";
       }
       leaf radius-server-timeout {
         type uint32;
         description "Server timeout value in seconds";
       }
       leaf radius-server-pending-requests {
         type uint32;
         description "Server number of requests pending";
       }
       leaf radius-server-maximum-sessions {
         type uint32;
         description "Server maximum allowed sessions";
       }
       leaf radius-server-dead-time {
         type uint32;
         description "Server dead time value in seconds";
       }
       leaf radius-server-secret-type {
         type string;
         description "Server secret type";
       }
     }
   }
   grouping services-l2tp-radius-accounting-statistics-information-block {
     list radius-accounting-statistic-information-entry {
       description "RADIUS accounting statistic entry sorted by IP address";
       leaf radius-server-statistics-entry-header {
         type string;
         description "Server statistics entry header";
       }
       leaf radius-server-profile-name {
         type string;
         description "Server profile access name";
       }
       leaf radius-server-ip-address {
         type jt:ipaddr;
         description "Server IP address";
       }
       leaf radius-server-udp-port {
         type uint32;
         description "Server UDP port";
       }
       leaf radius-statistic-requests {
         type uint32;
         description "Requests count";
       }
       leaf radius-statistic-start-requests {
         type uint32;
         description "Start requests count";
       }
       leaf radius-statistic-interim-requests {
         type uint32;
         description "Interim requests count";
       }
       leaf radius-statistic-stop-requests {
         type uint32;
         description "Stop requests count";
       }
       leaf radius-statistic-rollover-requests {
         type uint32;
         description "Rollover requests count";
       }
       leaf radius-statistic-retransmissions {
         type uint32;
         description "Retransmissions count";
       }
       leaf radius-statistic-responses {
         type uint32;
         description "Responses count";
       }
       leaf radius-statistic-start-responses {
         type uint32;
         description "Start responses count";
       }
       leaf radius-statistic-interim-responses {
         type uint32;
         description "Interim responses count";
       }
       leaf radius-statistic-stop-responses {
         type uint32;
         description "Stop responses count";
       }
       leaf radius-statistic-malformed-responses {
         type uint32;
         description "Malformed responses count";
       }
       leaf radius-statistic-bad-authenticators {
         type uint32;
         description "Bad authenticators count";
       }
       leaf radius-statistic-requests-pending {
         type uint32;
         description "Requests pending count";
       }
       leaf radius-statistic-request-timeouts {
         type uint32;
         description "Request timeouts count";
       }
       leaf radius-statistic-unknown-responses {
         type uint32;
         description "Unknown responses count";
       }
       leaf radius-statistic-packets-dropped {
         type uint32;
         description "Packets dropped count";
       }
     }
   }
   grouping service-crtp-flow-table-information-block {
     list crtp-per-interface-flow-table {
       description "CRTP flows sorted by interface";
       leaf interface-name {
         type string;
         description "Name of the adaptive services interface";
       }
       list service-crtp-flow-table {
         description "CRTP flows";
         list crtp-flow-entry {
           description "CRTP flow information";
           leaf crtp-flow-type {
             type string;
             description "Flow type";
           }
           leaf crtp-flow-source-info {
             type string;
             description "Flow source information (IP address and UDP port)";
           }
           leaf crtp-flow-destination-info {
             type string;
             description "Flow destination information (IP address and UDP port)";
           }
           leaf crtp-flow-rtp-id {
             type int32;
             description "RTP SSRC identifier";
           }
           leaf crtp-flow-context-id {
             type int32;
             description "Context identifier";
           }
         }
       }
     }
   }
   grouping lsqinfo-cpu-usage-information-block {
     leaf cpu-role-name {
       type string;
       description "CPU family name";
     }
     leaf one-second-usage {
       type string;
       description "CPU usage. 1 second average";
     }
     leaf five-second-usage {
       type string;
       description "CPU usage. 5 second average";
     }
     container fragmenter-entries {
       list fragmenter-entry {
         leaf cpu-name {
           type string;
           description " CPU name";
         }
         leaf idle {
           type string;
           description "Percentage of CPU time taken by Idle thread";
         }
         leaf timer {
           type string;
           description "Percentage of CPU time taken by Timer thread";
         }
         leaf system {
           type string;
           description "Percentage of CPU time taken by System thread";
         }
         leaf drop {
           type string;
           description "Percentage of CPU time taken by Drop thread";
         }
         leaf fragmentation {
           type string;
           description "Percentage of CPU time taken by Fragmentation thread";
         }
         leaf reassembly {
           type string;
           description "Percentage of CPU time taken by reassembly thread";
         }
         leaf freeback {
           type string;
           description "Percentage of CPU time taken by Freeback thread";
         }
       }
     }
     container quality-of-service-entries {
       list quality-of-service-entry {
         leaf cpu-name {
           type string;
           description " CPU name";
         }
         leaf idle {
           type string;
           description "Percentage of CPU time taken by Idle thread";
         }
         leaf timer {
           type string;
           description "Percentage of CPU time taken by Timer thread";
         }
         leaf system {
           type string;
           description "Percentage of CPU time taken by System thread";
         }
         leaf input {
           type string;
           description "Percentage of CPU time taken by Input thread";
         }
         leaf output {
           type string;
           description "Percentage of CPU time taken by Output thread";
         }
         leaf fragment-output {
           type string;
           description "Percentage of CPU time taken by Fragment Output thread";
         }
         leaf bypass-output {
           type string;
           description "Percentage of CPU time taken by Bypass Output thread";
         }
         leaf free-frame {
           type string;
           description "Percentage of CPU time taken by Free Frame thread";
         }
       }
     }
     container sequencer-entries {
       list sequencer-entry {
         leaf cpu-name {
           type string;
           description " CPU name";
         }
         leaf idle {
           type string;
           description "Percentage of CPU time taken by Idle thread";
         }
         leaf system {
           type string;
           description "Percentage of CPU time taken by System thread";
         }
         leaf input-lfi {
           type string;
           description "Percentage of CPU time taken by Input LFI thread";
         }
         leaf input-fragments {
           type string;
           description "Percentage of CPU time taken by Input Fragments thread";
         }
         leaf output-fragments {
           type string;
           description "Percentage of CPU time taken by Output Fragments thread";
         }
         leaf output-retry {
           type string;
           description "Percentage of CPU time taken by Output Retry thread";
         }
       }
     }
     container load-balancer-entries {
       list load-balancer-entry {
         leaf cpu-name {
           type string;
           description " CPU name";
         }
         leaf idle {
           type string;
           description "Percentage of CPU time taken by Idle thread";
         }
         leaf system {
           type string;
           description "Percentage of CPU time taken by System thread";
         }
         leaf input-1 {
           type string;
           description "Percentage of CPU time taken by Input 1 thread";
         }
         leaf input-2 {
           type string;
           description "Percentage of CPU time taken by Input 2 thread";
         }
         leaf output {
           type string;
           description "Percentage of CPU time taken by Output thread";
         }
         leaf freeback {
           type string;
           description "Percentage of CPU time taken by Freeback thread";
         }
       }
     }
   }
   grouping ip-monitoring-block {
     leaf ipmon-header {
       type string;
       description "Ip-monitoring header";
     }
     container policy-header {
       description "Ip-monitoring policy header";
       leaf policy-name {
         type string;
         description "Ip-monitoring policy name";
       }
     }
     container status {
       description "Ip-monitoring status";
       leaf probe-name {
         type string;
         description "RPM probe owner's name";
       }
       leaf test-name {
         type string;
         description "RPM test name";
       }
       leaf target-address {
         type string;
         description "Target address of test";
       }
       leaf probe-status {
         type string;
         description "RPM probe status";
       }
     }
     container status-route {
       leaf route-action-type {
         type string;
         description "The type of route action";
       }
       leaf instance {
         type string;
         description "Routing instance";
       }
       leaf route {
         type string;
         description "Static route";
       }
       leaf next-hop {
         type string;
         description "Next hop";
       }
       leaf preferred-route-state {
         type string;
         description "Preferred-route action state";
       }
     }
     container status-intf {
       leaf intf {
         type string;
         description "Interface";
       }
       leaf intf-action {
         type string;
         description "Interface action";
       }
       leaf intf-state {
         type string;
         description "Interface state";
       }
       leaf intf-action-state {
         type string;
         description "Interface action failover state";
       }
     }
   }
   grouping tdir-commit-status-block {
     leaf tdir-config-status {
       type string;
       description "Prints config status of previous commit";
     }
   }
   grouping url-filter-statistics-block {
     container url-filter-statistics-information {
       leaf act-accept-session-cnt {
         type uint64;
         description "Accept session count";
       }
       leaf act-accept-uplink-packet-cnt {
         type uint64;
         description "Accept uplink packet count";
       }
       leaf act-accept-uplink-bytes {
         type uint64;
         description "Accept uplink bytes";
       }
       leaf act-accept-downlink-packet-cnt {
         type uint64;
         description "Accept downlink packet count";
       }
       leaf act-accept-downlink-bytes {
         type uint64;
         description "Accept downlink bytes";
       }
       leaf act-custom-page-session-cnt {
         type uint64;
         description "Custom page session count";
       }
       leaf act-custom-page-uplink-packet-cnt {
         type uint64;
         description "Custom page uplink packet count";
       }
       leaf act-custom-page-uplink-bytes {
         type uint64;
         description "Custom page uplink bytes";
       }
       leaf act-custom-page-downlink-packet-cnt {
         type uint64;
         description "Custom page downlink packet count";
       }
       leaf act-custom-page-downlink-bytes {
         type uint64;
         description "Custom page downlink bytes";
       }
       leaf act-http-scode-session-cnt {
         type uint64;
         description "Http scode session count";
       }
       leaf act-http-scode-uplink-packet-cnt {
         type uint64;
         description "Http scode uplink packet count";
       }
       leaf act-http-scode-uplink-bytes {
         type uint64;
         description "Http scode uplink bytes";
       }
       leaf act-http-scode-downlink-packet-cnt {
         type uint64;
         description "Http scode downlink packet count";
       }
       leaf act-http-scode-downlink-bytes {
         type uint64;
         description "Http scode downlink bytes";
       }
       leaf act-redirect-url-session-cnt {
         type uint64;
         description "Redirect url session count";
       }
       leaf act-redirect-url-uplink-packet-cnt {
         type uint64;
         description "Redirect url uplink packet count";
       }
       leaf act-redirect-url-uplink-bytes {
         type uint64;
         description "Redirect url uplink bytes";
       }
       leaf act-redirect-url-downlink-packet-cnt {
         type uint64;
         description "Redirect url downlink packet count";
       }
       leaf act-redirect-url-downlink-bytes {
         type uint64;
         description "Redirect url downlink bytes";
       }
       leaf act-tcp-reset-session-cnt {
         type uint64;
         description "Tcp reset session count";
       }
       leaf act-tcp-reset-uplink-packet-cnt {
         type uint64;
         description "Tcp reset uplink packet count";
       }
       leaf act-tcp-reset-uplink-bytes {
         type uint64;
         description "Tcp reset uplink bytes";
       }
       leaf act-tcp-reset-downlink-packet-cnt {
         type uint64;
         description "Tcp reset downlink packet count";
       }
       leaf act-tcp-reset-downlink-bytes {
         type uint64;
         description "Tcp reset downlink bytes";
       }
       leaf act-sess-v4-duif-accepted {
         type uint64;
         description "IPv4 Sesscions accepted by disable URL IP filtering";
       }
       leaf act-sess-v4-duif-uplink-packet-cnt {
         type uint64;
         description "Disable URL IP filtering uplink IPv4 packets";
       }
       leaf act-sess-v4-duif-downlink-packet-cnt {
         type uint64;
         description "Disable URL IP filtering downlink IPv4 packets";
       }
       leaf act-sess-v4-duif-uplink-bytes {
         type uint64;
         description "Disable URL IP filtering uplink IPv4 bytes";
       }
       leaf act-sess-v4-duif-downlink-bytes {
         type uint64;
         description "Disable URL IP filtering downlink IPv4 bytes";
       }
       leaf act-sess-v6-duif-accepted {
         type uint64;
         description "IPv6 Sesscions accepted by disable URL IP filtering";
       }
       leaf act-sess-v6-duif-uplink-packet-cnt {
         type uint64;
         description "Disable URL IP filtering uplink IPv6 packets";
       }
       leaf act-sess-v6-duif-downlink-packet-cnt {
         type uint64;
         description "Disable URL IP filtering downlink IPv6 packets";
       }
       leaf act-sess-v6-duif-uplink-bytes {
         type uint64;
         description "Disable URL IP filtering uplink IPv6 bytes";
       }
       leaf act-sess-v6-duif-downlink-bytes {
         type uint64;
         description "Disable URL IP filtering downlink IPv6 bytes";
       }
     }
   }
   grouping url-filter-dns-resolution-block {
     leaf profile-name {
       type string;
       description "Profile Name";
     }
     list url-filter-template-dns-resolution-information {
       leaf template-name {
         type string;
         description "Template Name";
       }
       list url-filter-term-node-information {
         leaf filter-index {
           type uint32;
           description "Index of the Filter Term";
         }
         leaf filter-term-name {
           type string;
           description "Filter Term Name";
         }
         leaf filter-num-ipv4 {
           type uint32;
           description "Number of IPv4 addresses";
         }
         leaf filter-num-ipv6 {
           type uint32;
           description "Number of IPv6 addresses";
         }
         list url-filter-domain-node-information {
           leaf domain-index {
             type uint32;
             description "Index of the domain name";
           }
           leaf dns-domain-name {
             type string;
             description "Domain Name";
           }
           container dns-ipv4 {
             leaf-list dns-ipv4-address {
               type string;
               description "IPv4 Address";
             }
           }
           container dns-ipv6 {
             leaf-list dns-ipv6-address {
               type string;
               description "IPv6 Address";
             }
           }
         }
       }
     }
   }
   grouping url-filter-dns-resolution-statistics-block {
     leaf profile-name {
       type string;
       description "Profile Name";
     }
     list url-filter-template-dns-resolution-statistics-information {
       leaf template-name {
         type string;
         description "Template Name";
       }
       list url-filter-dns-resolution-stats-info {
         leaf dns-start-time {
           type string;
           description "DNS resolution start time";
         }
         leaf dns-finish-time {
           type string;
           description "DNS resolution finish time";
         }
         leaf next-dns-start-time {
           type string;
           description "Next DNS resolution start time";
         }
         leaf ipv4-resolved-domains {
           type uint32;
           description "IPv4 resolved domains";
         }
         leaf ipv6-resolved-domains {
           type uint32;
           description "IPv6 resolved domains";
         }
         leaf ipv4-unresolved-domains {
           type uint32;
           description "IPv4 unresolved domains";
         }
         leaf ipv6-unresolved-domains {
           type uint32;
           description "IPv6 unresolved domains";
         }
         leaf dns-requests-sent {
           type uint32;
           description "DNS requests sent";
         }
         leaf dns-response-received {
           type uint32;
           description "DNS responses received";
         }
         container dns-ipv4-extensive {
           leaf dns-ip-address {
             type string;
             description "DNS IP Address";
           }
           leaf dns-requests-sent {
             type uint32;
             description "DNS requests sent";
           }
           leaf dns-response-received {
             type uint32;
             description "DNS responses received";
           }
           leaf dns-retries {
             type uint32;
             description "DNS retries";
           }
           leaf-list dns-ipv4-address {
             type string;
             description "IPv4 Address";
           }
         }
         container dns-ipv6-extensive {
           leaf dns-ip-address {
             type string;
             description "DNS IP Address";
           }
           leaf dns-requests-sent {
             type uint32;
             description "DNS requests sent";
           }
           leaf dns-response-received {
             type uint32;
             description "DNS responses received";
           }
           leaf dns-retries {
             type uint32;
             description "DNS retries";
           }
           leaf-list dns-ipv6-address {
             type string;
             description "IPv6 Address";
           }
         }
         leaf filter-index {
           type uint32;
           description "Index of the Filter Term";
         }
         leaf dns-domain-name {
           type string;
           description "Domain Name";
         }
       }
     }
   }
   grouping url-filter-secintel-policy-status-block {
     leaf profile-name {
       type string;
       description "Profile Name";
     }
     leaf cc-db-file-name {
       type string;
       description "C&C DB file name";
     }
     leaf policy-state {
       type string;
       description "Policy enforcement state";
     }
     leaf db-change-time {
       type string;
       description "DB change time";
     }
     leaf db-load-time {
       type string;
       description "DB load time";
     }
     leaf ipv4-prefix-count {
       type uint32;
       description "IPv4 prefix count";
     }
     leaf ipv6-prefix-count {
       type uint32;
       description "IPv6 prefix count";
     }
     leaf threat-level {
       type uint32;
       description "Threat level";
     }
     leaf threat-level-action {
       type string;
       description "Threat level action";
     }
     leaf v4-term-count {
       type uint32;
       description "IPv4 Term count";
     }
     leaf term-ipv4-prefix-count {
       type uint32;
       description "Term IPv4 prefix count";
     }
     leaf v6-term-count {
       type uint32;
       description "IPv6 Term count";
     }
     leaf term-ipv6-prefix-count {
       type uint32;
       description "Term IPv6 prefix count";
     }
     list url-filter-global-wl-bl-secintel-policy-status {
       leaf gbl-wl-db-file-name {
         type string;
         description "Global Whitelist DB file name";
       }
       leaf gbl-wl-db-change-time {
         type string;
         description "Global Whitelist DB change time";
       }
       leaf gbl-wl-db-load-time {
         type string;
         description "Global Whitelist DB load time";
       }
       leaf gbl-wl-ipv4-prefix-count {
         type uint32;
         description "Global Whitelist IPv4 prefix count";
       }
       leaf gbl-wl-ipv6-prefix-count {
         type uint32;
         description "Global Whitelist IPv6 prefix count";
       }
       leaf gbl-bl-db-file-name {
         type string;
         description "Global Blacklist DB file name";
       }
       leaf gbl-bl-db-change-time {
         type string;
         description "Global Blacklist DB change time";
       }
       leaf gbl-bl-db-load-time {
         type string;
         description "Global Blacklist DB load time";
       }
       leaf gbl-bl-ipv4-prefix-count {
         type uint32;
         description "Global Blacklist IPv4 prefix count";
       }
       leaf gbl-bl-ipv6-prefix-count {
         type uint32;
         description "Global Blacklist IPv6 prefix count";
       }
     }
     list url-filter-template-secintel-policy-status {
       leaf template-name {
         type string;
         description "Template Name";
       }
       leaf wl-cc-db-file-name {
         type string;
         description "White list C&C DB file name";
       }
       leaf wl-policy-state {
         type string;
         description "Whitelist Policy enforcement state";
       }
       leaf wl-db-change-time {
         type string;
         description "Whitelist DB change time";
       }
       leaf wl-db-load-time {
         type string;
         description "Whitelist DB load time";
       }
       leaf wl-ipv4-prefix-count {
         type uint32;
         description "Whitelist IPv4 prefix count";
       }
       leaf wl-ipv6-prefix-count {
         type uint32;
         description "Whitelist IPv6 prefix count";
       }
       leaf bl-cc-db-file-name {
         type string;
         description "Blacklist C&C DB file name";
       }
       leaf bl-policy-state {
         type string;
         description "Blacklist Policy enforcement state";
       }
       leaf bl-db-change-time {
         type string;
         description "Blacklist DB change time";
       }
       leaf bl-db-load-time {
         type string;
         description "Blacklist DB load time";
       }
       leaf bl-ipv4-prefix-count {
         type uint32;
         description "Blacklist IPv4 prefix count";
       }
       leaf bl-ipv6-prefix-count {
         type uint32;
         description "Blacklist IPv6 prefix count";
       }
       leaf custom-cc-db-file-name {
         type string;
         description "Custom C&C DB file name";
       }
       leaf custom-policy-state {
         type string;
         description "Custom Policy enforcement state";
       }
       leaf custom-db-change-time {
         type string;
         description "Custom DB change time";
       }
       leaf custom-db-load-time {
         type string;
         description "Custom DB load time";
       }
       leaf custom-ipv4-prefix-count {
         type uint32;
         description "Custom IPv4 prefix count";
       }
       leaf custom-ipv6-prefix-count {
         type uint32;
         description "Custom IPv6 prefix count";
       }
       leaf custom-threat-level {
         type uint32;
         description "Threat level";
       }
       leaf custom-threat-level-action {
         type string;
         description "Threat level action";
       }
       leaf custom-v4-term-count {
         type uint32;
         description "IPv4 Term count";
       }
       leaf custom-term-ipv4-prefix-count {
         type uint32;
         description "Term IPv4 prefix count";
       }
       leaf custom-v6-term-count {
         type uint32;
         description "IPv6 Term count";
       }
       leaf custom-term-ipv6-prefix-count {
         type uint32;
         description "Term IPv6 prefix count";
       }
     }
     list url-filter-secintel-geoip-policy-status {
       leaf geoip-db-file-name {
         type string;
         description "GeoIP DB file name";
       }
       leaf geoip-policy-state {
         type string;
         description "GeoIP Policy enforcement state";
       }
       leaf geoip-db-change-time {
         type string;
         description "GeoIP DB change time";
       }
       leaf geoip-db-load-time {
         type string;
         description "GeoIP DB load time";
       }
       leaf geoip-ipv4-prefix-count {
         type uint32;
         description "GeoIP IPv4 prefix count";
       }
       leaf geoip-ipv6-prefix-count {
         type uint32;
         description "GeoIP IPv6 prefix count";
       }
       leaf geoip-country-name {
         type string;
         description "Geoip country name";
       }
       leaf geoip-threat-level-action {
         type string;
         description "Threat level action";
       }
       leaf geoip-v4-term-count {
         type uint32;
         description "IPv4 Term count";
       }
       leaf geoip-term-ipv4-prefix-count {
         type uint32;
         description "Term IPv4 prefix count";
       }
       leaf geoip-v6-term-count {
         type uint32;
         description "IPv6 Term count";
       }
       leaf geoip-term-ipv6-prefix-count {
         type uint32;
         description "Term IPv6 prefix count";
       }
     }
   }
 }
