/*
 * Copyright (c) 2024 Juniper Networks, Inc.
 * All rights reserved.
 */
 module junos-es-rpc-security {
   namespace "http://yang.juniper.net/junos-es/rpc/security";

   prefix security;

   import junos-common-types {
     prefix jt;
     revision-date 2024-01-01;
   }

   organization "Juniper Networks, Inc.";

   contact "yang-support@juniper.net";

   description "Junos RPC YANG module for security command(s)";

   revision 2024-01-01 {
     description "Junos: 24.2R1.17";
   }

   rpc get-security-alarm-information {
     description "Show active security alarm information";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       container security-alarm-information {
         uses security-alarm-information-block;
       }
     }
   }
   rpc get-security-log-information {
     description "Show auditable security log information";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       container security-log-information {
         uses security-log-information-block;
       }
     }
   }
   rpc get-security-hpl-infile {
     description "Show security logs in binary format";
     input {
       leaf file_name {
         description "Name of the binary log file to be displayed ";
         type string {
           length "1 .. 256";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
   }
   rpc get-security-hpl-infile-last {
     description "Show recent security logs in binary format";
     input {
       leaf seconds {
         description "Number of seconds of binary logs to display";
         type union {
           type uint32;
           type string {
             pattern "<.*>|$.*";
           }
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
   }
   rpc get-security-stream-hpl-infile {
     description "Show security logs stream file";
     input {
       leaf file-name {
         description "Name of the stream log file to be displayed ";
         type string {
           length "1 .. 256";
         }
         mandatory true;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
   }
   rpc get-security-log-query {
     description "Query logs from database";
     input {
       leaf category {
         description "Category name";
         type enumeration {
           enum "all" {
             description "Category all";
           }
           enum "utm" {
             description "Utm";
           }
           enum "fw-auth" {
             description "Fw-auth";
           }
           enum "screen" {
             description "Screen";
           }
           enum "alg" {
             description "Alg";
           }
           enum "nat" {
             description "Nat";
           }
           enum "flow" {
             description "Flow";
           }
           enum "sctp" {
             description "Sctp";
           }
           enum "gtp" {
             description "Gtp";
           }
           enum "ipsec" {
             description "Ipsec";
           }
           enum "idp" {
             description "Idp";
           }
           enum "rtlog" {
             description "Rtlog";
           }
           enum "pst-ds-lite" {
             description "Pst-ds-lite";
           }
           enum "appqos" {
             description "Appqos";
           }
           enum "secintel" {
             description "Secintel";
           }
           enum "aamw" {
             description "AAMW";
           }
           enum "dns" {
             description "Dns";
           }
         }
         mandatory true;
       }
       leaf count {
         description "Number of logs to be queried";
         type union {
           type uint32;
           type string {
             pattern "<.*>|$.*";
           }
         }
       }
       leaf src-ip {
         description "Filter source ip";
         type jt:ipaddr;
       }
       leaf dst-ip {
         description "Filter destination ip";
         type jt:ipaddr;
       }
       leaf src-port {
         description "Filter source port";
         type union {
           type string {
             pattern "<.*>|$.*";
           }
           type uint16 {
             range "1 .. 65535";
           }
         }
       }
       leaf dst-port {
         description "Filter destination port";
         type union {
           type string {
             pattern "<.*>|$.*";
           }
           type uint16 {
             range "1 .. 65535";
           }
         }
       }
       leaf application {
         description "Filter application";
         type string {
           length "1 .. 64";
         }
       }
       leaf user {
         description "Filter user";
         type string {
           length "1 .. 64";
         }
       }
       leaf service {
         description "Filter service";
         type string {
           length "1 .. 64";
         }
       }
       leaf event-type {
         description "Filter event-type";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
     }
   }
   rpc get-sec-log-report-top-all {
     description "Analyze all logs";
     input {
       leaf application {
         description "Show item by application";
         type string {
           length "1 .. 64";
         }
       }
       leaf attack-name {
         description "Show item by attack-name";
         type string {
           length "1 .. 64";
         }
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf category {
         description "Show item by category";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf high-risk-detail {
         description "Show summary of detail on high-risk apps";
         type empty;
       }
       leaf high-risk-action {
         description "Show summary of action on high-risk apps";
         type empty;
       }
       leaf operation {
         description "Operation between multiple parameters";
         type enumeration {
           enum "or" {
             description "Operation or";
           }
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-zone {
         description "Show item by source zone";
         type string {
           length "1 .. 64";
         }
       }
       leaf per-risk-category {
         description "Show summary per risk category";
         type empty;
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf-list expression {
         ordered-by user;
         description "Expression to handle multiple options";
         type jt:policy-algebra;
       }
       leaf reason {
         description "Show item by reason";
         type string {
           length "1 .. 64";
         }
       }
       leaf rule-name {
         description "Show item by rule-name";
         type string {
           length "1 .. 64";
         }
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf threat-severity {
         description "Show item by threat-severity";
         type string {
           length "1 .. 64";
         }
       }
       leaf url {
         description "Show item by url";
         type string {
           length "1 .. 64";
         }
       }
       leaf url-visitor-list {
         description "Show summary of url visitors";
         type empty;
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-all {
     description "Analyze all atp logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-aamw {
     description "Analyze all atp aamw logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-aamw-http {
     description "Analyze all atp aamw http logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-aamw-mail {
     description "Analyze all atp aamw mail logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-aamw-malware {
     description "Analyze all atp aamw malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-malware {
     description "Analyze all atp malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-atp-secintel {
     description "Analyze all atp secintel logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-dns {
     description "Analyze all dns logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-idp-all {
     description "Analyze all idp logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-idp-attack {
     description "Analyze all idp attack logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-ipsec-vpn {
     description "Analyze all ipsec-vpn logs";
     input {
       leaf destination-address {
         description "Show item by destination-address";
         type jt:ipaddr;
       }
       leaf event-type {
         description "Show item by event-type";
         type string {
           length "1 .. 64";
         }
       }
       leaf operation {
         description "Operation between multiple parameters";
         type enumeration {
           enum "or" {
             description "Operation or";
           }
         }
       }
       leaf destination-zone {
         description "Show item by destination zone";
         type string {
           length "1 .. 64";
         }
       }
       leaf profile {
         description "Show item by profile";
         type string {
           length "1 .. 64";
         }
       }
       leaf session-id {
         description "Show item by session-id";
         type string {
           length "1 .. 64";
         }
       }
       leaf source-address {
         description "Show item by source-address";
         type jt:ipaddr;
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-dst-country {
         description "Filter the data by dst country";
         type string {
           length "1 .. 64";
         }
       }
       leaf where-src-country {
         description "Filter the data by src country";
         type string {
           length "1 .. 64";
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-screen {
     description "Analyze all screen logs";
     input {
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-session-all {
     description "Analyze all session logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-session-close {
     description "Analyze all session-close logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-session-create {
     description "Analyze all session-create logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-session-deny {
     description "Analyze all session-deny logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-threat {
     description "Analyze all threat logs";
     input {
       leaf application {
         description "Show item by application";
         type string {
           length "1 .. 64";
         }
       }
       leaf category {
         description "Show item by category";
         type string {
           length "1 .. 64";
         }
       }
       leaf url {
         description "Show item by url";
         type string {
           length "1 .. 64";
         }
       }
       leaf threat-severity {
         description "Show item by threat-severity";
         type string {
           length "1 .. 64";
         }
       }
       leaf destination-zone {
         description "Show item by destination zone";
         type string {
           length "1 .. 64";
         }
       }
       leaf profile {
         description "Show item by profile";
         type string {
           length "1 .. 64";
         }
       }
       leaf attack-name {
         description "Show item by attack-name";
         type string {
           length "1 .. 64";
         }
       }
       leaf policy-name {
         description "Show item by policy-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf protocol-name {
         description "Show item by protocol name";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-port {
         description "Show item by source port";
         type string {
           length "1 .. 64";
         }
       }
       leaf user {
         description "Show item by user";
         type string {
           length "1 .. 64";
         }
       }
       leaf source-zone {
         description "Show item by source zone";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-all {
     description "Analyze all  logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-antispam {
     description "Analyze all utm antispam logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-av-detected {
     description "Analyze all utm antivirus detected logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-content-filter {
     description "Analyze all utm content filter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-wf {
     description "Analyze all utm webfilter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-wf-blocked {
     description "Analyze all utm webfilter blocked logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-top-utm-wf-permitted {
     description "Analyze all utm webfilter permiitted logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf ascending {
         description "Sorted in ascending order";
         type empty;
       }
       leaf top-number {
         description "Top N";
         default "5";
         type union {
           type string {
             pattern "<.*>|$.*";
           }
           type uint32 {
             range "1 .. 65535";
           }
         }
       }
       leaf group-by {
         description "Group the data";
         type enumeration {
           enum "application" {
             description "Group by application";
           }
           enum "destination-address" {
             description "Group by destination-address";
           }
           enum "source-address" {
             description "Group by source-address";
           }
           enum "name" {
             description "Group by name";
           }
           enum "user" {
             description "Group by user";
           }
           enum "source-interface" {
             description "Group by source-interface";
           }
           enum "source-zone" {
             description "Group by source-zone";
           }
           enum "destination-zone" {
             description "Group by destination-zone";
           }
           enum "profile" {
             description "Group by profile";
           }
           enum "protocol" {
             description "Group by protocol";
           }
           enum "reason" {
             description "Group by reason";
           }
           enum "category" {
             description "Group by category";
           }
           enum "application-category" {
             description "Group by application-category";
           }
           enum "application-subcategory" {
             description "Group by application-subcategory";
           }
           enum "application-risk-level" {
             description "Group by application-risk-level";
           }
           enum "url" {
             description "Group by url";
           }
           enum "event-type" {
             description "Group by event-type";
           }
           enum "policy-name" {
             description "Group by policy-name";
           }
           enum "attack-name" {
             description "Group by attack-name";
           }
           enum "rule-name" {
             description "Group by rule-name";
           }
           enum "threat-severity" {
             description "Group by threat-severity";
           }
           enum "unified-severity" {
             description "Group by unified-severity";
           }
           enum "threat-type" {
             description "Group by threat-type";
           }
           enum "file-name" {
             description "Group by file-name";
           }
           enum "destination-country" {
             description "Group by destination-country";
           }
           enum "source-country" {
             description "Group by source-country";
           }
           enum "malware" {
             description "Group by malware";
           }
           enum "actions" {
             description "Group by actions";
           }
           enum "service" {
             description "Group by service";
           }
           enum "sender-email" {
             description "Group by sender-email";
           }
           enum "recipient-email" {
             description "Group by recipient-email";
           }
         }
       }
       leaf order-by {
         description "Order by volume or count or packet";
         type enumeration {
           enum "url-access" {
             description "Order by url-accesses";
           }
           enum "volume" {
             description "Order by volume";
           }
           enum "count" {
             description "Order by count";
           }
           enum "packet" {
             description "Order by packet";
           }
           enum "user-number" {
             description "Order by user-number";
           }
           enum "count-percentage" {
             description "Order by count percentage";
           }
           enum "volume-percentage" {
             description "Order by volume percentage";
           }
           enum "destination-address-number" {
             description "Order by destination-address-number";
           }
           enum "risk" {
             description "Order by risk";
           }
           enum "volume-total" {
             description "Order by total volume";
           }
           enum "bandwidth" {
             description "Order by bandwidth";
           }
           enum "duration" {
             description "Order by duration of url access";
           }
         }
       }
       leaf where-attack {
         description "Filter the data by attack name";
         type enumeration {
           enum "botnet" {
             description "Filter attack botnet";
           }
           enum "malware" {
             description "Filter attack malware";
           }
         }
       }
       leaf where-application {
         description "Filter the data by application";
         type enumeration {
           enum "http" {
             description "Filter http application";
           }
         }
       }
       leaf where-application-category {
         description "Filter the data by application category";
         type enumeration {
           enum "CC" {
             description "Filter CC log";
           }
           enum "Infected-Hosts" {
             description "Filter Infected-Hosts log";
           }
         }
       }
       leaf where-application-risk {
         description "Filter the data by application risk";
         type enumeration {
           enum "high" {
             description "Filter high risk application";
           }
         }
       }
       leaf where-app-mobile-remote-access {
         description "Filter the data when app category is Remote access and subcategory is Mobile";
         type empty;
       }
       leaf where-severity {
         description "Filter the data by severity";
         type enumeration {
           enum "critical" {
             description "Filter severity critical";
           }
           enum "major" {
             description "Filter severity major";
           }
           enum "minor" {
             description "Filter severity minor";
           }
           enum "warning" {
             description "Filter severity warning";
           }
           enum "info" {
             description "Filter severity info";
           }
         }
       }
       leaf where-address {
         description "Filter the data by ip address";
         type jt:ipaddr;
       }
       leaf where-malware-new {
         description "Filter the data for new malware";
         type empty;
       }
       leaf where-malware-known {
         description "Filter the data for known malware";
         type empty;
       }
       leaf where-srczone {
         description "Filter the data by srczone";
         type string {
           length "1 .. 64";
         }
       }
       leaf where-dstzone {
         description "Filter the data by dstzone";
         type string {
           length "1 .. 64";
         }
       }
       leaf where-srcint {
         description "Filter the data by src interface";
         type string {
           length "1 .. 64";
         }
       }
       leaf where-policy-name {
         description "Filter the data by policy name";
         type string {
           length "1 .. 64";
         }
       }
       leaf where-threat-level {
         description "Filter the data by sky threat level";
         type enumeration {
           enum "high" {
             description "Filter high threat level";
           }
         }
       }
       leaf where-action {
         description "Filter the data by action";
         type enumeration {
           enum "permit" {
             description "Filter permit action";
           }
           enum "block" {
             description "Filter block action";
           }
           enum "quarantine" {
             description "Filter quarantine action";
           }
         }
       }
       leaf where-exclude {
         description "Exclude the data";
         type enumeration {
           enum "session-deny" {
             description "Exclude session-deny log";
           }
         }
       }
       leaf where-exclude-src-country {
         description "Filter the data by src country negatively";
         type string {
           length "1 .. 64";
         }
       }
       leaf where-exclude-dst-country {
         description "Filter the data by dst country negatively";
         type string {
           length "1 .. 64";
         }
       }
       leaf where-url-risk {
         description "Filter the data by url risk";
         type enumeration {
           enum "high" {
             description "Filter url risk high";
           }
           enum "high-medium" {
             description "Filter url risk high and medium";
           }
           enum "productivity-loss" {
             description "Filter url risk productivity-loss";
           }
           enum "legal-liability" {
             description "Filter url risk legal-liability";
           }
         }
       }
       leaf where-url-category {
         description "Filter the data by url category";
         type string {
           length "1 .. 64";
         }
       }
       leaf where-username {
         description "Filter the data by username";
         type string {
           length "1 .. 64";
         }
       }
       leaf with {
         description "Calculate again based on result";
         type enumeration {
           enum "application" {
             description "With application";
           }
           enum "user" {
             description "With user";
           }
           enum "severity" {
             description "With severity";
           }
           enum "url" {
             description "With severity";
           }
         }
       }
     }
   }
   rpc get-sec-log-report-detail-all {
     description "Analyze all logs";
     input {
       leaf application {
         description "Show item by application";
         type string {
           length "1 .. 64";
         }
       }
       leaf attack-name {
         description "Show item by attack-name";
         type string {
           length "1 .. 64";
         }
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf category {
         description "Show item by category";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf high-risk-detail {
         description "Show summary of detail on high-risk apps";
         type empty;
       }
       leaf high-risk-action {
         description "Show summary of action on high-risk apps";
         type empty;
       }
       leaf operation {
         description "Operation between multiple parameters";
         type enumeration {
           enum "or" {
             description "Operation or";
           }
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-zone {
         description "Show item by source zone";
         type string {
           length "1 .. 64";
         }
       }
       leaf per-risk-category {
         description "Show summary per risk category";
         type empty;
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf-list expression {
         ordered-by user;
         description "Expression to handle multiple options";
         type jt:policy-algebra;
       }
       leaf reason {
         description "Show item by reason";
         type string {
           length "1 .. 64";
         }
       }
       leaf rule-name {
         description "Show item by rule-name";
         type string {
           length "1 .. 64";
         }
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf threat-severity {
         description "Show item by threat-severity";
         type string {
           length "1 .. 64";
         }
       }
       leaf url {
         description "Show item by url";
         type string {
           length "1 .. 64";
         }
       }
       leaf url-visitor-list {
         description "Show summary of url visitors";
         type empty;
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-all {
     description "Analyze all atp logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-aamw {
     description "Analyze all atp aamw logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-aamw-http {
     description "Analyze all atp aamw http logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-aamw-mail {
     description "Analyze all atp aamw mail logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-aamw-malware {
     description "Analyze all atp aamw malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-malware {
     description "Analyze all atp malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-atp-secintel {
     description "Analyze all atp secintel logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-dns {
     description "Analyze all dns logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-idp-all {
     description "Analyze all idp logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-idp-attack {
     description "Analyze all idp attack logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-ipsec-vpn {
     description "Analyze all ipsec-vpn logs";
     input {
       leaf destination-address {
         description "Show item by destination-address";
         type jt:ipaddr;
       }
       leaf event-type {
         description "Show item by event-type";
         type string {
           length "1 .. 64";
         }
       }
       leaf operation {
         description "Operation between multiple parameters";
         type enumeration {
           enum "or" {
             description "Operation or";
           }
         }
       }
       leaf destination-zone {
         description "Show item by destination zone";
         type string {
           length "1 .. 64";
         }
       }
       leaf profile {
         description "Show item by profile";
         type string {
           length "1 .. 64";
         }
       }
       leaf session-id {
         description "Show item by session-id";
         type string {
           length "1 .. 64";
         }
       }
       leaf source-address {
         description "Show item by source-address";
         type jt:ipaddr;
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf where-dst-country {
         description "Filter the data by dst country";
         type string {
           length "1 .. 64";
         }
       }
       leaf where-src-country {
         description "Filter the data by src country";
         type string {
           length "1 .. 64";
         }
       }
       leaf descending {
         description "Sorted in descending order";
         type empty;
       }
     }
   }
   rpc get-sec-log-report-detail-screen {
     description "Analyze all screen logs";
     input {
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-session-all {
     description "Analyze all session logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-detail-session-close {
     description "Analyze all session-close logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-detail-session-create {
     description "Analyze all session-create logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-detail-session-deny {
     description "Analyze all session-deny logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-detail-threat {
     description "Analyze all threat logs";
     input {
       leaf application {
         description "Show item by application";
         type string {
           length "1 .. 64";
         }
       }
       leaf category {
         description "Show item by category";
         type string {
           length "1 .. 64";
         }
       }
       leaf url {
         description "Show item by url";
         type string {
           length "1 .. 64";
         }
       }
       leaf threat-severity {
         description "Show item by threat-severity";
         type string {
           length "1 .. 64";
         }
       }
       leaf destination-zone {
         description "Show item by destination zone";
         type string {
           length "1 .. 64";
         }
       }
       leaf profile {
         description "Show item by profile";
         type string {
           length "1 .. 64";
         }
       }
       leaf attack-name {
         description "Show item by attack-name";
         type string {
           length "1 .. 64";
         }
       }
       leaf policy-name {
         description "Show item by policy-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf protocol-name {
         description "Show item by protocol name";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-port {
         description "Show item by source port";
         type string {
           length "1 .. 64";
         }
       }
       leaf user {
         description "Show item by user";
         type string {
           length "1 .. 64";
         }
       }
       leaf source-zone {
         description "Show item by source zone";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-all {
     description "Analyze all logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-antispam {
     description "Analyze all utm antispam logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-av-detected {
     description "Analyze all utm antivirus detected logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-content-filter {
     description "Analyze all utm content filter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-wf {
     description "Analyze all utm webfilter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-wf-blocked {
     description "Analyze all utm webfilter blocked logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-detail-utm-wf-permitted {
     description "Analyze all utm webfilter permiitted logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf descending {
         description "Sorted in descending order";
         type empty;
       }
     }
   }
   rpc get-sec-log-report-interval-atp-all {
     description "Analyze all atp logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-aamw {
     description "Analyze all atp aamw logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-aamw-http {
     description "Analyze all atp aamw http logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-aamw-mail {
     description "Analyze all atp aamw mail logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-aamw-malware {
     description "Analyze all atp aamw malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-malware {
     description "Analyze all atp malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-atp-secintel {
     description "Analyze all atp secintel logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-dns {
     description "Analyze all dns logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-idp-all {
     description "Analyze all idp logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
     }
   }
   rpc get-sec-log-report-interval-idp-attack {
     description "Analyze all idp attack logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
     }
   }
   rpc get-sec-log-report-interval-ipsec-vpn {
     description "Analyze all ipsec-vpn logs";
     input {
       leaf destination-address {
         description "Show item by destination-address";
         type jt:ipaddr;
       }
       leaf event-type {
         description "Show item by event-type";
         type string {
           length "1 .. 64";
         }
       }
       leaf operation {
         description "Operation between multiple parameters";
         type enumeration {
           enum "or" {
             description "Operation or";
           }
         }
       }
       leaf destination-zone {
         description "Show item by destination zone";
         type string {
           length "1 .. 64";
         }
       }
       leaf profile {
         description "Show item by profile";
         type string {
           length "1 .. 64";
         }
       }
       leaf session-id {
         description "Show item by session-id";
         type string {
           length "1 .. 64";
         }
       }
       leaf source-address {
         description "Show item by source-address";
         type jt:ipaddr;
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-dst-country {
         description "Filter the data by dst country";
         type string {
           length "1 .. 64";
         }
       }
       leaf where-src-country {
         description "Filter the data by src country";
         type string {
           length "1 .. 64";
         }
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-screen {
     description "Analyze all screen logs";
     input {
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-session-all {
     description "Analyze all session logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-interval-count {
         description "Partition duration into interval count";
         type union {
           type string {
             pattern "<.*>|$.*";
           }
           type uint32 {
             range "1 .. 30";
           }
         }
       }
     }
   }
   rpc get-sec-log-report-interval-session-close {
     description "Analyze all session-close logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-interval-count {
         description "Partition duration into interval count";
         type union {
           type string {
             pattern "<.*>|$.*";
           }
           type uint32 {
             range "1 .. 30";
           }
         }
       }
     }
   }
   rpc get-sec-log-report-interval-session-create {
     description "Analyze all session-create logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-interval-count {
         description "Partition duration into interval count";
         type union {
           type string {
             pattern "<.*>|$.*";
           }
           type uint32 {
             range "1 .. 30";
           }
         }
       }
     }
   }
   rpc get-sec-log-report-interval-session-deny {
     description "Analyze all session-deny logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-interval-count {
         description "Partition duration into interval count";
         type union {
           type string {
             pattern "<.*>|$.*";
           }
           type uint32 {
             range "1 .. 30";
           }
         }
       }
     }
   }
   rpc get-sec-log-report-interval-threat {
     description "Analyze all threat logs";
     input {
       leaf application {
         description "Show item by application";
         type string {
           length "1 .. 64";
         }
       }
       leaf category {
         description "Show item by category";
         type string {
           length "1 .. 64";
         }
       }
       leaf url {
         description "Show item by url";
         type string {
           length "1 .. 64";
         }
       }
       leaf threat-severity {
         description "Show item by threat-severity";
         type string {
           length "1 .. 64";
         }
       }
       leaf destination-zone {
         description "Show item by destination zone";
         type string {
           length "1 .. 64";
         }
       }
       leaf profile {
         description "Show item by profile";
         type string {
           length "1 .. 64";
         }
       }
       leaf attack-name {
         description "Show item by attack-name";
         type string {
           length "1 .. 64";
         }
       }
       leaf policy-name {
         description "Show item by policy-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf protocol-name {
         description "Show item by protocol name";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-port {
         description "Show item by source port";
         type string {
           length "1 .. 64";
         }
       }
       leaf user {
         description "Show item by user";
         type string {
           length "1 .. 64";
         }
       }
       leaf source-zone {
         description "Show item by source zone";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-all {
     description "Analyze all  logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-antispam {
     description "Analyze all utm antispam logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-av-detected {
     description "Analyze all utm antivirus detected logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-content-filter {
     description "Analyze all utm content filter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-wf {
     description "Analyze all utm webfilter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-wf-blocked {
     description "Analyze all utm webfilter blocked logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-interval-utm-wf-permitted {
     description "Analyze all utm webfilter permiitted logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf application-risk-info {
         description "Show application risk info for interval report";
         type empty;
       }
       leaf application-info-avg {
         description "Show application info average interval report";
         type empty;
       }
       leaf host-activity {
         description "Show host activity for interval report";
         type empty;
       }
       leaf detection-info {
         description "Show detection info for interval report";
         type empty;
       }
       leaf scan-info {
         description "Show scan info for interval report";
         type empty;
       }
       leaf user-activity {
         description "Show user activity for interval report";
         type empty;
       }
       leaf user-activity-avg {
         description "Show user activity average for interval report";
         type empty;
       }
       leaf where-application-risk {
         description "Filter the data by application risk";
         type enumeration {
           enum "high" {
             description "Filter high risk application";
           }
         }
       }
       leaf where-action {
         description "Filter the data by action";
         type enumeration {
           enum "permit" {
             description "Filter permit action";
           }
           enum "block" {
             description "Filter block action";
           }
           enum "quarantine" {
             description "Filter quarantine action";
           }
         }
       }
       leaf where-address {
         description "Filter the data by ip address";
         type jt:ipaddr;
       }
       leaf where-interval-count {
         description "Partition duration into interval count";
         type union {
           type string {
             pattern "<.*>|$.*";
           }
           type uint32 {
             range "1 .. 30";
           }
         }
       }
     }
   }
   rpc get-sec-log-report-summary-all {
     description "Analyze all logs";
     input {
       leaf application {
         description "Show item by application";
         type string {
           length "1 .. 64";
         }
       }
       leaf attack-name {
         description "Show item by attack-name";
         type string {
           length "1 .. 64";
         }
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf category {
         description "Show item by category";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf high-risk-detail {
         description "Show summary of detail on high-risk apps";
         type empty;
       }
       leaf high-risk-action {
         description "Show summary of action on high-risk apps";
         type empty;
       }
       leaf operation {
         description "Operation between multiple parameters";
         type enumeration {
           enum "or" {
             description "Operation or";
           }
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-zone {
         description "Show item by source zone";
         type string {
           length "1 .. 64";
         }
       }
       leaf per-risk-category {
         description "Show summary per risk category";
         type empty;
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf-list expression {
         ordered-by user;
         description "Expression to handle multiple options";
         type jt:policy-algebra;
       }
       leaf reason {
         description "Show item by reason";
         type string {
           length "1 .. 64";
         }
       }
       leaf rule-name {
         description "Show item by rule-name";
         type string {
           length "1 .. 64";
         }
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf threat-severity {
         description "Show item by threat-severity";
         type string {
           length "1 .. 64";
         }
       }
       leaf url {
         description "Show item by url";
         type string {
           length "1 .. 64";
         }
       }
       leaf url-visitor-list {
         description "Show summary of url visitors";
         type empty;
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
   }
   rpc get-sec-log-report-summary-atp-all {
     description "Analyze all atp logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-aamw {
     description "Analyze all atp aamw logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-aamw-http {
     description "Analyze all atp aamw http logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-aamw-mail {
     description "Analyze all atp aamw mail logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-aamw-malware {
     description "Analyze all atp aamw malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-malware {
     description "Analyze all atp malware logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-atp-secintel {
     description "Analyze all atp secintel logs";
     input {
       leaf application {
         description "Show item by application";
         type string {
           length "1 .. 64";
         }
       }
       leaf detection-info {
         description "Show detection info for interval report";
         type empty;
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf session-id {
         description "Show item by session-id";
         type string {
           length "1 .. 64";
         }
       }
       leaf source-address {
         description "Show item by source-address";
         type jt:ipaddr;
       }
       leaf source-zone {
         description "Show item by source zone";
         type string {
           length "1 .. 64";
         }
       }
       leaf threat-severity {
         description "Show item by threat-severity";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-action {
         description "Filter the data by action";
         type enumeration {
           enum "permit" {
             description "Filter permit action";
           }
           enum "block" {
             description "Filter block action";
           }
           enum "quarantine" {
             description "Filter quarantine action";
           }
         }
       }
       leaf where-threat-level {
         description "Filter the data by sky threat level";
         type enumeration {
           enum "high" {
             description "Filter high threat level";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-dns {
     description "Analyze all dns logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-idp-all {
     description "Analyze all idp logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-idp-attack {
     description "Analyze all idp attack logs";
     input {
       leaf application {
         description "Show item by application";
         type string {
           length "1 .. 64";
         }
       }
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf rule-name {
         description "Show item by rule-name";
         type string {
           length "1 .. 64";
         }
       }
       leaf session-id {
         description "Show item by session-id";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-interval-count {
         description "Partition duration into interval count";
         type union {
           type string {
             pattern "<.*>|$.*";
           }
           type uint32 {
             range "1 .. 30";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-ipsec-vpn {
     description "Analyze all ipsec-vpn logs";
     input {
       leaf destination-address {
         description "Show item by destination-address";
         type jt:ipaddr;
       }
       leaf event-type {
         description "Show item by event-type";
         type string {
           length "1 .. 64";
         }
       }
       leaf operation {
         description "Operation between multiple parameters";
         type enumeration {
           enum "or" {
             description "Operation or";
           }
         }
       }
       leaf destination-zone {
         description "Show item by destination zone";
         type string {
           length "1 .. 64";
         }
       }
       leaf profile {
         description "Show item by profile";
         type string {
           length "1 .. 64";
         }
       }
       leaf session-id {
         description "Show item by session-id";
         type string {
           length "1 .. 64";
         }
       }
       leaf source-address {
         description "Show item by source-address";
         type jt:ipaddr;
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
       leaf where-dst-country {
         description "Filter the data by dst country";
         type string {
           length "1 .. 64";
         }
       }
       leaf where-src-country {
         description "Filter the data by src country";
         type string {
           length "1 .. 64";
         }
       }
     }
   }
   rpc get-sec-log-report-summary-screen {
     description "Analyze all screen logs";
     input {
       leaf attack-name {
         description "Show item by attack-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf source-address {
         description "Show item by source-address";
         type jt:ipaddr;
       }
       leaf source-port {
         description "Show item by source port";
         type string {
           length "1 .. 64";
         }
       }
       leaf source-zone {
         description "Show item by source zone";
         type string {
           length "1 .. 64";
         }
       }
       leaf threat-severity {
         description "Show item by threat-severity";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-session-all {
     description "Analyze all session logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-summary-session-close {
     description "Analyze all session-close logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-summary-session-create {
     description "Analyze all session-create logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-summary-session-deny {
     description "Analyze all session-deny logs";
     input {
       leaf application {
         description "Show item by application";
         type string {
           length "1 .. 64";
         }
       }
       leaf-list expression {
         ordered-by user;
         description "Expression to handle multiple options";
         type jt:policy-algebra;
       }
       leaf bandwidth-per-user {
         description "Show average bandwidth per user";
         type empty;
       }
       leaf source-port {
         description "Show item by source port";
         type string {
           length "1 .. 64";
         }
       }
       leaf destination-port {
         description "Show item by destination port";
         type string {
           length "1 .. 64";
         }
       }
       leaf protocol-name {
         description "Show item by protocol name";
         type string {
           length "1 .. 64";
         }
       }
       leaf destination-address {
         description "Show item by destination-address";
         type jt:ipaddr;
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf policy-name {
         description "Show item by policy-name";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-zone {
         description "Show item by source zone";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
     }
   }
   rpc get-sec-log-report-summary-threat {
     description "Analyze all threat logs";
     input {
       leaf application {
         description "Show item by application";
         type string {
           length "1 .. 64";
         }
       }
       leaf category {
         description "Show item by category";
         type string {
           length "1 .. 64";
         }
       }
       leaf url {
         description "Show item by url";
         type string {
           length "1 .. 64";
         }
       }
       leaf threat-severity {
         description "Show item by threat-severity";
         type string {
           length "1 .. 64";
         }
       }
       leaf destination-zone {
         description "Show item by destination zone";
         type string {
           length "1 .. 64";
         }
       }
       leaf profile {
         description "Show item by profile";
         type string {
           length "1 .. 64";
         }
       }
       leaf attack-name {
         description "Show item by attack-name";
         type string {
           length "1 .. 64";
         }
       }
       leaf policy-name {
         description "Show item by policy-name";
         type string {
           length "1 .. 64";
         }
       }
       leaf-list expression {
         ordered-by user;
         description "Expression to handle multiple options";
         type jt:policy-algebra;
       }
       leaf destination-address {
         description "Show item by destination-address";
         type jt:ipaddr;
       }
       leaf destination-port {
         description "Show item by destination port";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf protocol {
         description "Show item by protocol";
         type string {
           length "1 .. 64";
         }
       }
       leaf protocol-name {
         description "Show item by protocol name";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-port {
         description "Show item by source port";
         type string {
           length "1 .. 64";
         }
       }
       leaf user {
         description "Show item by user";
         type string {
           length "1 .. 64";
         }
       }
       leaf source-zone {
         description "Show item by source zone";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf per-risk-category {
         description "Show summary per risk category";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-all {
     description "Analyze all  logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-antispam {
     description "Analyze all utm antispam logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-av-detected {
     description "Analyze all utm antivirus detected logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-content-filter {
     description "Analyze all utm content filter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-wf {
     description "Analyze all utm webfilter logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-wf-blocked {
     description "Analyze all utm webfilter blocked logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-sec-log-report-summary-utm-wf-permitted {
     description "Analyze all utm webfilter permiitted logs";
     input {
       leaf application {
         description "Show item by application";
         type string {
           length "1 .. 64";
         }
       }
       leaf-list expression {
         ordered-by user;
         description "Expression to handle multiple options";
         type jt:policy-algebra;
       }
       leaf category {
         description "Show item by category";
         type string {
           length "1 .. 64";
         }
       }
       leaf destination-address {
         description "Show item by destination-address";
         type jt:ipaddr;
       }
       leaf destination-port {
         description "Show item by destination port";
         type string {
           length "1 .. 64";
         }
       }
       leaf destination-zone {
         description "Show item by destination zone";
         type string {
           length "1 .. 64";
         }
       }
       leaf event-type {
         description "Show item by event-type";
         type string {
           length "1 .. 64";
         }
       }
       leaf operation {
         description "Operation between multiple parameters";
         type enumeration {
           enum "or" {
             description "Operation or";
           }
         }
       }
       leaf per-risk-category {
         description "Show summary per risk category";
         type empty;
       }
       leaf profile {
         description "Show item by profile";
         type string {
           length "1 .. 64";
         }
       }
       leaf protocol {
         description "Show item by protocol";
         type string {
           length "1 .. 64";
         }
       }
       leaf reason {
         description "Show item by reason";
         type string {
           length "1 .. 64";
         }
       }
       leaf session-id {
         description "Show item by session-id";
         type string {
           length "1 .. 64";
         }
       }
       leaf source-address {
         description "Show item by source-address";
         type jt:ipaddr;
       }
       leaf source-interface {
         description "Show item by source interface";
         type string {
           length "1 .. 64";
         }
       }
       leaf source-name {
         description "Show item by name";
         type string {
           length "1 .. 64";
         }
       }
       leaf source-port {
         description "Show item by source port";
         type string {
           length "1 .. 64";
         }
       }
       leaf source-zone {
         description "Show item by source zone";
         type string {
           length "1 .. 64";
         }
       }
       leaf url {
         description "Show item by url";
         type string {
           length "1 .. 64";
         }
       }
       leaf user {
         description "Show item by user";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
       leaf start-from {
         description "Show item from a given value";
         type union {
           type uint32;
           type string {
             pattern "<.*>|$.*";
           }
         }
       }
       leaf count {
         description "Number of items to show";
         type union {
           type string {
             pattern "<.*>|$.*";
           }
           type uint32 {
             range "1 .. 65535";
           }
         }
       }
       leaf per-user-count {
         description "Number of users to show";
         type union {
           type string {
             pattern "<.*>|$.*";
           }
           type uint32 {
             range "1 .. 10";
           }
         }
       }
       leaf where-dst-country {
         description "Filter the data by dst country";
         type string {
           length "1 .. 64";
         }
       }
       leaf-list where-exclude-log {
         ordered-by user;
         description "Exclude the specific logs";
         type enumeration {
           enum "atp-aamw" {
             description "Exclude atp-aamw log";
           }
           enum "utm-webfilter" {
             description "Exclude utm-webfilter log";
           }
         }
         max-elements 8;
       }
       leaf where-src-country {
         description "Filter the data by src country";
         type string {
           length "1 .. 64";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
       leaf high-risk-detail {
         description "Show summary of detail on high-risk apps";
         type empty;
       }
       leaf high-risk-action {
         description "Show summary of action on high-risk apps";
         type empty;
       }
       leaf summary-category-file-count {
         description "Show summary of diff category file-count";
         type empty;
       }
       leaf summary-target-email-file-count {
         description "Show summary of target-email and file-count";
         type empty;
       }
       leaf summary-threat-new-and-known-malware {
         description "Show summary of new and known malware threats";
         type empty;
       }
       leaf url-visitor-list {
         description "Show summary of url visitors";
         type empty;
       }
     }
   }
   rpc get-security-log-profile-template {
     description "Show security log profile template info";
     input {
       leaf template-name {
         description "Specify the rtlog profile template name";
         type enumeration {
           enum "sd-wan" {
             description "Template sd-wan";
           }
           enum "unified-ngfw" {
             description "Template unified-ngfw";
           }
           enum "traditional-firewall" {
             description "Template traditional-firewall";
           }
         }
         mandatory true;
       }
     }
     output {
       container security-log-profile-template {
         uses security-log-profile-template-block;
       }
     }
   }
   rpc get-security-log-profile-config {
     description "Show security log profile config info";
     input {
       leaf profile-name {
         description "Specify the rtlog profile name";
         type string {
           length "1 .. 64";
         }
         mandatory true;
       }
     }
     output {
       container security-log-profile-config {
         uses security-log-profile-config-block;
       }
     }
   }
   rpc get-security-log-radius-stream {
     description "Radius server counters/information";
     input {
       choice stream {
         case stream-name {
           leaf stream-name {
             description "Specify the stream name";
             type string;
           }
         }
         case all {
           leaf all {
             description "Display all streams information";
             type empty;
           }
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       container security-log-radius-stream {
         uses security-log-radius-stream-block;
       }
     }
   }
   rpc get-casb-policy-information {
     description "Show the cloud access security broker policies configured";
     input {
       uses command-forwarding;
       leaf policy-name {
         description "Policy name";
         type string;
       }
     }
     output {
       container casb-policy-information {
         uses casb-policy-information-block;
       }
     }
   }
   rpc get-tpm-status {
     description "Show TPM status";
     input {
       choice daemon-select {
         case logical-system {
           leaf logical-system {
             description "Name of logical system, or 'all'";
             type string {
             }
           }
         }
       }
     }
     output {
       container tpm-status {
         uses tpm-status-block;
       }
     }
   }
   rpc get-hsm-status {
     description "Show HSM status";
     output {
       container hsm-status {
         uses hsm-status-block;
       }
     }
   }
   rpc get-pki-certificate-request {
     description "Show PKCS-10 certificate request information";
     input {
       uses command-forwarding;
       choice daemon-select {
         case logical-system {
         }
       }
       leaf certificate-id {
         description "Certificate identifier";
         type string {
           length "1 .. 32";
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-ca-certificate {
     description "Show certificate-authority certificate information";
     input {
       uses command-forwarding;
       choice daemon-select {
         case logical-system {
         }
       }
       choice ca-cert-choice {
         case ca-profile {
           leaf ca-profile {
             description "Certificate authority profile";
             type string {
               length "1 .. 32";
             }
           }
         }
         case ca-profile-group {
           leaf ca-profile-group {
             description "Show CA profile group";
             type string {
               length "1 .. 32";
             }
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-node-local-local-certificate {
     description "Show router certificate information";
     input {
       uses command-forwarding;
       choice daemon-select {
         case logical-system {
         }
       }
       choice certificate-choice {
         case certificate-id {
           leaf certificate-id {
             description "Certificate identifier";
             type string {
               length "1 .. 32";
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-node-local-certificate-request {
     description "Show PKCS-10 certificate request information";
     input {
       uses command-forwarding;
       choice daemon-select {
         case logical-system {
         }
       }
       leaf certificate-id {
         description "Certificate identifier";
         type string {
           length "1 .. 32";
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-local-certificate {
     description "Show router certificate information";
     input {
       uses command-forwarding;
       choice daemon-select {
         case logical-system {
         }
       }
       choice certificate-choice {
         case certificate-id {
           leaf certificate-id {
             description "Certificate identifier";
             type string {
               length "1 .. 32";
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       container x509-pki-certificate-info-list {
         uses x509-pki-certificate-info-list-block;
       }
     }
   }
   rpc get-pki-crl {
     description "Show certificate revocation list information";
     input {
       uses command-forwarding;
       choice daemon-select {
         case logical-system {
         }
       }
       leaf ca-profile {
         description "Certificate authority profile";
         type string {
           length "1 .. 32";
         }
       }
       leaf level {
         default "brief";
         type enumeration {
           enum "brief" {
             description "Display brief output";
           }
           enum "detail" {
             description "Display detailed output";
           }
         }
       }
     }
     output {
       container x509-pkid-crl-information-list {
         uses x509-pkid-crl-information-list-block;
       }
     }
   }
   rpc get-pki-statistics {
     description "Show PKI related statistics";
     input {
       uses command-forwarding;
       choice daemon-select {
         case logical-system {
         }
       }
       leaf level {
         default "brief";
         type enumeration {
           enum "brief" {
             description "Display brief output";
           }
           enum "detail" {
             description "Display detailed output";
           }
         }
       }
     }
     output {
       container pki-statistics {
         uses pki-statistics-block;
       }
     }
   }
   rpc get-ssl-cloud-certificate {
     description "Show cloud certificate information";
     input {
       uses command-forwarding;
       choice certificate-choice {
         case certificate-id {
           leaf certificate-id {
             description "Certificate identifier";
             type string {
               length "1 .. 32";
             }
           }
         }
       }
     }
     output {
       container ssl-cloud-certificates-information {
         uses ssl-cloud-certificates-information-block;
       }
     }
   }
   rpc get-pki-encryption-status {
     description "Show PKI encryption status";
     output {
       container pki-encryption-status {
         uses pki-encryption-status-block;
       }
     }
   }
   rpc get-pending-redistribution-cmds {
     description "Show tunnel migration commands in the pending state";
     input {
       uses command-forwarding;
       leaf gateway-name {
         description "Gateway name";
         type string {
           length "1 .. 32";
         }
       }
     }
   }
   rpc get-security-associations-information {
     description "Show IPSec security association information";
     input {
       uses command-forwarding;
       leaf level {
         default "brief";
         type enumeration {
           enum "brief" {
             description "Display brief output";
           }
           enum "detail" {
             description "Display detailed output";
           }
           enum "extensive" {
             description "Display extensive output";
           }
         }
       }
       leaf family {
         description "Show IPSec security association information by family";
         default "inet";
         type enumeration {
           enum "inet" {
             description "Show IPv4";
           }
           enum "inet6" {
             description "Show IPv6";
           }
         }
       }
       leaf sa-type {
         description "Show IPSec security association by type";
         type enumeration {
           enum "shortcut" {
             description "Show Shortcut SAs";
           }
         }
       }
       leaf show-index-ipsec-security-association {
         description "Index of security association";
         type union {
           type string {
             pattern "<.*>|$.*";
           }
           type uint32 {
             range "1 .. 4294967295";
           }
         }
       }
       leaf show-srg-id-ipsec-security-association {
         description "Index of srg-id";
         type union {
           type string {
             pattern "<.*>|$.*";
           }
           type uint32 {
             range "1 .. 20";
           }
         }
       }
       leaf node-local {
         description "Show IPSec security association of node-local tunnels";
         type empty;
       }
       leaf show-vpnname-ipsec-security-association {
         description "VPN name";
         default "all";
         type string;
       }
       leaf show-trafficselectorname-ipsec-security-association {
         description "Traffic-selector name";
         default "all";
         type string;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container security-associations-information {
         uses security-associations-information-block;
       }
     }
   }
   rpc get-ha-link-encryptioninformation {
     description "Show IPSec security association for HA Link Encryption";
     input {
       uses command-forwarding;
       leaf level {
         default "brief";
         type enumeration {
           enum "brief" {
             description "Display brief output";
           }
           enum "detail" {
             description "Display detailed output";
           }
           enum "extensive" {
             description "Display extensive output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
       leaf show-vpnname-ipsec-security-association {
         description "VPN name";
         default "all";
         type string;
       }
     }
     output {
       container security-associations-information {
         uses security-associations-information-block;
       }
     }
   }
   rpc get-control-plane-security-associations-information {
     description "Show IPSec control plane security association information";
     input {
       uses command-forwarding;
       leaf level {
         default "brief";
         type enumeration {
           enum "brief" {
             description "Display brief output";
           }
           enum "detail" {
             description "Display detailed output";
           }
         }
       }
       leaf show-saname-ipsec-control-plane-security-association {
         description "SA name";
         default "all";
         type string;
       }
       leaf show-ha-link-ipsec-statistics {
         description "Show statistics for ha-link encryption tunnel";
         type empty;
       }
     }
   }
   rpc get-ipsec-statistics-information {
     description "Show IPSec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf show-index-ipsec-statistics {
         description "Index of Security Association";
         type union {
           type string {
             pattern "<.*>|$.*";
           }
           type uint32 {
             range "1 .. 4294967295";
           }
         }
       }
       leaf show-ha-link-encryption-ipsec-stats {
         description "Show statistics for ha-link encryption tunnel";
         type empty;
       }
       leaf show-srg-ipsec-statistics {
         description "Show statistics for srg";
         type union {
           type string {
             pattern "<.*>|$.*";
           }
           type uint32 {
             range "1 .. 20";
           }
         }
       }
     }
     output {
       container usp-ipsec-total-statistics-information {
         uses usp-ipsec-total-statistics-information-block;
       }
     }
   }
   rpc get-inactive-tunnels {
     description "Inactive-tunnels";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
       leaf show-srg-id-ipsec-security-association {
         description "Index of srg-id";
         type union {
           type string {
             pattern "<.*>|$.*";
           }
           type uint32 {
             range "1 .. 20";
           }
         }
       }
       leaf node-local {
         description "Show Inactive node-local tunnels";
         type empty;
       }
       leaf show-vpnname-ipsec-security-association {
         description "VPN name";
         default "all";
         type string;
       }
       leaf sa-type {
         description "Show inactive IPSec SAs by type";
         type enumeration {
           enum "shortcut" {
             description "Show Shortcut SAs";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container ipsec-unestablished-tunnel-information {
         uses ipsec-unestablished-tunnel-information-block;
       }
     }
   }
   rpc get-l2-ha-inactive-tunnels {
     description "Show inactive IPSec security association for HA Link Encryption";
     input {
       uses command-forwarding;
       leaf level {
         default "brief";
         type enumeration {
           enum "brief" {
             description "Display brief output";
           }
           enum "detail" {
             description "Display detailed output";
           }
         }
       }
       leaf show-index-ipsec-security-association {
         description "Index of security association";
         type union {
           type string {
             pattern "<.*>|$.*";
           }
           type uint32 {
             range "1 .. 4294967295";
           }
         }
       }
       leaf show-vpnname-ipsec-security-association {
         description "VPN name";
         default "all";
         type string;
       }
     }
     output {
       container ipsec-unestablished-tunnel-information {
         uses ipsec-unestablished-tunnel-information-block;
       }
     }
   }
   rpc get-ipsec-next-hop-tunnel-information {
     description "Show manual and auto next-hop-tunnel entries";
     input {
       uses command-forwarding;
       leaf interface-name {
         description "Name of secure tunnel logical interface";
         default "all";
         type string;
       }
       leaf family {
         description "Show IPSec next-hop-tunnel entries by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
     }
   }
   rpc get-ipsec-traffic-selector-information {
     description "Show traffic-selector information for a st0 interface";
     input {
       uses command-forwarding;
       leaf interface-name {
         description "Name of secure tunnel logical interface";
         type string;
         mandatory true;
       }
       leaf source-address {
         description "Source IP address";
         type jt:ipprefix-mandatory;
       }
       leaf destination-address {
         description "Destination IP address";
         type jt:ipprefix-mandatory;
       }
       leaf protocol {
         description "TS protocol id";
         type string;
       }
       leaf source-port {
         description "TS source port number";
         type string;
       }
       leaf destination-port {
         description "TS destination port number";
         type string;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-ipsec-tunnel-event-statistics {
     description "Show tunnel event statstics";
     input {
       uses command-forwarding;
     }
     output {
       container ipsec-tunnel-event-statistics {
         uses ipsec-tunnel-event-statistics-block;
       }
     }
   }
   rpc get-ipsec-tunnel-distribution {
     description "Show tunnel distribution";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf level {
         default "brief";
         type enumeration {
           enum "brief" {
             description "Display brief IPsec tunnel-distribution (default)";
           }
           enum "summary" {
             description "Display IPsec tunnel-distribution summary info";
           }
           enum "summary-cpuload" {
             description "Display IPsec tunnel-distribution summary info with CPU load";
           }
         }
       }
       leaf srg-id {
         description "Index of srg-id";
         type union {
           type string {
             pattern "<.*>|$.*";
           }
           type uint32 {
             range "1 .. 20";
           }
         }
       }
     }
     output {
       container ipsec-tunnel-distribution-information {
         uses ipsec-tunnel-distribution-information-block;
       }
     }
   }
   rpc get-ike-peers-statistics-information {
     description "Show IKE Peers Statistics";
     input {
       choice ike-peers-cmd-params {
         case level {
           leaf level {
             type enumeration {
               enum "summary" {
                 description "Summary";
               }
             }
           }
         }
         case gateway-name {
           leaf gateway-name {
             description "IKE Gateway Name";
             type string {
               length "1 .. 32";
             }
           }
         }
       }
     }
     output {
       container ike-peers-statistics-information {
         uses ike-peers-statistics-information-block;
       }
     }
   }
   rpc get-ike-peers-in-progress-information {
     description "Show IKE In-progress Peers ";
     input {
       leaf level {
         default "brief";
         type enumeration {
           enum "brief" {
             description "Display brief output";
           }
           enum "detail" {
             description "Display detailed output";
           }
         }
       }
       leaf remote-ip-address {
         description "Remote IP address";
         type jt:ipaddr;
       }
       leaf local-ip-address {
         description "Local IP address";
         type jt:ipaddr;
       }
       leaf index {
         description "Index";
         type union {
           type uint32;
           type string {
             pattern "<.*>|$.*";
           }
         }
       }
       leaf gateway-name {
         description "IKE Gateway Name";
         type string {
           length "1 .. 32";
         }
       }
       leaf role {
         description "Role";
         type enumeration {
           enum "initiator" {
             description "Remote Peer is Initiator";
           }
           enum "responder" {
             description "Remote peer is Responder";
           }
         }
       }
     }
     output {
       container ike-peers-in-progress-information {
         uses ike-peers-in-progress-information-block;
       }
     }
   }
   rpc get-ike-peers-failed-information {
     description "Show IKE Failed Peers ";
     input {
       leaf level {
         default "brief";
         type enumeration {
           enum "brief" {
             description "Display brief output";
           }
           enum "detail" {
             description "Display detailed output";
           }
         }
       }
       leaf remote-ip-address {
         description "Remote IP address";
         type jt:ipaddr;
       }
       leaf local-ip-address {
         description "Local IP address";
         type jt:ipaddr;
       }
       leaf index {
         description "Index";
         type union {
           type uint32;
           type string {
             pattern "<.*>|$.*";
           }
         }
       }
       leaf gateway-name {
         description "IKE Gateway Name";
         type string {
           length "1 .. 32";
         }
       }
       leaf role {
         description "Role";
         type enumeration {
           enum "initiator" {
             description "Remote Peer is Initiator";
           }
           enum "responder" {
             description "Remote peer is Responder";
           }
         }
       }
     }
     output {
       container ike-peers-failed-information {
         uses ike-peers-failed-information-block;
       }
     }
   }
   rpc get-ike-peers-blocked-information {
     description "Show IKE Blocked Peers ";
     input {
       leaf level {
         default "brief";
         type enumeration {
           enum "brief" {
             description "Display brief output";
           }
           enum "detail" {
             description "Display detailed output";
           }
         }
       }
       leaf remote-ip-address {
         description "Remote IP address";
         type jt:ipaddr;
       }
       leaf local-ip-address {
         description "Local IP address";
         type jt:ipaddr;
       }
       leaf index {
         description "Index";
         type union {
           type uint32;
           type string {
             pattern "<.*>|$.*";
           }
         }
       }
       leaf gateway-name {
         description "IKE Gateway Name";
         type string {
           length "1 .. 32";
         }
       }
       leaf role {
         description "Role";
         type enumeration {
           enum "initiator" {
             description "Remote Peer is Initiator";
           }
           enum "responder" {
             description "Remote peer is Responder";
           }
         }
       }
       leaf blocklist-name {
         description "IKE Blocklist Name";
         type string {
           length "1 .. 32";
         }
       }
     }
     output {
       container ike-peers-blocked-information {
         uses ike-peers-blocked-information-block;
       }
     }
   }
   rpc get-ike-peers-backoff-information {
     description "Show IKE Backoff Peers ";
     input {
       leaf level {
         default "brief";
         type enumeration {
           enum "brief" {
             description "Display brief output";
           }
           enum "detail" {
             description "Display detailed output";
           }
         }
       }
       leaf remote-ip-address {
         description "Remote IP address";
         type jt:ipaddr;
       }
       leaf local-ip-address {
         description "Local IP address";
         type jt:ipaddr;
       }
       leaf index {
         description "Index";
         type union {
           type uint32;
           type string {
             pattern "<.*>|$.*";
           }
         }
       }
       leaf gateway-name {
         description "IKE Gateway Name";
         type string {
           length "1 .. 32";
         }
       }
       leaf role {
         description "Role";
         type enumeration {
           enum "initiator" {
             description "Remote Peer is Initiator";
           }
           enum "responder" {
             description "Remote peer is Responder";
           }
         }
       }
     }
     output {
       container ike-peers-backoff-information {
         uses ike-peers-backoff-information-block;
       }
     }
   }
   rpc get-pre-shared-key {
     description "Show IKE pre-shared key information for a particular group-ike-id user";
     input {
       uses command-forwarding;
       leaf user-id {
         description "IKE user-id value";
         type string {
           length "1 .. 255";
         }
         mandatory true;
       }
       choice ike-psk {
         case master-key {
           leaf master-key {
             description "Master pre-shared key";
             type string {
               length "1 .. 255";
             }
             mandatory true;
           }
         }
         case gateway-name {
           leaf gateway-name {
             description "Gateway name";
             type string {
               length "1 .. 32";
             }
           }
         }
       }
     }
     output {
       container ike-show-pre-shared-key-information {
         uses ike-show-pre-shared-key-information-block;
       }
     }
   }
   rpc get-ike-config-management-statistics {
     description "Show IKE configuration management daemon statistics";
     input {
       uses command-forwarding;
       leaf level {
         default "brief";
         type enumeration {
           enum "brief" {
             description "Display brief(Non-zero) output";
           }
           enum "detail" {
             description "Display detailed(including zeros) output";
           }
         }
       }
     }
     output {
       container ike-config-management-statistics-information {
         uses ike-config-management-statistics-information-block;
       }
     }
   }
   rpc get-ike-config-management-snmp-stats {
     description "Show SNMP walk/get/get-next statistics";
     input {
       leaf level {
         default "brief";
         type enumeration {
           enum "brief" {
             description "Display brief(Non-zero) output";
           }
           enum "detail" {
             description "Display detailed(including zeros) output";
           }
         }
       }
     }
     output {
       container ike-config-management-snmp-stats {
         uses ike-config-management-snmp-stats-block;
       }
     }
   }
   rpc get-ike-config-management-memory-stats {
     description "Show IKEMD memory statistics";
     input {
       leaf level {
         default "brief";
         type enumeration {
           enum "brief" {
             description "Display brief(Non-zero) output";
           }
           enum "detail" {
             description "Display detailed(including zeros) output";
           }
         }
       }
     }
     output {
       container ike-config-management-memory-stats {
         uses ike-config-management-memory-stats-block;
       }
     }
   }
   rpc get-ike-config-management-manual-sa-stats {
     description "Show manual-sa config related statistics";
     input {
       leaf level {
         default "brief";
         type enumeration {
           enum "brief" {
             description "Display brief(Non-zero) output";
           }
           enum "detail" {
             description "Display detailed(including zeros) output";
           }
         }
       }
     }
     output {
       container ike-config-management-manual-sa-stats {
         uses ike-config-management-manual-sa-stats-block;
       }
     }
   }
   rpc get-ike-security-associations-information {
     description "Show IKE security association information";
     input {
       uses command-forwarding;
       leaf peer-address {
         description "IP address of the peer";
         type jt:ipaddr;
       }
       leaf level {
         default "brief";
         type enumeration {
           enum "brief" {
             description "Show brief output (default)";
           }
           enum "detail" {
             description "Show detailed output";
           }
         }
       }
       leaf family {
         description "Show IKE security association by family";
         default "inet";
         type enumeration {
           enum "inet" {
             description "Show IPv4";
           }
           enum "inet6" {
             description "Show IPv6";
           }
         }
       }
       leaf show-index-ike-security-association {
         description "Index of security association";
         type union {
           type string {
             pattern "<.*>|$.*";
           }
           type uint32 {
             range "1 .. 4294967295";
           }
         }
       }
       leaf show-srg-id-ike-security-association {
         description "Index of srg-id";
         type union {
           type string {
             pattern "<.*>|$.*";
           }
           type uint32 {
             range "1 .. 20";
           }
         }
       }
       leaf node-local {
         description "Show IKE security association of node-local tunnels";
         type empty;
       }
       leaf sa-type {
         description "Show IKE security association by type";
         type enumeration {
           enum "shortcut" {
             description "Show Shortcut SAs";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       container ike-security-associations-information {
         uses ike-security-associations-information-block;
       }
     }
   }
   rpc get-l2-ha-ike-security-associations-information {
     description "Show IKE security association for HA Link Encryption";
     input {
       uses command-forwarding;
       leaf peer-address {
         description "IP address of the peer";
         type jt:ipaddr;
       }
       leaf level {
         default "brief";
         type enumeration {
           enum "brief" {
             description "Show brief output (default)";
           }
           enum "detail" {
             description "Show detailed output";
           }
         }
       }
       leaf show-index-ike-security-association {
         description "Index of security association";
         type union {
           type string {
             pattern "<.*>|$.*";
           }
           type uint32 {
             range "1 .. 4294967295";
           }
         }
       }
     }
     output {
       container ike-security-associations-information {
         uses ike-security-associations-information-block;
       }
     }
   }
   rpc get-ike-active-peers-information {
     description "Show IKE active peers ";
     input {
       uses command-forwarding;
       leaf level {
         default "brief";
         type enumeration {
           enum "brief" {
             description "Display brief output";
           }
           enum "detail" {
             description "Display detailed output";
           }
           enum "stats" {
             description "Display detailed output along with stats";
           }
         }
       }
       leaf peer-address {
         description "IP of peer";
         type jt:ipaddr;
       }
       leaf local-address {
         description "Local gateway IP address";
         type jt:ipaddr;
       }
       leaf port {
         description "Port number of peer";
         type union {
           type string {
             pattern "<.*>|$.*";
           }
           type uint32 {
             range "1 .. 65535";
           }
         }
       }
       leaf local-port {
         description "Local gateway port number";
         type union {
           type string {
             pattern "<.*>|$.*";
           }
           type uint32 {
             range "1 .. 65535";
           }
         }
       }
       leaf ha-link-encryption {
         description "Show IKE active peers for HA link encryption";
         type empty;
       }
       leaf ike-id {
         description "IKE ID";
         default "all";
         type string;
       }
       leaf local-ike-id {
         description "Local gateway IKE ID";
         default "all";
         type string;
       }
       leaf srg-id {
         description "Index of srg-id";
         type union {
           type string {
             pattern "<.*>|$.*";
           }
           type uint32 {
             range "1 .. 20";
           }
         }
       }
       leaf node-local {
         description "Show IKE active peers of node-local tunnels";
         type empty;
       }
       leaf routing-instance {
         description "Name of the local gateway routing-instance";
         default "all";
         type string;
       }
       leaf aaa-username {
         description "AAA username";
         default "all";
         type string;
       }
       leaf debug {
         description "Show additional peer-entry debug information";
         type empty;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       container ike-active-peers-information {
         uses ike-active-peers-information-block;
       }
     }
   }
   rpc get-config-ike-debug {
     description "Show current enabled IKE debug information";
     input {
       uses command-forwarding;
     }
     output {
       container security-ike-debug-info {
         uses security-ike-debug-info-block;
       }
     }
   }
   rpc get-iked-tunnel-mapping-information {
     description "Display tunnel mapping info for site-to-site tunnels";
     input {
       uses command-forwarding;
       leaf level {
         default "brief";
         type enumeration {
           enum "brief" {
             description "Display brief tunnel-mapping (default)";
           }
           enum "summary" {
             description "Display tunnel-mapping summary info";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       container iked-tunnel-mapping-information {
         uses iked-tunnel-mapping-information-block;
       }
     }
   }
   rpc get-gvpn-security-associations-information {
     description "Show IPSec security association information";
     input {
       uses command-forwarding;
       leaf level {
         default "brief";
         type enumeration {
           enum "brief" {
             description "Display brief output";
           }
           enum "detail" {
             description "Display detailed output";
           }
         }
       }
       leaf show-gvpn-index-ipsec-security-association {
         description "Index of security association";
         default "0";
         type union {
           type uint32;
           type string {
             pattern "<.*>|$.*";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf group-id {
         description "Group VPN identification number";
         type union {
           type string {
             pattern "<.*>|$.*";
           }
           type uint32 {
             range "1 .. 4294967295";
           }
         }
       }
     }
     output {
       container ipsec-security-associations-information {
         uses ipsec-security-associations-information-block;
       }
     }
   }
   rpc get-gvpn-ipsec-statistics-information {
     description "Show IPSec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf show-gvpn-index-ipsec-statistics {
         description "Index of Security Association";
         default "0";
         type union {
           type uint32;
           type string {
             pattern "<.*>|$.*";
           }
         }
       }
     }
     output {
       container usp-ipsec-total-statistics-information {
         uses usp-ipsec-total-statistics-information-block;
       }
     }
   }
   rpc get-gvpn-inactive-tunnels {
     description "Inactive-tunnels";
     input {
       uses command-forwarding;
       leaf level {
         default "brief";
         type enumeration {
           enum "brief" {
             description "Display brief output";
           }
           enum "detail" {
             description "Display detailed output";
           }
         }
       }
       leaf group-id {
         description "Group VPN identification number";
         type union {
           type string {
             pattern "<.*>|$.*";
           }
           type uint32 {
             range "1 .. 4294967295";
           }
         }
       }
     }
     output {
       container ipsec-unestablished-tunnel-information {
         uses ipsec-unestablished-tunnel-information-block;
       }
     }
   }
   rpc get-gvpn-ike-security-associations-information {
     description "Show IKE security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container ike-security-associations-information {
         uses ike-security-associations-information-block;
       }
     }
   }
   rpc get-gvpn-kek-security-associations-information {
     description "Show KEK security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container ike-security-associations-information {
         uses ike-security-associations-information-block;
       }
     }
   }
   rpc get-gvpn-policy-information {
     description "Show group vpn policies";
     input {
       uses command-forwarding;
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
     }
     output {
       container gvpn-policy-information {
         uses gvpn-policy-information-block;
       }
     }
   }
   rpc get-security-group-vpn-server-registered-members {
     description "Show group VPN registered members for group VPN server";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-address {
           leaf peer-address {
             description "Peer IP address";
             type jt:ipaddr;
           }
         }
       }
       leaf level {
         default "brief";
         type enumeration {
           enum "brief" {
             description "Show brief output (default)";
           }
           enum "detail" {
             description "Show detailed output";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-security-group-vpn-server-kek-sa {
     description "Show KEK security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-security-group-vpn-server-security-information {
     description "Show IPSec security association information for group VPN server";
     input {
       uses command-forwarding;
       leaf level {
         default "brief";
         type enumeration {
           enum "brief" {
             description "Show brief output (default)";
           }
           enum "detail" {
             description "Show detailed output";
           }
         }
       }
       choice group_choice {
         description "Specify group or group-id filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-security-group-vpn-server-ike-security-associations-information {
     description "Show IKE security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case peer-address {
           leaf peer-address {
             description "Peer IP address";
             type jt:ipaddr;
           }
         }
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-security-group-vpn-svr-svr-cluster-info {
     description "Show group vpn server cluster information";
     input {
       uses command-forwarding;
       leaf level {
         default "brief";
         type enumeration {
           enum "brief" {
             description "Show brief output (default)";
           }
           enum "detail" {
             description "Show detailed output";
           }
         }
       }
       choice group_cluster_index_choice {
         description "Specify group, group-id or peer gateway filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-gateway {
           leaf peer-gateway {
             description "Show specified peer server gateway name";
             type string {
               length "1 .. 32";
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
   }
   rpc get-security-group-vpn-server-stats {
     description "Show group server statistics";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container security-group-vpn-server-stats {
         uses security-group-vpn-server-stats-block;
       }
     }
   }
   rpc get-internal-security-association {
     description "Show internal security association";
     input {
       uses command-forwarding;
     }
     output {
       container internal-sa-information {
         uses internal-sa-information-block;
       }
     }
   }
   rpc get-idp-application-system-cache {
     description "Show IDP application system cache";
     input {
       uses command-forwarding;
     }
     output {
       container idp-application-system-cache-information {
         uses idp-application-system-cache-information-block;
       }
     }
   }
   rpc get-idp-active-policy {
     description "Show active IDP policy";
     status deprecated;
     input {
       uses command-forwarding;
     }
     output {
       container idp-version-information {
         uses idp-version-information-block;
       }
     }
   }
   rpc get-idp-policy-commit-status {
     description "Show the status of ongoing policy compilation and load";
     input {
       uses command-forwarding;
       leaf clear {
         description "Clears the policy commit status";
         type empty;
       }
     }
     output {
       container idp-policy-commit-status {
         uses idp-policy-commit-status-block;
       }
     }
   }
   rpc get-idp-security-package-proxy-information {
     description "Show proxy profile details";
     input {
       uses command-forwarding;
     }
     output {
       container idp-security-package-proxy-profile {
         uses idp-security-package-proxy-profile-block;
       }
     }
   }
   rpc get-idp-security-package-information {
     description "Show the version of currently installed security-package";
     input {
       uses command-forwarding;
       leaf detail {
         description "Show last security-package version which failed dataplane validation";
         type empty;
       }
     }
     output {
       container idp-security-package-information {
         uses idp-security-package-information-block;
       }
     }
   }
   rpc get-idp-jist-package-information {
     description "Show the version of currently installed JIST package";
     input {
       uses command-forwarding;
     }
     output {
       container idp-jist-package-information {
         uses idp-jist-package-information-block;
       }
     }
   }
   rpc get-idp-recent-security-package-information {
     description "List ten most recent security package versions";
     input {
       uses command-forwarding;
     }
     output {
       container idp-recent-security-package-information {
         uses idp-recent-security-package-information-block;
       }
     }
   }
   rpc get-idp-memory-information {
     description "Show IDP data plane memory statistics";
     input {
       uses command-forwarding;
     }
     output {
       container idp-memory-information {
         uses idp-memory-information-block;
       }
     }
   }
   rpc get-idp-subscriber-policy-list {
     description "Show the currently used policies";
     input {
       uses command-forwarding;
     }
     output {
       container idp-subscriber-policy-list {
         uses idp-subscriber-policy-list-block;
       }
     }
   }
   rpc get-idp-policy-template-information {
     description "Show available policy templates";
     input {
       uses command-forwarding;
     }
     output {
       leaf idp-policy-template-information {
         type string;
         description "List available IDP policy templates";
       }
     }
   }
   rpc get-idp-status-information {
     description "Show IDP status";
     input {
       uses command-forwarding;
     }
     output {
       container idp-status-information {
         uses idp-status-information-block;
       }
     }
   }
   rpc get-idp-detail-status-information {
     description "Show IDP detail status";
     input {
       uses command-forwarding;
     }
     output {
       container idp-detail-status-information {
         uses idp-detail-status-information-block;
       }
     }
   }
   rpc get-idp-predefined-attack-groups {
     description "Show predefined attack groups";
     output {
       container idp-predefined-attack-groups {
         uses idp-predefined-attack-groups-block;
       }
     }
   }
   rpc get-idp-predefined-attack-group-filters {
     description "Configure filters";
     input {
       uses command-forwarding;
       leaf category {
         description "Category of attack group";
         type string;
       }
     }
   }
   rpc get-idp-predefined-attacks {
     description "Show predefined attacks";
     output {
       container idp-predefined-attacks {
         uses idp-predefined-attacks-block;
       }
     }
   }
   rpc get-idp-predefined-attack-filters {
     description "Configure filters";
     input {
       uses command-forwarding;
       leaf category {
         description "Category of attack";
         type string;
       }
       leaf severity {
         description "Severity of attack";
         type enumeration {
           enum "info" {
             description "Provide information of attack when it matches";
           }
           enum "warning" {
             description "The attack is a minor one";
           }
           enum "minor" {
             description "The attack is a minor one";
           }
           enum "major" {
             description "The attack is a major one";
           }
           enum "critical" {
             description "The attack is a critical one";
           }
         }
       }
       leaf direction {
         description "Direction of attack";
         type enumeration {
           enum "client-to-server" {
             description "Select attacks from client to server";
           }
           enum "server-to-client" {
             description "Select attacks from server to client";
           }
           enum "any" {
             description "Select attacks which can occur in either direction";
           }
           enum "exclude-client-to-server" {
             description "Filter out attacks from client to server";
           }
           enum "exclude-server-to-client" {
             description "Filter out attacks from server to client";
           }
           enum "exclude-any" {
             description "Filter out attacks which are in any direction";
           }
         }
       }
     }
   }
   rpc get-idp-counter-information {
     description "Show IDP counters";
     output {
       container idp-counter-information {
         uses idp-counter-information-block;
       }
     }
   }
   rpc get-idp-counters-packet {
     description "Show IDP Packet counters";
     input {
       uses command-forwarding;
       choice lsys {
         case logical-system {
         }
         case tenant {
         }
       }
     }
     output {
       container idp-counter-information {
         uses idp-counter-information-block;
       }
     }
   }
   rpc get-idp-counters-tcp-reass {
     description "Show IDP Reassembler counters";
     input {
       uses command-forwarding;
       choice lsys {
         case logical-system {
         }
         case tenant {
         }
       }
     }
     output {
       container idp-counter-information {
         uses idp-counter-information-block;
       }
     }
   }
   rpc get-idp-counters-ips {
     description "Show IPS counters";
     input {
       uses command-forwarding;
       choice lsys {
         case logical-system {
         }
         case tenant {
         }
       }
     }
     output {
       container idp-counter-information {
         uses idp-counter-information-block;
       }
     }
   }
   rpc get-idp-counters-flow {
     description "Show IDP Flow counters";
     input {
       uses command-forwarding;
       choice lsys {
         case logical-system {
         }
         case tenant {
         }
       }
     }
     output {
       container idp-counter-information {
         uses idp-counter-information-block;
       }
     }
   }
   rpc get-idp-counters-dfa {
     description "Show IDP DFA counters";
     input {
       uses command-forwarding;
       choice lsys {
         case logical-system {
         }
         case tenant {
         }
       }
     }
     output {
       container idp-counter-information {
         uses idp-counter-information-block;
       }
     }
   }
   rpc get-idp-counters-log {
     description "Show IDP Log counters";
     input {
       uses command-forwarding;
       choice lsys {
         case logical-system {
         }
         case tenant {
         }
       }
     }
     output {
       container idp-counter-information {
         uses idp-counter-information-block;
       }
     }
   }
   rpc get-idp-counters-pol-mngr {
     description "Show IDP Policy counters";
     input {
       uses command-forwarding;
       choice lsys {
         case logical-system {
         }
         case tenant {
         }
       }
     }
     output {
       container idp-counter-information {
         uses idp-counter-information-block;
       }
     }
   }
   rpc get-idp-counters-packet-log {
     description "Show IDP Packet capture counters";
     input {
       uses command-forwarding;
       choice lsys {
         case logical-system {
         }
         case tenant {
         }
       }
     }
     output {
       container idp-counter-information {
         uses idp-counter-information-block;
       }
     }
   }
   rpc get-idp-counters-appid {
     description "Show Application Identification counters";
     input {
       uses command-forwarding;
       choice lsys {
         case logical-system {
         }
         case tenant {
         }
       }
     }
     output {
       container idp-counter-information {
         uses idp-counter-information-block;
       }
     }
   }
   rpc get-idp-counters-ssl-inspection {
     description "Show SSL Inspection counters";
     status deprecated;
     input {
       uses command-forwarding;
       choice lsys {
         case logical-system {
         }
         case tenant {
         }
       }
     }
     output {
       container idp-counter-information {
         uses idp-counter-information-block;
       }
     }
   }
   rpc get-idp-counters-memory {
     description "Show IDP memory counters";
     input {
       uses command-forwarding;
       choice lsys {
         case logical-system {
         }
         case tenant {
         }
       }
     }
     output {
       container idp-counter-information {
         uses idp-counter-information-block;
       }
     }
   }
   rpc get-idp-counters-action {
     description "Show IDP policy action counters";
     input {
       uses command-forwarding;
       choice lsys {
         case logical-system {
         }
         case tenant {
         }
       }
     }
     output {
       container idp-counter-information {
         uses idp-counter-information-block;
       }
     }
   }
   rpc get-idp-counters-pdf-decoder {
     description "Show the PDF decoder counters";
     input {
       uses command-forwarding;
       choice lsys {
         case logical-system {
         }
         case tenant {
         }
       }
     }
     output {
       container idp-counter-information {
         uses idp-counter-information-block;
       }
     }
   }
   rpc get-idp-counters-http-decoder {
     description "Show the HTTP decoder counters";
     input {
       uses command-forwarding;
       choice lsys {
         case logical-system {
         }
         case tenant {
         }
       }
     }
     output {
       container idp-counter-information {
         uses idp-counter-information-block;
       }
     }
   }
   rpc get-idp-applications-information {
     description "Show IDP application statistics";
     input {
       uses command-forwarding;
     }
   }
   rpc get-idp-attack-table-information {
     description "Show IDP attack table";
     input {
       uses command-forwarding;
       choice lsys {
         case logical-system {
         }
         case tenant {
         }
       }
     }
   }
   rpc get-idp-attack-context-information {
     description "Show IDP attack contexts";
     input {
       uses command-forwarding;
       choice lsys {
         case logical-system {
         }
         case tenant {
         }
       }
     }
     output {
       container idp-attack-context-information {
         uses idp-attack-context-information-block;
       }
     }
   }
   rpc get-idp-attack-deprecated-list-information {
     description "Show IDP attack deprecated-list";
     output {
       container idp-attack-deprecated-list-information {
         uses idp-attack-deprecated-list-information-block;
       }
     }
   }
   rpc get-idp-policy-deprecated-attack-information {
     description "Show IDP attack deprecated-list for the configured policy";
     input {
       leaf policy {
         description "IDP policy name";
         type string;
         mandatory true;
       }
     }
     output {
       container idp-policy-deprecated-attack-information {
         uses idp-policy-deprecated-attack-information-block;
       }
     }
   }
   rpc get-idp-all-policy-deprecated-attack-information {
     description "Show IDP attack deprecated-list for all the idp policies in use";
     input {
       leaf logical-system {
         description "Name of logical system";
         type string {
         }
       }
       leaf tenant {
         description "Name of tenant";
         type string {
         }
       }
     }
     output {
       container idp-all-policy-deprecated-attack-information {
         uses idp-all-policy-deprecated-attack-information-block;
       }
     }
   }
   rpc get-idp-attack-description-information {
     description "Show description of specified attack";
     input {
       leaf attack-name {
         description "Attack name";
         type string;
         mandatory true;
       }
     }
     output {
       container idp-attack-description-information {
         uses idp-attack-description-information-block;
       }
     }
   }
   rpc get-idp-attack-detail-information {
     description "Show details of specified attack";
     input {
       leaf attack-name {
         description "Attack name";
         type string;
         mandatory true;
       }
     }
     output {
       container idp-attack-detail-information {
         uses idp-attack-detail-information-block;
       }
     }
   }
   rpc get-idp-attack-group-entry-detail-information {
     description "Show detail of all attack and group";
     input {
       leaf offset {
         description "Offset value to start with (0 to any number)";
         type union {
           type uint32;
           type string {
             pattern "<.*>|$.*";
           }
         }
       }
       leaf limit {
         description "Number of entries to display";
         type union {
           type string {
             pattern "<.*>|$.*";
           }
           type int32 {
             range "1 .. 50";
           }
         }
       }
     }
     output {
       container idp-attack-group-entry-detail-information {
         uses idp-attack-group-entry-detail-information-block;
       }
     }
   }
   rpc get-idp-attack-group-entry-filters-information {
     description "Show detail of all attack and group which match the provided filters";
     input {
       leaf-list category {
         ordered-by user;
         description "Category of attack";
         type string;
       }
       leaf-list type-attack {
         ordered-by user;
         description "Type of attack";
         type enumeration {
           enum "0" {
             description "Static attack";
           }
           enum "1" {
             description "Dynamic attack";
           }
         }
       }
       leaf-list recommended-action {
         ordered-by user;
         description "Recommended action";
         type enumeration {
           enum "0" {
             description "None";
           }
           enum "1" {
             description "Close client and server";
           }
           enum "2" {
             description "Close client";
           }
           enum "3" {
             description "Close server";
           }
           enum "4" {
             description "Ignore";
           }
           enum "5" {
             description "Drop";
           }
           enum "6" {
             description "Drop packet";
           }
         }
       }
       leaf-list attack-type {
         ordered-by user;
         description "Attack type";
         type enumeration {
           enum "0" {
             description "Attack type - signature";
           }
           enum "1" {
             description "Attack type - anomaly";
           }
           enum "2" {
             description "Attack type - chain";
           }
         }
       }
       leaf-list performance {
         ordered-by user;
         description "Performance category type";
         type enumeration {
           enum "0" {
             description "Performance 0 - unknown";
           }
           enum "1" {
             description "Performance 1 - low";
           }
           enum "5" {
             description "Performance 5 - medium ";
           }
           enum "9" {
             description "Performance 9 - high";
           }
         }
       }
       leaf-list severity {
         ordered-by user;
         description "Severity of attack";
         type enumeration {
           enum "0" {
             description "Info attack";
           }
           enum "1" {
             description "Warning attack";
           }
           enum "2" {
             description "Minor attack";
           }
           enum "3" {
             description "Major attack";
           }
           enum "4" {
             description "Critical attack`";
           }
         }
       }
       leaf-list direction {
         ordered-by user;
         description "Direction of attack";
         type enumeration {
           enum "0" {
             description "Select attacks from client to server";
           }
           enum "1" {
             description "Select attacks from server to client";
           }
           enum "2" {
             description "Select attacks which can occur in either direction";
           }
         }
       }
       leaf-list recommended {
         ordered-by user;
         description "Recommended attack or not";
         type enumeration {
           enum "0" {
             description "Non recommended attack";
           }
           enum "1" {
             description "Recommended attack";
           }
         }
       }
       leaf-list group-name {
         ordered-by user;
         description "Group name";
         type string;
       }
       leaf-list group-type {
         ordered-by user;
         description "Group type";
         type enumeration {
           enum "0" {
             description "Predefined group";
           }
           enum "1" {
             description "Custom attack";
           }
           enum "2" {
             description "Custom attack group";
           }
           enum "3" {
             description "Predefined attack";
           }
         }
       }
       leaf-list service {
         ordered-by user;
         description "Attack service type";
         type string;
       }
       leaf-list cve-id {
         ordered-by user;
         description "Cve identifier";
         type string;
       }
       leaf-list certificate {
         ordered-by user;
         description "Certificate identifier";
         type string;
       }
       leaf-list bug-id {
         ordered-by user;
         description "Bug identifier";
         type string;
       }
       leaf-list false-positive {
         ordered-by user;
         description "Attack falsepositive type";
         type enumeration {
           enum "0" {
             description "Falsepositive category - unknown";
           }
           enum "1" {
             description "Falsepositive category - occassionally";
           }
           enum "2" {
             description "Falsepositive category - frequently";
           }
           enum "3" {
             description "Falsepositive category - rarely";
           }
         }
       }
       leaf limit {
         description "Number of entries to display";
         type union {
           type string {
             pattern "<.*>|$.*";
           }
           type int32 {
             range "1 .. 50";
           }
         }
       }
       leaf offset {
         description "Offset to start with (0 to any number)";
         type union {
           type uint32;
           type string {
             pattern "<.*>|$.*";
           }
         }
       }
     }
     output {
       container idp-attack-group-entry-filters-information {
         uses idp-attack-group-entry-filters-information-block;
       }
     }
   }
   rpc get-idp-group-attacklist-information {
     description "Shows list of all attacks present in the attack group specified";
     input {
       choice filter-choice {
         case predefined-group {
           leaf predefined-group {
             description "Predefined group name";
             type string;
           }
         }
         case custom-group {
           leaf custom-group {
             description "Custom group name";
             type string;
           }
         }
         case dynamic-group {
           leaf dynamic-group {
             description "Dynamic group name";
             type string;
           }
         }
         case policy {
           leaf policy {
             description "IDP policy name";
             type string;
           }
         }
       }
       leaf recursive {
         description "To show attack list recursively";
         type empty;
       }
     }
     output {
       container idp-group-attacklist-information {
         uses idp-group-attacklist-information-block;
       }
     }
   }
   rpc get-idp-group-forattack-information {
     description "Shows list of predefined attack-groups to which the predefined-attack belongs";
     input {
       leaf attack-name {
         description "Attack name";
         type string;
         mandatory true;
       }
     }
     output {
       container idp-group-forattack-information {
         uses idp-group-forattack-information-block;
       }
     }
   }
   rpc get-idp-attack-type-anomaly-test-service {
     description "Test name";
     input {
       leaf service {
         description "Service name";
         type string;
       }
     }
     output {
       container idp-attack-type-anomaly-test-service {
         uses idp-attack-type-anomaly-test-service-block;
       }
     }
   }
   rpc get-idp-ssl-session-cache-information {
     description "Session ID cache";
     input {
       uses command-forwarding;
     }
     output {
       container get-idp-ssl-session-cache-information {
         uses get-idp-ssl-session-cache-information-block;
       }
     }
   }
   rpc get-idp-ssl-key-information {
     description "Show SSL keys";
     input {
       uses command-forwarding;
       leaf key-name {
         description "Key name";
         type string {
           length "1 .. 31";
         }
       }
     }
     output {
       container idp-ssl-key-information {
         uses idp-ssl-key-information-block;
       }
     }
   }
   rpc get-idp-lsys-policy-association {
     description "Show IDP policy association";
     input {
       uses command-forwarding;
     }
     output {
       container idp-lsys-policy-association {
         uses idp-lsys-policy-association-block;
       }
     }
   }
   rpc get-eedebug-action-profile {
     description "Show current datapath-debug action profile";
     output {
       container eedebug-all-action-profile {
         uses eedebug-all-action-profile-block;
       }
     }
   }
   rpc get-eedebug-events {
     description "Show current registered data path events";
     output {
       container eedebug-all-events {
         uses eedebug-all-events-block;
       }
     }
   }
   rpc get-eedebug-counters {
     description "Show datapath counters";
     output {
       container eedebug-all-counters {
         uses eedebug-all-counters-block;
       }
     }
   }
   rpc get-eedebug-capture {
     description "Show datapath debug capture file";
     output {
       container eedebug-capture-output {
         uses eedebug-capture-output-block;
       }
     }
   }
   rpc get-alg-status {
     description "Show ALG status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-status {
         uses alg-status-block;
       }
     }
   }
   rpc get-alg-h323-counters {
     description "Show H323 counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-h323-counters {
         uses alg-h323-counters-block;
       }
     }
   }
   rpc get-alg-mgcp-call-information {
     description "Show MGCP calls";
     input {
       uses command-forwarding;
       leaf endpoint {
         description "Show MGCP call endpoint";
         type string {
           length "1 .. 63";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-mgcp-call-information {
         uses alg-mgcp-call-information-block;
       }
     }
   }
   rpc get-alg-mgcp-counter-information {
     description "Show MGCP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-mgcp-counter-information {
         uses alg-mgcp-counter-information-block;
       }
     }
   }
   rpc get-alg-mgcp-endpoint-information {
     description "Show MGCP endpoints";
     input {
       uses command-forwarding;
       leaf endpoint-name {
         description "Show MGCP endpoint with identifier";
         type string {
           length "1 .. 63";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-mgcp-endpoint-information {
         uses alg-mgcp-endpoint-information-block;
       }
     }
   }
   rpc get-alg-msrpc-uuid2oid-table {
     description "Show MSRPC UUID to OID table";
     input {
       uses command-forwarding;
     }
   }
   rpc get-alg-sccp-calls {
     description "Show SCCP calls";
     input {
       uses command-forwarding;
       leaf level {
         default "brief";
         type enumeration {
           enum "detail" {
             description "Display detailed call information";
           }
           enum "brief" {
             description "Display brief call information (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-alg-sccp-counters {
     description "Show SCCP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-sccp-counters {
         uses alg-sccp-counters-block;
       }
     }
   }
   rpc get-alg-sip-call-information {
     description "Show SIP calls";
     input {
       uses command-forwarding;
       leaf level {
         default "brief";
         type enumeration {
           enum "detail" {
             description "Display detailed call information";
           }
           enum "brief" {
             description "Display brief call information (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-sip-call-information {
         uses alg-sip-call-information-block;
       }
     }
   }
   rpc get-alg-sip-counter-information {
     description "Show SIP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container alg-sip-counter-information {
         uses alg-sip-counter-information-block;
       }
     }
   }
   rpc get-alg-sip-rate-information {
     description "Show SIP rate";
     input {
       uses command-forwarding;
     }
   }
   rpc get-alg-ike-esp-state {
     description "Show all IKE-ESP ALG state information";
     input {
       uses command-forwarding;
     }
     output {
       container alg-ike-esp-show {
         uses alg-ike-esp-show-block;
       }
     }
   }
   rpc get-alg-ike-esp-summary {
     description "Show IKE-ESP ALG summary";
     input {
       uses command-forwarding;
     }
     output {
       container alg-ike-esp-show-summary {
         uses alg-ike-esp-show-summary-block;
       }
     }
   }
   rpc get-appfw-rule-set {
     description "Show security application firewall rule-set";
     input {
       uses command-forwarding;
       choice rule-set-choice {
         case rule-set-name {
           leaf rule-set-name {
             description "Show the rule-set information matching the given rule-set name";
             type string {
               length "1 .. 64";
             }
             mandatory true;
           }
         }
         case all {
           leaf all {
             description "Show all rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container application-firewall {
         uses application-firewall-block;
       }
     }
   }
   rpc get-application-firewall-shadow-rules {
     description "Show security application firewall shadow-rules in one rule-set";
     input {
       uses command-forwarding;
       leaf rule-set-name {
         description "Rule-set name";
         type string {
           length "1 .. 64";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appfw-shadow-rules {
         uses appfw-shadow-rules-block;
       }
     }
   }
   rpc get-application-firewall-match-rule {
     description "Show matching rules in one rule-set";
     input {
       uses command-forwarding;
       leaf rule-set-name {
         description "Rule-set name";
         type string {
           length "1 .. 64";
         }
         mandatory true;
       }
       leaf dynamic-application {
         description "Dynamic application name";
         type string;
         mandatory true;
       }
       leaf encrypted {
         description "Specify encrypted or plain-text rules";
         default "any";
         type enumeration {
           enum "yes" {
             description "Encrypted rule";
           }
           enum "no" {
             description "Non-encrypted rule";
           }
           enum "any" {
             description "Encrypted and non-encrypted rule";
           }
         }
       }
       leaf result-count {
         description "Number of rules to show";
         default "1";
         type union {
           type string {
             pattern "<.*>|$.*";
           }
           type uint32 {
             range "1 .. 128000";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container appfw-match-rule {
         uses appfw-match-rule-block;
       }
     }
   }
   rpc get-avt-counters {
     description "Show Application tracking counters";
     input {
       uses command-forwarding;
     }
     output {
       container avt-counters {
         uses avt-counters-block;
       }
     }
   }
   rpc get-utmd-status {
     description "Show security utm status";
     input {
       uses command-forwarding;
     }
     output {
       container utmd-status {
         uses utmd-status-block;
       }
     }
   }
   rpc get-utmd-session {
     description "Show security utm session";
     input {
       uses command-forwarding;
     }
     output {
       container utmd-session {
         uses utmd-session-block;
       }
     }
   }
   rpc get-anti-virus {
     description "Show anti-virus information";
     output {
       choice output_c {
         case output-tag {
           leaf output {
             type string;
           }
         }
         case multichassis-tag {
           anyxml multi-routing-engine-results;
         }
       }
     }
   }
   rpc get-anti-virus-statistics {
     description "Show anti-virus statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container anti-virus {
         uses anti-virus-block;
       }
     }
   }
   rpc get-anti-virus-status {
     description "Show anti-virus status";
     input {
       uses command-forwarding;
     }
     output {
       container anti-virus {
         uses anti-virus-block;
       }
     }
   }
   rpc get-anti-virus-status-detail {
     description "Show anti-virus detailed status";
     input {
       uses command-forwarding;
     }
     output {
       container anti-virus {
         uses anti-virus-block;
       }
     }
   }
   rpc get-anti-virus-performance {
     description "Show anti-virus performance";
     input {
       uses command-forwarding;
     }
     output {
       container anti-virus {
         uses anti-virus-block;
       }
     }
   }
   rpc get-custom-objects {
     description "Show custom-objects information";
     output {
       choice output_c {
         case output-tag {
           leaf output {
             type string;
           }
         }
         case multichassis-tag {
           anyxml multi-routing-engine-results;
         }
       }
     }
   }
   rpc get-url-feed {
     description "Show url-feed information";
     output {
       choice output_c {
         case output-tag {
           leaf output {
             type string;
           }
         }
         case multichassis-tag {
           anyxml multi-routing-engine-results;
         }
       }
     }
   }
   rpc get-url-feed-status {
     description "Show the status of url-feed";
     input {
       uses command-forwarding;
       leaf feed-name {
         description "Show the status of url-feed";
         type string;
         mandatory true;
       }
       leaf options {
         description "Options to show the files related to url-feed";
         type enumeration {
           enum "invalid-urls" {
             description "Show all the invalid urls present in the url-feed file";
           }
           enum "ignored-urls" {
             description "Show all the ignored urls present in the url-feed file";
           }
         }
       }
       choice lsys {
         case logical-system {
         }
         case root-logical-system {
           leaf root-logical-system {
             description "Root logical-system (default)";
             type empty;
           }
         }
         case tenant {
         }
       }
     }
     output {
       container url-feed {
         uses url-feed-block;
       }
     }
   }
   rpc get-web-filtering {
     description "Show web-filtering information";
     output {
       choice output_c {
         case output-tag {
           leaf output {
             type string;
           }
         }
         case multichassis-tag {
           anyxml multi-routing-engine-results;
         }
       }
     }
   }
   rpc get-web-filtering-statistics {
     description "Show web-filtering statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container utmd-web-filtering {
         uses utmd-web-filtering-block;
       }
     }
   }
   rpc get-web-filtering-status {
     description "Show web-filtering status";
     input {
       uses command-forwarding;
     }
     output {
       container utmd-web-filtering {
         uses utmd-web-filtering-block;
       }
     }
   }
   rpc get-web-filtering-cache {
     description "Show web-filter url cache";
     input {
       uses command-forwarding;
     }
     output {
       container ewf-cache {
         uses ewf-cache-block;
       }
     }
   }
   rpc get-ewf-cache-preload {
     description "Show cache-preload information";
     output {
       choice output_c {
         case output-tag {
           leaf output {
             type string;
           }
         }
         case multichassis-tag {
           anyxml multi-routing-engine-results;
         }
       }
     }
   }
   rpc get-ewf-cache-preload-status {
     description "Show cache-preload settings and status";
     input {
       uses command-forwarding;
     }
     output {
       container ewf-cache-preload {
         uses ewf-cache-preload-block;
       }
     }
   }
   rpc get-web-filtering-category {
     description "Show category information";
     output {
       choice output_c {
         case output-tag {
           leaf output {
             type string;
           }
         }
         case multichassis-tag {
           anyxml multi-routing-engine-results;
         }
       }
     }
   }
   rpc get-category-status {
     description "Show category package download/install status";
     input {
       uses command-forwarding;
     }
     output {
       container category {
         uses category-block;
       }
     }
   }
   rpc get-category-category-list {
     description "Show EWF predefined category";
     input {
       uses command-forwarding;
       leaf start {
         description "Paging start";
         type union {
           type uint32;
           type string {
             pattern "<.*>|$.*";
           }
         }
       }
       leaf count {
         description "Item count";
         type union {
           type uint32;
           type string {
             pattern "<.*>|$.*";
           }
         }
       }
     }
     output {
       container category {
         uses category-block;
       }
     }
   }
   rpc get-enhanced-to-ng-migrate-status {
     description "Show migration to ng-juniper status";
     input {
       uses command-forwarding;
     }
     output {
       container enhanced-to-ng-migrate-status {
         uses enhanced-to-ng-migrate-status-block;
       }
     }
   }
   rpc get-ng-category-category-list {
     description "Show NG Juniper predefined category";
     input {
       uses command-forwarding;
       leaf start {
         description "Paging start";
         type union {
           type uint32;
           type string {
             pattern "<.*>|$.*";
           }
         }
       }
       leaf count {
         description "Item count";
         type union {
           type uint32;
           type string {
             pattern "<.*>|$.*";
           }
         }
       }
     }
     output {
       container category {
         uses category-block;
       }
     }
   }
   rpc get-category-base-filter {
     description "Show EWF predefined base-filter";
     input {
       uses command-forwarding;
       leaf base-filter-name {
         description "Base-filter name";
         type string;
       }
       leaf start {
         description "Paging start";
         type union {
           type uint32;
           type string {
             pattern "<.*>|$.*";
           }
         }
       }
       leaf count {
         description "Item count";
         type union {
           type uint32;
           type string {
             pattern "<.*>|$.*";
           }
         }
       }
     }
     output {
       container category {
         uses category-block;
       }
     }
   }
   rpc get-content-filtering {
     description "Show content-filtering information";
     output {
       choice output_c {
         case output-tag {
           leaf output {
             type string;
           }
         }
         case multichassis-tag {
           anyxml multi-routing-engine-results;
         }
       }
     }
   }
   rpc get-content-filtering-statistics {
     description "Show content-filtering statistics";
     input {
       uses command-forwarding;
       leaf utm-policy {
         description "Show statistics associated to utm-policy";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container content-filtering {
         uses content-filtering-block;
       }
     }
   }
   rpc get-content-filtering-dpi-status {
     description "Show content-filtering status";
     input {
       uses command-forwarding;
     }
     output {
       container content-filtering {
         uses content-filtering-block;
       }
     }
   }
   rpc get-anti-spam {
     description "Show anti-spam information";
     output {
       choice output_c {
         case output-tag {
           leaf output {
             type string;
           }
         }
         case multichassis-tag {
           anyxml multi-routing-engine-results;
         }
       }
     }
   }
   rpc get-anti-spam-statistics {
     description "Show anti-spam statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container anti-spam {
         uses anti-spam-block;
       }
     }
   }
   rpc get-anti-spam-status {
     description "Show anti-spam status";
     input {
       uses command-forwarding;
     }
     output {
       container anti-spam {
         uses anti-spam-block;
       }
     }
   }
   rpc get-security-dynamic-address {
     description "Security dynamic address name";
     input {
       uses command-forwarding;
       leaf category-name {
         description "Source category";
         type enumeration {
           enum "IPFilter" {
             description "IPFilter";
           }
           enum "GeoIP" {
             description "GeoIP";
           }
           enum "CC" {
             description "Command and control";
           }
           enum "JWAS" {
             description "JWAS";
           }
           enum "Blacklist" {
             description "Blacklist";
           }
           enum "Whitelist" {
             description "Whitelist";
           }
           enum "Infected-Hosts" {
             description "Infected-Hosts";
           }
           enum "SecProfiling" {
             description "SecProfiling";
           }
         }
       }
       leaf feed-name {
         description "Source feed name";
         type string {
           length "1 .. 240";
         }
       }
       leaf address-name {
         description "Dynamic address name";
         type string {
           length "1 .. 63";
         }
       }
       leaf ip-start {
         description "Numerically minimal IP address within the range";
         type jt:ipaddr;
       }
       leaf ip-end {
         description "Numerically maximal IP address within the range";
         type jt:ipaddr;
       }
       leaf family {
         description "Protocol-family";
         type enumeration {
           enum "inet" {
             description "IPv4 address";
           }
           enum "inet6" {
             description "IPv6 address";
           }
         }
       }
       leaf instance {
         description "Dynamic address instance";
         type enumeration {
           enum "default" {
             description "Default instance";
           }
           enum "geoip" {
             description "GeoIP instance";
           }
           enum "advanced-anti-malware" {
             description "Instance for anti-malware solution";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container security-dynamic-address {
         uses security-dynamic-address-block;
       }
     }
   }
   rpc get-security-dynamic-address-summary {
     description "Summary about dynamic address";
     input {
       uses command-forwarding;
       leaf instance {
         description "Dynamic address instance";
         type enumeration {
           enum "default" {
             description "Default instance";
           }
           enum "geoip" {
             description "GeoIP instance";
           }
           enum "advanced-anti-malware" {
             description "Instance for anti-malware solution";
           }
         }
       }
       leaf address-name {
         description "Show summary by dynamic address name";
         type string {
           length "1 .. 63";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container security-dynamic-address {
         uses security-dynamic-address-block;
       }
     }
   }
   rpc get-ssh-key-information {
     description "Show SSH identity brief information";
     input {
       leaf identity-name {
         description "Show brief information of specified identity";
         type string {
         }
       }
     }
     output {
       container identity-information {
         uses identity-information-block;
       }
     }
   }
   rpc get-ssh-key-public-information {
     description "Show SSH identity public key";
     input {
       leaf identity-name {
         description "Show public key of specified identity";
         type string {
         }
         mandatory true;
       }
     }
     output {
       container identity-public-information {
         uses identity-public-information-block;
       }
     }
   }
   rpc get-ds-lite-softwire-sc-infomation {
     description "Show softwire information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-ds-lite-softwire-one-sc-information {
     description "Show Softwire Concentrator object";
     input {
       uses command-forwarding;
       leaf softwire-name-str {
         description "Softwire Name";
         type string;
         mandatory true;
       }
       leaf start-id {
         description "Show softwire initiator info from start identifier";
         type union {
           type string {
             pattern "<.*>|$.*";
           }
           type uint32 {
             range "1 .. 100000";
           }
         }
       }
       leaf count {
         description "Number of softwire initiator entries";
         type union {
           type string {
             pattern "<.*>|$.*";
           }
           type uint32 {
             range "1 .. 100000";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-mape-domain-information {
     description "Show MAP-E information";
   }
   rpc get-mape-confidentiality-status {
     description "Show confidentiality status";
     output {
       container mape-confidentiality-status {
         uses mape-confidentiality-status-block;
       }
     }
   }
   rpc get-mape-one-domain-information {
     description "Show MAP-E domain object";
     input {
       leaf mape-domain-name {
         description "Specify name of the MAP-E domain";
         type string;
         mandatory true;
       }
       leaf rule {
         description "MAP-E rule name";
         type string;
       }
       leaf statistics {
         description "MAP-E statistics";
         type empty;
       }
     }
   }
   rpc get-firewall-dynamic-policies {
     description "Show security firewall dynamic policies";
     input {
       uses command-forwarding;
       leaf from-zone {
         description "Show the policy information matching the given source zone";
         type string;
       }
       leaf to-zone {
         description "Show the policy information matching the given destination zone";
         type string;
       }
       leaf detail {
         description "Show the detailed dynamic policy information";
         type empty;
       }
       leaf scope-id {
         description "Show the policy information matching the given scope policy id [4...MAX_POLICIES]";
         type union {
           type string {
             pattern "<.*>|$.*";
           }
           type uint32 {
             range "4 .. 4294967295";
           }
         }
       }
     }
     output {
       container security-dynamic-policies {
         uses security-dynamic-policies-block;
       }
     }
   }
   rpc get-swrss-io-information {
     description "Show swrss io status";
     input {
       uses command-forwarding;
     }
     output {
       container flow-swrss-io {
         uses flow-swrss-io-block;
       }
     }
   }
   rpc get-pmi-statistics-all {
     description "Show pmi statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container flow-pmi-statistics {
         uses flow-pmi-statistics-block;
       }
     }
   }
   rpc get-tunnel-inspection-statistics-all {
     description "Show tunnel-inspection statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container flow-tunnel-inspection-statistics {
         uses flow-tunnel-inspection-statistics-block;
       }
     }
   }
   rpc get-flow-statistics-all {
     description "Show flow statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container flow-statistics-all {
         uses flow-statistics-all-block;
       }
     }
   }
   rpc get-flow-status-all {
     description "Show flow status";
     input {
       uses command-forwarding;
       choice lsys {
         case logical-system {
         }
         case root-logical-system {
           leaf root-logical-system {
             description "Root logical-system (default)";
             type empty;
           }
         }
         case tenant {
         }
       }
     }
     output {
       container flow-status-all {
         uses flow-status-all-block;
       }
     }
   }
   rpc get-flow-gate-information {
     description "Show gate information";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "brief";
         type enumeration {
           enum "summary" {
             description "Show output summary";
           }
           enum "brief" {
             description "Show brief output (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container flow-gate-information {
         uses flow-gate-information-block;
       }
     }
   }
   rpc get-flow-cp-session {
     description "Show CP sessions";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "terse";
         type enumeration {
           enum "summary" {
             description "Show output summary";
           }
           enum "terse" {
             description "Show terse output (default)";
           }
         }
       }
       leaf flag-old {
         description "Obsoleted json-unfriendly format for old script compatibility";
         type enumeration {
           enum "old" {
             description "Show summary in old json-unfriendly format";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf conn-tag {
         description "Session connection tag";
         type union {
           type string {
             pattern "<.*>|$.*";
           }
           type uint32 {
             range "0 .. 4294967295";
           }
         }
       }
     }
   }
   rpc get-advanced-connection-tracking-entries {
     description "Advanced-connection-tracking table";
     input {
       uses command-forwarding;
       leaf family {
         description "Protocol family";
         type enumeration {
           enum "inet" {
             description "Show IPv4";
           }
           enum "inet6" {
             description "Show IPv6/IPv6-NATPT";
           }
         }
       }
       leaf destination-prefix {
         description "Destination IP prefix or address";
         type jt:ipprefix;
       }
       leaf source-prefix {
         description "Source IP prefix or address";
         type jt:ipprefix;
       }
       leaf destination-port {
         description "Destination port";
         type union {
           type string {
             pattern "<.*>|$.*";
           }
           type uint32 {
             range "0 .. 65535";
           }
         }
       }
       leaf protocol {
         description "IP protocol number";
         type string;
       }
       leaf zone-name {
         description "Zone name";
         type string;
       }
       leaf type-of-entry {
         description "Advanced-connection-tracking entry type";
         type enumeration {
           enum "any-host" {
             description "Advanced-connection-tracking table any-host entry";
           }
           enum "target-host" {
             description "Advanced-connection-tracking table target-host entry";
           }
           enum "target-host-port" {
             description "Advanced-connection-tracking table target-host-port entry";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf level {
         default "terse";
         type enumeration {
           enum "summary" {
             description "Show output summary";
           }
           enum "terse" {
             description "Show terse output (default)";
           }
         }
       }
     }
     output {
       container advanced-connection-tracking-table {
         uses advanced-connection-tracking-table-block;
       }
     }
   }
   rpc get-flow-session-information {
     description "Show session table";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf level {
         default "brief";
         type enumeration {
           enum "summary" {
             description "Show output summary";
           }
           enum "brief" {
             description "Show brief output (default)";
           }
           enum "extensive" {
             description "Show detailed output";
           }
           enum "pretty" {
             description "Show output pretty";
           }
           enum "plugins" {
             description "Show session plugins";
           }
         }
       }
       leaf flag-old {
         description "Obsoleted json-unfriendly format for old script compatibility";
         type enumeration {
           enum "old" {
             description "Show summary in old json-unfriendly format";
           }
         }
       }
       leaf enc {
         type enumeration {
           enum "encrypted" {
             description "Show encrypted traffic";
           }
         }
       }
       leaf add-on {
         type enumeration {
           enum "idp" {
             description "IDP sessions";
           }
           enum "ssl" {
             description "SSL sessions";
           }
           enum "tunnel" {
             description "Tunnel sessions";
           }
           enum "nat" {
             description "Sessions with network address translation";
           }
           enum "services-offload" {
             description "Services-offload sessions";
           }
           enum "resource-manager" {
             description "Sessions with resource manager";
           }
           enum "application-firewall" {
             description "Show application-firewall sessions";
           }
           enum "application-traffic-control" {
             description "Show application-traffic-control sessions";
           }
           enum "security-intelligence" {
             description "Show security-intelligence sessions";
           }
           enum "advanced-anti-malware" {
             description "Show advanced-anti-malware sessions";
           }
           enum "anti-virus" {
             description "Show anti-virus sessions";
           }
           enum "drop-flow" {
             description "Drop-flow sessions";
           }
           enum "content-filtering" {
             description "Show content-filtering sessions";
           }
           enum "web-filtering" {
             description "Show web-filtering sessions";
           }
         }
       }
       leaf application {
         description "Application protocol name";
         type enumeration {
           enum "dns" {
             description "Domain Name Service";
           }
           enum "ftp" {
             description "File Transfer Protocol";
           }
           enum "ignore" {
             description "Ignore application type";
           }
           enum "mgcp-ca" {
             description "MGCP-CA";
           }
           enum "mgcp-ua" {
             description "MGCP-UA";
           }
           enum "ms-rpc" {
             description "Microsoft RPC";
           }
           enum "pptp" {
             description "Point-to-Point Tunneling Protocol";
           }
           enum "sun-rpc" {
             description "Sun Microsystems RPC";
           }
           enum "q931" {
             description "Q.931";
           }
           enum "ras" {
             description "RAS";
           }
           enum "realaudio" {
             description "RealAudio";
           }
           enum "rsh" {
             description "Remote Shell";
           }
           enum "rtsp" {
             description "Real Time Streaming Protocol";
           }
           enum "sccp" {
             description "Skinny Client Control Protocol";
           }
           enum "sip" {
             description "Session Initiation Protocol";
           }
           enum "sqlnet-v2" {
             description "Oracle SQL*Net Version 2";
           }
           enum "talk" {
             description "Talk program";
           }
           enum "tftp" {
             description "Trivial File Transfer Protocol";
           }
           enum "http" {
             description "Hyper Text transfer protocol";
           }
           enum "https" {
             description "Secure HyperText Transfer Protocol";
           }
           enum "smtp" {
             description "Simple Mail Transfer Protocol";
           }
           enum "imap" {
             description "Internet Message Access Protocol";
           }
           enum "ssh" {
             description "Secure Shell";
           }
           enum "telnet" {
             description "Telnet Terminal Emulation Protocol";
           }
         }
       }
       leaf family {
         description "Protocol family";
         type enumeration {
           enum "inet" {
             description "Show IPv4";
           }
           enum "inet6" {
             description "Show IPv6/IPv6-NATPT";
           }
         }
       }
       leaf policy-id {
         description "Policy id value";
         type union {
           type string {
             pattern "<.*>|$.*";
           }
           type uint32 {
             range "1 .. 4294967295";
           }
         }
       }
       leaf zone {
         description "Zone name";
         type string;
       }
       leaf interface {
         description "Name of incoming or outgoing interface";
         type string;
       }
       leaf application-firewall-rule-set {
         description "Show application-firewall session by rule-set";
         type string;
       }
       leaf application-traffic-control-rule-set {
         description "Show application-traffic-control session by rule-set";
         type string;
       }
       leaf dynamic-application {
         description "Dynamic application name";
         type string;
       }
       leaf url-category {
         description "Show session by url-category";
         type string;
       }
       leaf dynamic-application-group {
         description "Dynamic application group name";
         type string;
       }
       leaf start-identifier {
         description "Show sessions from this start identifier";
         type union {
           type string {
             pattern "<.*>|$.*";
           }
           type uint64 {
             range "1 .. 18446744073709551615";
           }
         }
       }
       leaf count {
         description "Number of entries to show";
         type union {
           type string {
             pattern "<.*>|$.*";
           }
           type uint32 {
             range "1 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf conn-tag {
         description "Session connection tag";
         type union {
           type string {
             pattern "<.*>|$.*";
           }
           type uint32 {
             range "0 .. 4294967295";
           }
         }
       }
       leaf vrf-group {
         description "Session L3VPN VRF Group";
         type string;
       }
       leaf session-state {
         description "Session state";
         type enumeration {
           enum "warm" {
             description "L3 HA warm session ";
           }
           enum "backup" {
             description "L2 HA backup session";
           }
           enum "active-warm" {
             description "MNHA session with one active wing and one warm wing";
           }
         }
       }
       leaf tunnel-inspection-type {
         description "Tunnel inspection type";
         type enumeration {
           enum "vxlan" {
             description "Show vxlan tunnel inspection";
           }
           enum "gre" {
             description "Show gre tunnel inspection";
           }
           enum "ipip" {
             description "Show ipip tunnel inspection";
           }
           enum "geneve" {
             description "Show geneve tunnel inspection";
           }
         }
       }
       leaf vxlan-vni {
         description "VXLAN VNI";
         type union {
           type string {
             pattern "<.*>|$.*";
           }
           type uint32 {
             range "0 .. 4294967295";
           }
         }
       }
       leaf geneve-vni {
         description "GENEVE VNI";
         type union {
           type string {
             pattern "<.*>|$.*";
           }
           type uint32 {
             range "0 .. 4294967295";
           }
         }
       }
       leaf ha-link {
         description "Show HA link session";
         type empty;
       }
       leaf plugin-name {
         description "Plugin name";
         type enumeration {
           enum "junos-idp" {
             description "Junos-idp";
           }
           enum "junos-idp-stream" {
             description "Junos-idp-stream";
           }
           enum "junos-appid-packet" {
             description "Junos-appid-packet";
           }
           enum "junos-appid-stream" {
             description "Junos-aapid-stream";
           }
           enum "junos-appqos" {
             description "Junos-appqos";
           }
           enum "junos-appfw" {
             description "Junos-appfw";
           }
           enum "junos-appfw-stream" {
             description "Junos-appfw-stream";
           }
           enum "junos-secintel" {
             description "Junos-secintel";
           }
           enum "junos-secintel-stream" {
             description "Junos-secintel-stream";
           }
           enum "junos-aamw" {
             description "Junos-aamw";
           }
           enum "junos-aamw-stream" {
             description "Junos-aamw-stream";
           }
           enum "junos-alg" {
             description "Junos-alg";
           }
           enum "junos-gprs" {
             description "Junos-gprs";
           }
           enum "junos-utm-uf-pkt" {
             description "Junos-utm-uf-pkt";
           }
           enum "junos-utm-uf-stream" {
             description "Junos-utm-uf-stream";
           }
           enum "junos-utm" {
             description "Junos-utm";
           }
           enum "junos-utm-udp" {
             description "Junos-utm-udp";
           }
           enum "junos-icap-redirect" {
             description "Junos-icap-redirect";
           }
           enum "junos-uac" {
             description "Junos-uac";
           }
           enum "junos-rtm" {
             description "Junos-rtm";
           }
           enum "junos-captive-portal" {
             description "Junos-captive-portal";
           }
           enum "junos-tcp-svr-emul" {
             description "Junos-tcp-svr-emul";
           }
           enum "junos-tcp-clt-emul" {
             description "Junos-tcp-clt-emul";
           }
           enum "junos-hcm" {
             description "Junos-hcm";
           }
           enum "junos-hcm-pkt" {
             description "Junos-hcm-pkt";
           }
           enum "junos-slb-main" {
             description "Junos-slb-main";
           }
           enum "junos-slb-strm" {
             description "Junos-slb-strm";
           }
           enum "junos-slb-xlate" {
             description "Junos-slb-xlate";
           }
           enum "junos-screen-adapter" {
             description "Junos-screen-adapter";
           }
           enum "junos-fwauth-adapter" {
             description "Junos-fwauth-adapter";
           }
           enum "junos-fwauth-stream-adapter" {
             description "Junos-fwauth-stream-adapter";
           }
           enum "junos-syn-term" {
             description "Junos-syn-term";
           }
           enum "junos-syn-init" {
             description "Junos-syn-init";
           }
           enum "junos-test" {
             description "Junos-test";
           }
           enum "junos-ssl-term" {
             description "Junos-ssl-term";
           }
           enum "junos-ssl-init" {
             description "Junos-ssl-init";
           }
           enum "junos-ssl-proxy" {
             description "Junos-ssl-proxy";
           }
           enum "jsf-ssl-test" {
             description "Jsf-ssl-test";
           }
           enum "junos-jwx-policy" {
             description "Junos-jwx-policy";
           }
           enum "junos-jwx-cifs" {
             description "Junos-jwx-cifs";
           }
           enum "junos-jwx-zlib" {
             description "Junos-jwx-zlib";
           }
           enum "junos-cpcd" {
             description "Junos-cpcd";
           }
           enum "junos-rpm" {
             description "Junos-rpm";
           }
           enum "junos-subsc" {
             description "Junos-subsc";
           }
           enum "junos-mobile-subsc" {
             description "Junos-mobile-subsc";
           }
           enum "junos-pcef" {
             description "Junos-pcef";
           }
           enum "junos-tcp-utils" {
             description "Junos-tcp-utils";
           }
           enum "junos-userfw" {
             description "Junos-userfw";
           }
           enum "junos-jcpp" {
             description "Junos-jcpp";
           }
           enum "junos-rtcom-stream" {
             description "Junos-rtcom-stream";
           }
           enum "junos-rtcom" {
             description "Junos-rtcom";
           }
           enum "junos-log" {
             description "Junos-log";
           }
           enum "junos-jdpi" {
             description "Junos-jdpi";
           }
           enum "junos-dpi-stream" {
             description "Junos-dpi-stream";
           }
           enum "junos-lrf" {
             description "Junos-lrf";
           }
           enum "junos-ipsec" {
             description "Junos-ipsec";
           }
           enum "junos-apbr-main" {
             description "Junos-apbr-main";
           }
           enum "junos-url-filter" {
             description "Junos-url-filter";
           }
           enum "junos-remote-access-gw" {
             description "Junos-remote-access-gw";
           }
           enum "junos-dynapp" {
             description "Junos-dynapp";
           }
           enum "junos-dynapp-stream" {
             description "Junos-dynapp-stream";
           }
           enum "junos-telemetry" {
             description "Junos-telemetry";
           }
           enum "junos-appqoe" {
             description "Junos-appqoe";
           }
           enum "junos-appqoe-stream" {
             description "Junos-appqoe-stream";
           }
           enum "junos-amr" {
             description "Junos-amr";
           }
           enum "junos-cos" {
             description "Junos-cos";
           }
           enum "junos-tcplog" {
             description "Junos-tcplog";
           }
           enum "junos-stateful-ha" {
             description "Junos-stateful-ha";
           }
           enum "junos-web-proxy" {
             description "Junos-web-proxy";
           }
           enum "junos-web-proxy-pkt" {
             description "Junos-web-proxy-pkt";
           }
           enum "junos-web-proxy-sentinel" {
             description "Junos-web-proxy-sentinel";
           }
           enum "junos-emsdp-main" {
             description "Junos-emsdp-main";
           }
           enum "junos-health-check" {
             description "Junos-health-check";
           }
           enum "junos-ha-peer-infra" {
             description "Junos-ha-peer-infra";
           }
           enum "junos-softwire-head" {
             description "Junos-softwire-head";
           }
           enum "junos-softwire-tail" {
             description "Junos-softwire-tail";
           }
           enum "junos-csrx" {
             description "Junos-csrx";
           }
           enum "junos-srx-inline-ka-rt" {
             description "Junos-srx-inline-ka-rt";
           }
           enum "junos-utm-cf-stream" {
             description "Junos-utm-cf-stream";
           }
           enum "junos-utm-cf-pkt" {
             description "Junos-utm-cf-pkt";
           }
         }
       }
       leaf plugin-status {
         description "Plugin status";
         type enumeration {
           enum "interested" {
             description "Session's plugin is interested";
           }
           enum "ignore" {
             description "Session's plugin is ignored";
           }
         }
       }
       leaf duration-more-than {
         description "Session's duration time is more";
         type union {
           type string {
             pattern "<.*>|$.*";
           }
           type uint32 {
             range "1 .. 100000";
           }
         }
       }
       leaf duration-less-than {
         description "Session's duration time is less";
         type union {
           type string {
             pattern "<.*>|$.*";
           }
           type uint32 {
             range "1 .. 100000";
           }
         }
       }
       leaf timeout-more-than {
         description "Session's timeout value is more";
         type union {
           type string {
             pattern "<.*>|$.*";
           }
           type uint32 {
             range "1 .. 100000";
           }
         }
       }
       leaf timeout-less-than {
         description "Session's timeout value is less";
         type union {
           type string {
             pattern "<.*>|$.*";
           }
           type uint32 {
             range "1 .. 100000";
           }
         }
       }
       leaf curr-more-than {
         description "Session's current-timeout value is more";
         type union {
           type string {
             pattern "<.*>|$.*";
           }
           type uint32 {
             range "1 .. 100000";
           }
         }
       }
       leaf curr-less-than {
         description "Session's current-timeout value is less";
         type union {
           type string {
             pattern "<.*>|$.*";
           }
           type uint32 {
             range "1 .. 100000";
           }
         }
       }
       leaf packets-more-than {
         description "Session's packets-count is more";
         type union {
           type string {
             pattern "<.*>|$.*";
           }
           type uint32 {
             range "1 .. 4294967295";
           }
         }
       }
       leaf packets-less-than {
         description "Session's packets-count is less";
         type union {
           type string {
             pattern "<.*>|$.*";
           }
           type uint32 {
             range "1 .. 4294967295";
           }
         }
       }
       leaf bytes-more-than {
         description "Session's bytes-count is more";
         type union {
           type string {
             pattern "<.*>|$.*";
           }
           type uint32 {
             range "1 .. 4294967295";
           }
         }
       }
       leaf bytes-less-than {
         description "Session's bytes-count is less";
         type union {
           type string {
             pattern "<.*>|$.*";
           }
           type uint32 {
             range "1 .. 4294967295";
           }
         }
       }
       leaf source-tenant {
         description "Vector routing source tenant";
         type string;
       }
       leaf destination-service {
         description "Vector routing destination service";
         type string;
       }
       leaf aging {
         description "Early Ageout";
         type empty;
       }
       leaf source-nat-pool {
         description "Source NAT Pool name";
         type string;
       }
       leaf nat-port-overload-index {
         description "NAT port overloading index";
         type union {
           type string {
             pattern "<.*>|$.*";
           }
           type uint32 {
             range "0 .. 127";
           }
         }
       }
       leaf tunnel-info {
         description "Show sessions for specified tunnel-info ";
         type union {
           type string {
             pattern "<.*>|$.*";
           }
           type uint32 {
             range "0 .. 4294967295";
           }
         }
       }
     }
     output {
       container flow-session-information {
         uses flow-session-information-block;
       }
     }
   }
   rpc get-flow-session-geneve-information {
     description "Show geneve tunnel-inspection session information";
     input {
       uses command-forwarding;
     }
     output {
       container flow-session-information {
         uses flow-session-information-block;
       }
     }
   }
   rpc get-flow-session-aws-geneve-information {
     description "Show geneve aws session information";
     input {
       uses command-forwarding;
       leaf attachment-id {
         description "Attachment ID";
         type string {
           length "1 .. 16";
         }
       }
       leaf gw-endpoint-id {
         description "GW endpoint ID";
         type string {
           length "1 .. 16";
         }
       }
       leaf flow-cookie {
         description "Flow cookie";
         type string {
           length "1 .. 16";
         }
       }
     }
     output {
       container flow-session-information {
         uses flow-session-information-block;
       }
     }
   }
   rpc get-flow-session-by-identifier {
     description "Show session with specified session identifier";
     input {
       uses command-forwarding;
       leaf session-identifier {
         description "Session identifier";
         type union {
           type string {
             pattern "<.*>|$.*";
           }
           type uint64 {
             range "1 .. 18446744073709551615";
           }
         }
         mandatory true;
       }
       leaf level {
         type enumeration {
           enum "pretty" {
             description "Show output pretty";
           }
           enum "plugins" {
             description "Show session plugins";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container flow-session-information {
         uses flow-session-information-block;
       }
     }
   }
   rpc get-flow-session-summary-idp {
     description "Show IDP session summary";
     status deprecated;
     input {
       uses command-forwarding;
     }
     output {
       container idp-session-summary-information {
         uses idp-session-summary-information-block;
       }
     }
   }
   rpc get-flow-ipaction-information {
     description "Show ip-action table";
     input {
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
       leaf level {
         default "brief";
         type enumeration {
           enum "summary" {
             description "Show output summary";
           }
           enum "brief" {
             description "Show brief output (default)";
           }
         }
       }
     }
     output {
       container flow-ipaction-information {
         uses flow-ipaction-information-block;
       }
     }
   }
   rpc get-flow-ipaction-information-all {
     description "Show all ip-action entries";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       container flow-ipaction-information {
         uses flow-ipaction-information-block;
       }
     }
   }
   rpc get-forward-options-information {
     description "Show forward-options status";
   }
   rpc get-secure-wire-information {
     description "Show secure wire information";
     input {
       uses command-forwarding;
       choice lsys {
         case logical-system {
         }
         case root-logical-system {
           leaf root-logical-system {
             description "Root logical-system (default)";
             type empty;
           }
         }
       }
       leaf secure-wire-name {
         description "Display specified secure wire";
         type string;
       }
     }
     output {
       container secure-wire-information {
         uses secure-wire-information-block;
       }
     }
   }
   rpc get-flow-resource-manager-settings {
     description "Show resource manager settings";
     input {
       uses command-forwarding;
     }
     output {
       container flow-resource-manager-settings {
         uses flow-resource-manager-settings-block;
       }
     }
   }
   rpc get-resource-manager-status-details {
     description "Show resource manager status";
     input {
       uses command-forwarding;
     }
     output {
       container resource-manager-status-details {
         uses resource-manager-status-details-block;
       }
     }
   }
   rpc get-dpts-status-all {
     description "Show dataplane sleep status";
     input {
       uses command-forwarding;
     }
     output {
       container flow-vsrx-dpts-status {
         uses flow-vsrx-dpts-status-block;
       }
     }
   }
   rpc get-mirror-filter {
     description "Show  mirror-filter with specified filter-name";
     input {
       uses command-forwarding;
       choice filter {
         case name {
           leaf get-mirror-filter-by-name {
             description "Mirror filter name";
             type string;
             mandatory true;
           }
         }
         case all {
           leaf get-mirror-filter-all {
             description "List all mirror filters Counter";
             type empty;
           }
         }
       }
     }
     output {
       container show-mirror-filter-entry {
         uses show-mirror-filter-entry-block;
       }
     }
   }
   rpc get-packet-drop-records-all {
     description "Show packet-drop records";
     input {
       uses command-forwarding;
     }
     output {
       container packet-drop-records {
         uses packet-drop-records-block;
       }
     }
   }
   rpc get-firewall-authentication-jims {
     description "Show JIMS information";
     input {
       uses command-forwarding;
       choice filter {
         case statistics {
           leaf statistics {
             description "Show firewall authentication JIMS statistics";
             type empty;
           }
         }
       }
     }
   }
   rpc get-firewall-authentication-users {
     description "Show current firewall authentication users";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case identifier {
           leaf identifier {
             description "Locate authentication entry by id";
             type union {
               type uint32;
               type string {
                 pattern "<.*>|$.*";
               }
             }
           }
         }
         case auth-type {
           leaf auth-type {
             description "Show authentication entry matching the given auth-type";
             type enumeration {
               enum "user-firewall" {
                 description "User firewall authentication";
               }
               enum "pass-through" {
                 description "Pass-through authentication";
               }
               enum "web-authentication" {
                 description "Web firewall authentication";
               }
             }
           }
         }
         case address {
           leaf address {
             description "Locate authentication entry by ip address";
             type jt:ipprefix;
           }
         }
         case from-zone {
           leaf from-zone {
             description "Show authentication entry matching the given source zone, null for web-auth and userfw-auth";
             type string;
           }
         }
         case to-zone {
           leaf to-zone {
             description "Show authentication entry matching the given destination zone, null for web-auth and userfw-auth";
             type string;
           }
         }
       }
     }
     output {
       container firewall-authentication-table-details {
         uses firewall-authentication-table-details-block;
       }
     }
   }
   rpc get-firewall-authentication-history {
     description "Show firewall authentication history";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case identifier {
           leaf identifier {
             description "Locate authentication history by id";
             type union {
               type uint32;
               type string {
                 pattern "<.*>|$.*";
               }
             }
           }
         }
         case address {
           leaf address {
             description "Locate authentication history by ip address";
             type jt:ipprefix;
           }
         }
         case from-zone {
           leaf from-zone {
             description "Show authentication history matching the given source zone, null for web-auth and userfw-auth";
             type string;
           }
         }
         case to-zone {
           leaf to-zone {
             description "Show authentication history matching the given destination zone, null for web-auth and userfw-auth";
             type string;
           }
         }
       }
     }
     output {
       container firewall-authentication-history-details {
         uses firewall-authentication-history-details-block;
       }
     }
   }
   rpc get-firewall-authentication-debug-counters {
     description "Show debug counters";
     output {
       container fwauth-debug-counters {
         uses fwauth-debug-counters-block;
       }
     }
   }
   rpc get-fwauth-message-exchange-debug-counters {
     output {
       container fwauth-debug-counters {
         uses fwauth-debug-counters-block;
       }
     }
   }
   rpc get-fwauth-general-debug-counters {
     output {
       container fwauth-debug-counters {
         uses fwauth-debug-counters-block;
       }
     }
   }
   rpc get-security-screen-ids-data {
     description "Show screen data";
     input {
       uses command-forwarding;
     }
     output {
       container show-ids-data {
         uses show-ids-data-block;
       }
     }
   }
   rpc get-security-screen-ids-whitelist {
     description "Show white list data";
     input {
       uses command-forwarding;
       leaf wlist-name {
         description "White list name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container show-ids-whitelist {
         uses show-ids-whitelist-block;
       }
     }
   }
   rpc get-security-screen-ids-status {
     description "Show status of screen object";
     input {
       uses command-forwarding;
       leaf screen-name {
         description "Screen name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container show-ids-status {
         uses show-ids-status-block;
       }
     }
   }
   rpc get-ids-statistics {
     description "Show screen attack statistics information";
     input {
       uses command-forwarding;
       choice filter {
         case zone {
           leaf zone {
             description "IDS statistics zone";
             type string;
           }
         }
         case interface {
           leaf interface {
             description "IDS statistics interface";
             type string;
           }
         }
       }
       leaf ip {
         description "IDS statistics ip";
         type enumeration {
           enum "tunnel" {
             description "IDS statistics ip tunnel";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-destination-nat-pool-information {
     description "Show destination NAT address-pool information";
     input {
       uses command-forwarding;
       choice pool-choice {
         case pool-name {
           leaf pool-name {
             description "Destination address pool name";
             type string {
               length "1 .. 64";
             }
             mandatory true;
           }
         }
         case all {
           leaf all {
             description "Display all destination NAT address-pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-pool-information {
         uses destination-nat-pool-information-block;
       }
     }
   }
   rpc get-destination-nat-rule-sets-information {
     description "Show destination NAT rule-set information";
     input {
       uses command-forwarding;
       choice rule-choice {
         case rule-name {
           leaf rule-name {
             description "Destination NAT rule name";
             type string {
               length "1 .. 64";
             }
             mandatory true;
           }
         }
         case all {
           leaf all {
             description "Display all destination NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
   }
   rpc get-destination-nat-rule-application-information {
     description "Show destination NAT rule application information";
     input {
       uses command-forwarding;
       choice rule-choice {
         case rule-name {
           leaf rule-name {
             description "Destination NAT rule name";
             type string {
               length "1 .. 64";
             }
             mandatory true;
           }
         }
         case all {
           leaf all {
             description "Display all destination NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-rule-application-information {
         uses destination-nat-rule-application-information-block;
       }
     }
   }
   rpc retrieve-destination-nat-summary-information {
     description "Show destination NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container destination-nat-summary-information {
         uses destination-nat-summary-information-block;
       }
     }
   }
   rpc retrieve-source-nat-pool-information {
     description "Show source NAT information of this pool";
     input {
       uses command-forwarding;
       choice pool-choice {
         case pool-name {
           leaf pool-name {
             description "Source address pool name";
             type string;
             mandatory true;
           }
         }
         case all {
           leaf all {
             description "Display all source NAT pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-pool-information {
         uses source-nat-pool-information-block;
       }
     }
   }
   rpc get-persist-nat-all {
     description "Show all persistent NAT information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf family {
         description "Protocol family";
         type enumeration {
           enum "inet" {
             description "Show IPv4";
           }
           enum "inet6" {
             description "Show IPv6/IPv6-NATV6V4";
           }
         }
       }
     }
   }
   rpc get-persist-nat-sum {
     description "Show persistent NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc retrieve-persist-nat-pool-information {
     description "Show persistent NAT information of this pool";
     input {
       uses command-forwarding;
       leaf pool-name {
         description "Source NAT pool name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-persist-nat-interface-information {
     description "Show persistent NAT information of this interface";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container source-nat-summary {
         uses source-nat-summary-block;
       }
     }
   }
   rpc retrieve-persist-nat-ip-port-information {
     description "Show persistent NAT information of internal IP and port";
     input {
       uses command-forwarding;
       leaf ip {
         description "Internal IP address";
         type jt:ipaddr;
         mandatory true;
       }
       leaf internal-port {
         description "Internal port";
         type union {
           type uint16;
           type string {
             pattern "<.*>|$.*";
           }
         }
       }
       leaf internal-protocol {
         description "Internal protocol";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-src-nat-port-block {
     description "Show port block allocation information";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-deterministic-nat {
     description "Show deterministic port block allocation information";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-det-nat-host-sddr-range {
     description "Show deterministic host address range without overlap";
     input {
       uses command-forwarding;
       leaf pool {
         description "Source NAT pool name";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc retrieve-source-nat-paired-address-information {
     description "Show paired address information";
     input {
       uses command-forwarding;
       leaf pool-name {
         description "Address pool name";
         type string;
       }
       choice ip-choice {
         case internal-ip {
           leaf internal-ip {
             description "Internal IP address";
             type jt:ipaddr;
           }
         }
         case xlated-ip {
           leaf xlated-ip {
             description "Xlated IP address";
             type jt:ipaddr;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-source-nat-rule-sets-information {
     description "Show source NAT rule-set information";
     input {
       uses command-forwarding;
       choice rule-choice {
         case rule-name {
           leaf rule-name {
             description "Source NAT rule name";
             type string {
               length "1 .. 64";
             }
             mandatory true;
           }
         }
         case all {
           leaf all {
             description "Display all source NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
   }
   rpc get-source-nat-rule-application-information {
     description "Show source NAT rule application information";
     input {
       uses command-forwarding;
       choice rule-choice {
         case rule-name {
           leaf rule-name {
             description "Source NAT rule name";
             type string {
               length "1 .. 64";
             }
             mandatory true;
           }
         }
         case all {
           leaf all {
             description "Display all source NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-rule-application-information {
         uses source-nat-rule-application-information-block;
       }
     }
   }
   rpc retrieve-source-nat-summary {
     description "Show source NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container source-nat-summary {
         uses source-nat-summary-block;
       }
     }
   }
   rpc get-source-nat-pool-distribution {
     description "Show source NAT pool-distribution";
     input {
       uses command-forwarding;
     }
     output {
       container source-nat-pool-distribution {
         uses source-nat-pool-distribution-block;
       }
     }
   }
   rpc get-static-nat-rule-information {
     description "Show static NAT rule information";
     input {
       uses command-forwarding;
       choice rule-choice {
         case rule-name {
           leaf rule-name {
             description "Static NAT rule name";
             type string {
               length "1 .. 64";
             }
             mandatory true;
           }
         }
         case all {
           leaf all {
             description "Display all static NAT rule information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container static-nat-rule-information {
         uses static-nat-rule-information-block;
       }
     }
   }
   rpc get-interface-nat-ports-information {
     description "Show interface nat ports information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container interface-nat-ports-information {
         uses interface-nat-ports-information-block;
       }
     }
   }
   rpc retrieve-source-nat-pool-resource-usage {
     description "Show source pool resource usage information";
     input {
       uses command-forwarding;
       choice pool-choice {
         case pool-name {
           leaf pool-name {
             description "Source address pool name";
             type string;
             mandatory true;
           }
         }
         case all {
           leaf all {
             description "Display all source NAT pool resource usage";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-firewall-policies {
     description "Show security firewall policies";
     input {
       uses command-forwarding;
       leaf from-zone {
         description "Show the policy information matching the given source zone";
         type string;
       }
       leaf to-zone {
         description "Show the policy information matching the given destination zone";
         type string;
       }
       leaf policy-set {
         description "Show the policy information matching the given policy-set";
         type string;
       }
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       container security-policies {
         uses security-policies-block;
       }
     }
   }
   rpc get-security-policies-explicit-proxy {
     description "Show the explicit proxy policies";
     input {
       uses command-forwarding;
       leaf explicit-proxy-profile {
         description "Show the policy information matching the given explicit proxy profile";
         type string;
       }
       leaf policy-name {
         description "Show the policy information matching the given policy name";
         type string;
       }
       leaf detail {
         description "Show the detailed information";
         type empty;
       }
       leaf profile-context {
         description "Show the count of policies in each explicit proxy profile context";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container explicit-proxy-policies {
         uses explicit-proxy-policies-block;
       }
     }
   }
   rpc get-explicit-proxy-policies-hit-count {
     description "Show the hit count of policies";
     input {
       uses command-forwarding;
       leaf explicit-proxy-profile {
         description "Show the policy hit-count matching the given explicit proxy profile";
         type string;
       }
       leaf detail {
         description "Show the detailed information";
         type empty;
       }
       leaf policy-name {
         description "Show the policy information matching the given policy name";
         type string;
       }
       leaf dynamic-applications {
         description "Show hit-count for each dynamic-application of this policy";
         type empty;
       }
       leaf url-categories {
         description "Show hit-count for each url-category of this policy";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container explicit-proxy-policy-hit-count {
         uses explicit-proxy-policy-hit-count-block;
       }
     }
   }
   rpc get-explicit-proxy-policy-checksum-information {
     description "Show policy information checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
   }
   rpc get-security-policies-hit-count {
     description "Show the hit count of policies";
     input {
       uses command-forwarding;
       leaf from-zone {
         description "Show the policy hit-count matching the given source zone";
         type string;
       }
       leaf to-zone {
         description "Show the policy hit-count matching the given destination zone";
         type string;
       }
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
       leaf detail {
         description "Show the detailed information";
         type empty;
       }
       leaf policy-name {
         description "Show the policy information matching the given policy name";
         type string;
       }
       leaf dynamic-applications {
         description "Show hit-count for each dynamic-application of this policy";
         type empty;
       }
       leaf url-categories {
         description "Show hit-count for each url-category of this policy";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container policy-hit-count {
         uses policy-hit-count-block;
       }
     }
   }
   rpc get-global-firewall-policies {
     description "Show the policy information of global policies";
     input {
       uses command-forwarding;
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc unknown-source-identity-of-policies {
     description "Show the unknown-source-identity of policy";
     input {
       uses command-forwarding;
     }
     output {
       container security-policies {
         uses security-policies-block;
       }
     }
   }
   rpc get-unknown-destination-identity {
     description "Show the unknown-destination-identity of policy";
     input {
       uses command-forwarding;
     }
     output {
       container security-policies {
         uses security-policies-block;
       }
     }
   }
   rpc get-firewall-policies-information {
     description "Show the policy information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container security-policies {
         uses security-policies-block;
       }
     }
   }
   rpc get-policy-checksum-information {
     description "Show policy information checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       container security-policies {
         uses security-policies-block;
       }
     }
   }
   rpc match-firewall-policies {
     description "Show security match policies";
     input {
       uses command-forwarding;
       choice lsys {
         case logical-system {
         }
         case root-logical-system {
           leaf root-logical-system {
             description "Root logical-system (default)";
             type empty;
           }
         }
         case tenant {
         }
       }
       leaf from-zone {
         description "Match policy for the given source zone(optional for global policies)";
         type string;
         mandatory true;
       }
       leaf to-zone {
         description "Match policy for the given destination zone (optional for global policies)";
         type string;
         mandatory true;
       }
       leaf policy-set {
         description "Match policy for the given policy-set";
         type string;
       }
       leaf explicit-proxy-profile {
         description "Show the policy information matching the given explicit proxy profile";
         type string;
       }
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf url-category {
         description "Match policy for the given url category";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf destination-identity-context {
         description "Match policy for the given destination roles (optional)";
         type string {
         }
       }
       leaf source-end-user-profile {
         description "Match policy for the given source-end-user-profile (optional)";
         type string;
       }
       leaf destination-identity-context-profile {
         description "Match policy for the given destination-identity-context-profile (optional)";
         type string;
       }
       leaf source-vrf {
         description "Match policy for the given source vrf (optional)";
         type string;
       }
       leaf destination-vrf {
         description "Match policy for the given destination vrf (optional)";
         type string;
       }
     }
     output {
       container security-policy-match {
         uses security-policy-match-block;
       }
     }
   }
   rpc match-global-policies {
     description "Match global policy";
     input {
       uses command-forwarding;
       choice lsys {
         case logical-system {
         }
         case root-logical-system {
           leaf root-logical-system {
             description "Root logical-system (default)";
             type empty;
           }
         }
         case tenant {
         }
       }
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf url-category {
         description "Match policy for the given url category";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf destination-identity-context {
         description "Match policy for the given destination roles (optional)";
         type string {
         }
       }
       leaf source-end-user-profile {
         description "Match policy for the given source-end-user-profile (optional)";
         type string;
       }
       leaf destination-identity-context-profile {
         description "Match policy for the given destination-identity-context-profile (optional)";
         type string;
       }
       leaf from-zone {
         description "Match policy for the given source zone(optional for global policies)";
         type string;
       }
       leaf to-zone {
         description "Match policy for the given destination zone (optional for global policies)";
         type string;
       }
       leaf source-vrf {
         description "Match policy for the given source vrf (optional)";
         type string;
       }
       leaf destination-vrf {
         description "Match policy for the given destination vrf (optional)";
         type string;
       }
     }
   }
   rpc get-firewall-policy-dns-cache {
     description "Show DNS cache of firewall policy";
     input {
       leaf dns-name {
         description "Show DNS cache matching the given DNS name";
         type string;
       }
     }
     output {
       container security-dns-cache {
         uses security-dns-cache-block;
       }
     }
   }
   rpc shadow-firewall-policies {
     description "Show security shadow policies";
     input {
       uses command-forwarding;
       choice lsys {
         case logical-system {
         }
         case root-logical-system {
           leaf root-logical-system {
             description "Root logical-system (default)";
             type empty;
           }
         }
         case tenant {
         }
       }
       leaf from-zone {
         description "Show shadow policy information for the given source zone";
         type string;
         mandatory true;
       }
       leaf to-zone {
         description "Show shadow policy information for the given destination zone";
         type string;
         mandatory true;
       }
       leaf policy {
         description "Show shadow policy information for the given policy";
         type string;
       }
       leaf reverse {
         description "Show the policies which shadows the given policy";
         type empty;
       }
     }
     output {
       container security-policy-shadow {
         uses security-policy-shadow-block;
       }
     }
   }
   rpc shadow-global-policies {
     description "Shadow policy information for global policy";
     input {
       uses command-forwarding;
       choice lsys {
         case logical-system {
         }
         case root-logical-system {
           leaf root-logical-system {
             description "Root logical-system (default)";
             type empty;
           }
         }
         case tenant {
         }
       }
       leaf policy {
         description "Show shadow policy information for the given policy";
         type string;
       }
       leaf reverse {
         description "Show the policies which shadows the given policy";
         type empty;
       }
     }
   }
   rpc get-policy-report {
     description "Show security policy report";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf from-zone {
         description "Show policy report for the given source zone";
         type string;
       }
       leaf to-zone {
         description "Show policy report for the given destination zone";
         type string;
       }
       leaf report-type {
         description "Policy report";
         type enumeration {
           enum "shadowing" {
             description "Shadow report";
           }
           enum "redundant" {
             description "Redundant report";
           }
           enum "generalization" {
             description "Generalization report";
           }
           enum "consolidation" {
             description "Consolidation report";
           }
           enum "unused" {
             description "Unused report";
           }
           enum "expired" {
             description "Expired report";
           }
           enum "scheduler" {
             description "Scheduler report";
           }
           enum "no-comments" {
             description "No-comments report";
           }
           enum "no-logging" {
             description "No-logging report";
           }
           enum "most-hit" {
             description "Most-hit report";
           }
           enum "least-hit" {
             description "Least-hit report";
           }
           enum "30d-not-hit" {
             description "Not-hit-30-days report";
           }
           enum "60d-not-hit" {
             description "Not-hit-60-days report";
           }
           enum "90d-not-hit" {
             description "Not-hit-90-days report";
           }
           enum "1-year-not-hit" {
             description "Not-hit-1-year report";
           }
         }
       }
     }
     output {
       container security-policy-report {
         uses security-policy-report-block;
       }
     }
   }
   rpc get-explicit-proxy-policy-report {
     description "Show security explicit proxy policy report";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf explicit-proxy-profile {
         description "Show policy report for the given explicit proxy profile";
         type string;
       }
     }
     output {
       container security-explicit-proxy-policy-report {
         uses security-explicit-proxy-policy-report-block;
       }
     }
   }
   rpc get-global-policies-repot {
     description "Show security policy report for global policy";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf report-type {
         description "Policy report";
         type enumeration {
           enum "shadowing" {
             description "Shadow report";
           }
           enum "redundant" {
             description "Redundant report";
           }
           enum "generalization" {
             description "Generalization report";
           }
           enum "consolidation" {
             description "Consolidation report";
           }
           enum "unused" {
             description "Unused report";
           }
           enum "expired" {
             description "Expired report";
           }
           enum "scheduler" {
             description "Scheduler report";
           }
           enum "no-comments" {
             description "No-comments report";
           }
           enum "no-logging" {
             description "No-logging report";
           }
           enum "most-hit" {
             description "Most-hit report";
           }
           enum "least-hit" {
             description "Least-hit report";
           }
           enum "30d-not-hit" {
             description "Not-hit-30-days report";
           }
           enum "60d-not-hit" {
             description "Not-hit-60-days report";
           }
           enum "90d-not-hit" {
             description "Not-hit-90-days report";
           }
           enum "1-year-not-hit" {
             description "Not-hit-1-year report";
           }
         }
       }
     }
   }
   rpc get-apbr-policies {
     description "Show advance policy based routing information";
     input {
       uses command-forwarding;
       leaf from-zone {
         description "Show the policy information matching the given source zone";
         type string;
       }
       leaf policy-name {
         description "Show the policy information matching the given policy name";
         type string;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf detail {
         description "Show the detailed information";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container apbr-policies {
         uses apbr-policies-block;
       }
     }
   }
   rpc get-sla-policies-hit-count {
     description "Show the hit count of policies";
     input {
       uses command-forwarding;
       leaf from-zone {
         description "Show the policy hit-count matching the given source zone";
         type string;
       }
       leaf order {
         description "Policy order";
         type enumeration {
           enum "ascending" {
             description "Ascending order";
           }
           enum "descending" {
             description "Descending order";
           }
         }
       }
       leaf less-than {
         description "Maximum hit-count";
         type union {
           type string {
             pattern "<.*>|$.*";
           }
           type uint32 {
             range "0 .. 4294967295";
           }
         }
       }
       leaf greater-than {
         description "Minimum hit-count";
         type union {
           type string {
             pattern "<.*>|$.*";
           }
           type uint32 {
             range "0 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container sla-hit-count {
         uses sla-hit-count-block;
       }
     }
   }
   rpc get-apbr-statistics {
     description "Show advance-policy-based-routing statistics";
     input {
       uses command-forwarding;
     }
     output {
       container apbr-statistics {
         uses apbr-statistics-block;
       }
     }
   }
   rpc get-apbr-profile {
     description "Show advance-policy-based-routing profile";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
   }
   rpc get-apbr-status {
     description "Show advance-policy-based-routing status";
     input {
       uses command-forwarding;
     }
   }
   rpc get-apbr-sla-status {
     description "Show advance-policy-based-routing sla status";
     input {
       uses command-forwarding;
     }
     output {
       container apbr-sla-status {
         uses apbr-sla-status-block;
       }
     }
   }
   rpc get-apbr-sla-version {
     description "Show advance-policy-based-routing sla version";
     input {
       uses command-forwarding;
     }
     output {
       container apbr-sla-version {
         uses apbr-sla-version-block;
       }
     }
   }
   rpc get-apbr-sla-statistics {
     description "Show advance-policy-based-routing sla statistics";
     input {
       uses command-forwarding;
     }
     output {
       container apbr-sla-statistics {
         uses apbr-sla-statistics-block;
       }
     }
   }
   rpc get-apbr-sla-active-statistics {
     description "Choose for a Probe Params";
     input {
       uses command-forwarding;
       leaf active-probe-params-name {
         description "Active Probe Params Name";
         type string;
         mandatory true;
       }
     }
     output {
       container apbr-active-statistics {
         uses apbr-active-statistics-block;
       }
     }
   }
   rpc get-apbr-sla-information {
     description "Show advance-policy-based-routing sla profile data";
     input {
       uses command-forwarding;
       leaf profile-name {
         description "Profile name";
         type string;
         mandatory true;
       }
       leaf application {
         description "Application name";
         type string;
       }
       leaf dscp {
         description "DSCP value";
         type union {
           type string {
             pattern "<.*>|$.*";
           }
           type uint32 {
             range "0 .. 63";
           }
         }
       }
       leaf next-hop {
         description "Forwarding Next-Hop ID";
         type union {
           type int32;
           type string {
             pattern "<.*>|$.*";
           }
         }
       }
       leaf server-ip {
         description "SaaS server IP";
         type jt:ipaddr;
       }
       leaf get-apbr-sla-options {
         description "Options";
         type enumeration {
           enum "status" {
             description "Current running Status";
           }
         }
       }
     }
     output {
       container apbr-prof-app {
         uses apbr-prof-app-block;
       }
     }
   }
   rpc get-multipath-rule-status {
     description "Show multipath rule details";
     input {
       uses command-forwarding;
       leaf rule-name {
         description "Multipath rule name";
         type string;
         mandatory true;
       }
       choice filter {
         case application {
           leaf application {
             description "Application name";
             type string;
           }
         }
         case cos-q {
           leaf cos-q {
             description "Cos-Q number from 0-7";
             type union {
               type string {
                 pattern "<.*>|$.*";
               }
               type uint32 {
                 range "0 .. 7";
               }
             }
           }
         }
         case ifl-name {
           leaf ifl-name {
             description "Specify ifl name";
             type string;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container multipath-rule-status {
         uses multipath-rule-status-block;
       }
     }
   }
   rpc get-multipath-policy-information {
     description "Show advance-policy-based-routing multipath policy statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf multipath-name {
         description "Multipath name";
         type string;
       }
       choice filter {
         case application {
           leaf application {
             description "Application name";
             type string;
           }
         }
       }
     }
     output {
       container multipath-policy-information {
         uses multipath-policy-information-block;
       }
     }
   }
   rpc get-ragw-statistics {
     description "Show TCP encapsulation statistics";
     input {
       uses command-forwarding;
     }
     output {
       container ragw-statistics {
         uses ragw-statistics-block;
       }
     }
   }
   rpc get-ragw-connection {
     description "Show TCP encap session details";
     input {
       uses command-forwarding;
       leaf level {
         default "brief";
         type enumeration {
           enum "brief" {
             description "Display brief output";
           }
           enum "detail" {
             description "Display detailed output";
           }
         }
       }
       leaf get-sess-id-connection-details {
         description "Session id";
         type union {
           type string {
             pattern "<.*>|$.*";
           }
           type uint32 {
             range "1 .. 4294967295";
           }
         }
       }
     }
   }
   rpc get-resmgr-group-active {
     description "Show active resource manager group service information";
     input {
       uses command-forwarding;
       leaf group-number {
         description "Show active resource manager group";
         type union {
           type uint32;
           type string {
             pattern "<.*>|$.*";
           }
         }
       }
     }
     output {
       container resmgr-group-active {
         uses resmgr-group-active-block;
       }
     }
   }
   rpc get-resmgr-resource-active {
     description "Show active resource manager resource service information";
     input {
       uses command-forwarding;
       leaf resource-number {
         description "Show active resource manager resource";
         type union {
           type uint32;
           type string {
             pattern "<.*>|$.*";
           }
         }
       }
     }
     output {
       container resmgr-resource-active {
         uses resmgr-resource-active-block;
       }
     }
   }
   rpc get-resmgr-settings {
     description "Show resource manager settings information";
     input {
       uses command-forwarding;
     }
     output {
       container resmgr-settings {
         uses resmgr-settings-block;
       }
     }
   }
   rpc get-resource-manager-summary {
     description "Show resource manager summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container resource-manager-summary-information {
         uses resource-manager-summary-information-block;
       }
     }
   }
   rpc get-security-report-threats-summary {
     description "Show threat indicator summary";
     input {
       uses command-forwarding;
     }
   }
   rpc get-security-report-threats-statistics {
     description "Show the threat statistics";
     input {
       uses command-forwarding;
     }
   }
   rpc get-security-report-threats-recent-activity {
     description "Show the most recent threat activities";
     input {
       uses command-forwarding;
     }
   }
   rpc get-security-report-traffic-statistics {
     description "Show the traffic statistics";
     input {
       uses command-forwarding;
     }
   }
   rpc get-performance-summary-information {
     description "Show security SPU monitoring information";
     input {
       uses command-forwarding;
     }
     output {
       container performance-summary-information {
         uses performance-summary-information-block;
       }
     }
   }
   rpc get-spu-monitoring-information {
     description "Show the FPC slot security monitoring information";
     input {
       uses command-forwarding;
       leaf fpc-slot {
         description "FPC slot number";
         type union {
           type string {
             pattern "<.*>|$.*";
           }
           type uint32;
         }
         mandatory true;
       }
     }
   }
   rpc get-spu-monitoring-re-ipc-debug {
     description "Show the debug info about IPC between RTLGOD on HA nodes.";
     output {
       container spu-monitroing-re-ipc-debug {
         uses spu-monitroing-re-ipc-debug-block;
       }
     }
   }
   rpc get-performance-spu-information {
     description "Show security performance SPU information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container performance-spu-information {
         uses performance-spu-information-block;
       }
     }
   }
   rpc get-performance-spu-extensive-information {
     description "Show security performance SPU extensive information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container performance-spu-extensive-information {
         uses performance-spu-extensive-information-block;
       }
     }
   }
   rpc get-performance-spu-summary-information {
     description "Show security performance SPU summary information";
     input {
       uses command-forwarding;
       leaf fpc {
         description "FPC slot number";
         type union {
           type string {
             pattern "<.*>|$.*";
           }
           type uint32;
         }
         mandatory true;
       }
       leaf pic {
         description "PIC slot number";
         type union {
           type string {
             pattern "<.*>|$.*";
           }
           type uint32;
         }
         mandatory true;
       }
       leaf thread {
         description "SPU thread number";
         type union {
           type string {
             pattern "<.*>|$.*";
           }
           type uint32 {
             range "0 .. 31";
           }
         }
       }
     }
     output {
       container performance-spu-summary-information {
         uses performance-spu-summary-information-block;
       }
     }
   }
   rpc get-performance-session-information {
     description "Show security performance session information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       container performance-session-information {
         uses performance-session-information-block;
       }
     }
   }
   rpc get-userfw-local-auth-table-all {
     description "Show the entire local user authentication table";
     input {
       uses command-forwarding;
       leaf level {
         default "brief";
         type enumeration {
           enum "brief" {
             description "Show brief output (default)";
           }
           enum "extensive" {
             description "Show extensive output";
           }
         }
       }
     }
     output {
       container user-identification {
         uses user-identification-block;
       }
     }
   }
   rpc get-userfw-local-auth-table-ip {
     description "Show local user authentication information for the specified ip-address";
     input {
       uses command-forwarding;
       leaf ip-address {
         description "IP address";
         type jt:ipaddr;
         mandatory true;
       }
     }
     output {
       container user-identification {
         uses user-identification-block;
       }
     }
   }
   rpc get-userfw-local-auth-table-user {
     description "Show local user authentication information for the specified user";
     input {
       uses command-forwarding;
       leaf user-name {
         description "User name";
         type string {
           length "1 .. 64";
         }
         mandatory true;
       }
     }
     output {
       container user-identification {
         uses user-identification-block;
       }
     }
   }
   rpc get-userfw-local-auth-table-role {
     description "Show local user authentication information for the specified role";
     input {
       uses command-forwarding;
       leaf role-name {
         description "Role name";
         type string {
           length "1 .. 63";
         }
         mandatory true;
       }
     }
     output {
       container user-identification {
         uses user-identification-block;
       }
     }
   }
   rpc get-userfw-local-auth-table-start {
     description "Show local user authentication table information from a given position";
     input {
       uses command-forwarding;
       leaf start {
         type union {
           type string {
             pattern "<.*>|$.*";
           }
           type uint32 {
             range "1 .. 65535";
           }
         }
         mandatory true;
       }
       leaf count {
         description "Number of local user authentication table entries to show";
         type union {
           type string {
             pattern "<.*>|$.*";
           }
           type uint32 {
             range "1 .. 65535";
           }
         }
         mandatory true;
       }
     }
     output {
       container user-identification {
         uses user-identification-block;
       }
     }
   }
   rpc get-userfw-device-info {
     description "Show all information";
     input {
       uses command-forwarding;
       leaf all {
         type empty;
       }
     }
     output {
       container user-identification {
         uses user-identification-block;
       }
     }
   }
   rpc get-userfw-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-ad-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-jims-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-role-info {
     description "Show all information";
     input {
       uses command-forwarding;
       leaf all {
         type empty;
       }
     }
     output {
       container user-identification {
         uses user-identification-block;
       }
     }
   }
   rpc get-userfw-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-ad-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-jims-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-user-info {
     description "Show all information";
     input {
       uses command-forwarding;
       leaf all {
         type empty;
       }
     }
     output {
       container user-identification {
         uses user-identification-block;
       }
     }
   }
   rpc get-userfw-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-ad-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-jims-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-userfw-source-identity-info {
     description "Show all information";
     input {
       uses command-forwarding;
       leaf all {
         type empty;
       }
     }
     output {
       container user-identification {
         uses user-identification-block;
       }
     }
   }
   rpc get-userfw-source-identity-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       container user-identification {
         uses user-identification-block;
       }
     }
   }
   rpc get-zones-information {
     description "Show security zone information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case name {
           leaf get-zones-named-information {
             description "Show information for a specified zone";
             type string;
           }
         }
         case type {
           leaf type {
             description "Show information for zones of a specified type";
             type enumeration {
               enum "functional" {
                 description "Show information for functional zones";
               }
               enum "security" {
                 description "Show information for security zones";
               }
             }
           }
         }
       }
       leaf level {
         default "detail";
         type enumeration {
           enum "terse" {
             description "Display terse output";
           }
           enum "detail" {
             description "Display detailed output (default)";
           }
         }
       }
     }
     output {
       container zones-information {
         uses zones-information-block;
       }
     }
   }
   rpc get-vrf-groups-information {
     description "Show security vrf-group information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-vrf-groups-named-information {
         description "Show information for a specified vrf-group";
         type string;
       }
       leaf level {
         default "detail";
         type enumeration {
           enum "terse" {
             description "Display terse output";
           }
           enum "detail" {
             description "Display detailed output (default)";
           }
         }
       }
     }
     output {
       container vrf-group-information {
         uses vrf-group-information-block;
       }
     }
   }
   rpc get-tunnel-inspections-profile-information {
     description "Show security tunnel-inspection profile information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-tunnel-inspections-profile-named-information {
         description "Show information for a specified tunnel-inspection profile";
         type string;
       }
     }
     output {
       container tunnel-inspection-profile-information {
         uses tunnel-inspection-profile-information-block;
       }
     }
   }
   rpc get-tunnel-inspections-vni-information {
     description "Show security tunnel-inspection vni information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-tunnel-inspections-vni-named-information {
         description "Show information for a specified tunnel-inspection vni";
         type string;
       }
     }
   }
   rpc get-tunnel-inspection-geneve-profile-information {
     description "Show tunnel-inspection GENEVE profile information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-tunnel-inspection-geneve-profile-information {
         description "Show a specific tunnel-inspection GENEVE profile";
         type string;
       }
     }
     output {
       container tunnel-inspection-geneve-profile-information {
         uses tunnel-inspection-geneve-profile-information-block;
       }
     }
   }
   rpc get-remote-access-default-config {
     description "Show default-config values";
     input {
       uses command-forwarding;
     }
     output {
       container remote-access-default-config {
         uses remote-access-default-config-block;
       }
     }
   }
   rpc get-security-gtp-tunnels {
     description "Show security gtp tunnels";
     input {
       uses command-forwarding;
       leaf level {
         default "brief";
         type enumeration {
           enum "summary" {
             description "Show the summary of GTP tunnels";
           }
           enum "brief" {
             description "Show a brief of each GTP tunnel (default)";
           }
           enum "detail" {
             description "Show a detail of each GTP tunnel";
           }
         }
       }
     }
   }
   rpc get-security-gtp-counters {
     description "Show security gtp counters";
     input {
       uses command-forwarding;
       choice counter-type {
         case path-rate-limit {
           leaf path-rate-limit {
             description "Show path-rate-limit counters";
             type empty;
           }
         }
         case rate-limit {
           leaf rate-limit {
             description "Show rate-limit counters";
             type empty;
           }
         }
         case uli-masked {
           leaf uli-masked {
             description "Show uli-ie masked counters";
             type empty;
           }
         }
         case error {
           leaf error {
             description "Show GTP error counters";
             type empty;
           }
         }
         case tunnel {
           leaf tunnel {
             description "Show GTP tunnel counters";
             type empty;
           }
         }
         case packet {
           leaf packet {
             description "Show GTP packet counters";
             type empty;
           }
         }
         case request {
           leaf request {
             description "Show GTP request counters";
             type empty;
           }
         }
         case data-packet {
           leaf data-packet {
             description "Show GTP-U data packet counters";
             type empty;
           }
         }
         case ha {
           leaf ha {
             description "Show GTP HA counters";
             type empty;
           }
         }
         case all {
           leaf all {
             description "Show all GTP counters";
             type empty;
           }
         }
       }
     }
     output {
       container gtp-show-counters {
         uses gtp-show-counters-block;
       }
     }
   }
   rpc get-security-gtp-counters-message {
     description "Show GTP message counters";
     input {
       uses command-forwarding;
       choice message-type {
         case v0-create-pdp-req {
           leaf v0-create-pdp-req {
             description "Show GTPv0 create PDP context request message";
             type empty;
           }
         }
         case v0-create-pdp-rsp {
           leaf v0-create-pdp-rsp {
             description "Show GTPv0 create PDP context response message";
             type empty;
           }
         }
         case v0-update-pdp-req {
           leaf v0-update-pdp-req {
             description "Show GTPv0 update PDP context request message";
             type empty;
           }
         }
         case v0-update-pdp-rsp {
           leaf v0-update-pdp-rsp {
             description "Show GTPv0 update PDP context response message";
             type empty;
           }
         }
         case v0-delete-pdp-req {
           leaf v0-delete-pdp-req {
             description "Show GTPv0 delete PDP context request message";
             type empty;
           }
         }
         case v0-delete-pdp-rsp {
           leaf v0-delete-pdp-rsp {
             description "Show GTPv0 delete PDP context response message";
             type empty;
           }
         }
         case v0-create-aa-pdp-req {
           leaf v0-create-aa-pdp-req {
             description "Show GTPv0 create AA PDP context request message";
             type empty;
           }
         }
         case v0-create-aa-pdp-rsp {
           leaf v0-create-aa-pdp-rsp {
             description "Show GTPv0 create AA PDP context response message";
             type empty;
           }
         }
         case v0-delete-aa-pdp-req {
           leaf v0-delete-aa-pdp-req {
             description "Show GTPv0 delete AA PDP context request message";
             type empty;
           }
         }
         case v0-delete-aa-pdp-rsp {
           leaf v0-delete-aa-pdp-rsp {
             description "Show GTPv0 delete AA PDP context response message";
             type empty;
           }
         }
         case v0-sgsn-context-req {
           leaf v0-sgsn-context-req {
             description "Show GTPv0 sgsn context request message";
             type empty;
           }
         }
         case v0-sgsn-context-rsp {
           leaf v0-sgsn-context-rsp {
             description "Show GTPv0 sgsn context response message";
             type empty;
           }
         }
         case v0-sgsn-context-ack {
           leaf v0-sgsn-context-ack {
             description "Show GTPv0 sgsn context acknowledge message";
             type empty;
           }
         }
         case v0-others {
           leaf v0-others {
             description "Show GTPv0 others message";
             type empty;
           }
         }
         case v1-create-pdp-req {
           leaf v1-create-pdp-req {
             description "Show GTPv1 create PDP context request message";
             type empty;
           }
         }
         case v1-create-pdp-rsp {
           leaf v1-create-pdp-rsp {
             description "Show GTPv1 create PDP context response message";
             type empty;
           }
         }
         case v1-update-pdp-req {
           leaf v1-update-pdp-req {
             description "Show GTPv1 update PDP context request message";
             type empty;
           }
         }
         case v1-update-pdp-rsp {
           leaf v1-update-pdp-rsp {
             description "Show GTPv1 update PDP context response message";
             type empty;
           }
         }
         case v1-delete-pdp-req {
           leaf v1-delete-pdp-req {
             description "Show GTPv1 delete PDP context request message";
             type empty;
           }
         }
         case v1-delete-pdp-rsp {
           leaf v1-delete-pdp-rsp {
             description "Show GTPv1 delete PDP context response message";
             type empty;
           }
         }
         case v1-sgsn-context-req {
           leaf v1-sgsn-context-req {
             description "Show GTPv1 sgsn context request message";
             type empty;
           }
         }
         case v1-sgsn-context-rsp {
           leaf v1-sgsn-context-rsp {
             description "Show GTPv1 sgsn context response message";
             type empty;
           }
         }
         case v1-sgsn-context-ack {
           leaf v1-sgsn-context-ack {
             description "Show GTPv1 sgsn context acknowledge message";
             type empty;
           }
         }
         case v1-fwd-reloc-req {
           leaf v1-fwd-reloc-req {
             description "Show GTPv1 forward relocation request message";
             type empty;
           }
         }
         case v1-fwd-reloc-rsp {
           leaf v1-fwd-reloc-rsp {
             description "Show GTPv1 forward relocation response message";
             type empty;
           }
         }
         case v1-others {
           leaf v1-others {
             description "Show GTPv1 others message";
             type empty;
           }
         }
         case v2-create-session-req {
           leaf v2-create-session-req {
             description "Show GTPv2 create session request message";
             type empty;
           }
         }
         case v2-create-session-rsp {
           leaf v2-create-session-rsp {
             description "Show GTPv2 create session response message";
             type empty;
           }
         }
         case v2-delete-session-req {
           leaf v2-delete-session-req {
             description "Show GTPv2 delete session request message";
             type empty;
           }
         }
         case v2-delete-session-rsp {
           leaf v2-delete-session-rsp {
             description "Show GTPv2 delete session response message";
             type empty;
           }
         }
         case v2-create-bearer-req {
           leaf v2-create-bearer-req {
             description "Show GTPv2 create bearer request message";
             type empty;
           }
         }
         case v2-create-bearer-rsp {
           leaf v2-create-bearer-rsp {
             description "Show GTPv2 create bearer response message";
             type empty;
           }
         }
         case v2-modify-bearer-req {
           leaf v2-modify-bearer-req {
             description "Show GTPv2 modify bearer request message";
             type empty;
           }
         }
         case v2-modify-bearer-rsp {
           leaf v2-modify-bearer-rsp {
             description "Show GTPv2 modify bearer response message";
             type empty;
           }
         }
         case v2-delete-bearer-req {
           leaf v2-delete-bearer-req {
             description "Show GTPv2 delete bearer request message";
             type empty;
           }
         }
         case v2-delete-bearer-rsp {
           leaf v2-delete-bearer-rsp {
             description "Show GTPv2 delete bearer response message";
             type empty;
           }
         }
         case v2-context-req {
           leaf v2-context-req {
             description "Show GTPv2 context request message";
             type empty;
           }
         }
         case v2-context-rsp {
           leaf v2-context-rsp {
             description "Show GTPv2 context response message";
             type empty;
           }
         }
         case v2-context-ack {
           leaf v2-context-ack {
             description "Show GTPv2 context acknowledge message";
             type empty;
           }
         }
         case v2-fwd-reloc-req {
           leaf v2-fwd-reloc-req {
             description "Show GTPv2 forward relocation request message";
             type empty;
           }
         }
         case v2-fwd-reloc-rsp {
           leaf v2-fwd-reloc-rsp {
             description "Show GTPv2 forward relocation response message";
             type empty;
           }
         }
         case v2-create-ind-fwd-tnl-req {
           leaf v2-create-ind-fwd-tnl-req {
             description "Show GTPv2 create indirect forward tunnel request message";
             type empty;
           }
         }
         case v2-create-ind-fwd-tnl-rsp {
           leaf v2-create-ind-fwd-tnl-rsp {
             description "Show GTPv2 create indirect forward tunnel response message";
             type empty;
           }
         }
         case v2-others {
           leaf v2-others {
             description "Show GTPv2 others message";
             type empty;
           }
         }
         case brief {
           leaf brief {
             description "Show brief GTP messages";
             type empty;
           }
         }
       }
     }
   }
   rpc get-security-gtp-profile {
     description "Show gtp profile";
     input {
       choice profile-choice {
         case profile-name {
           leaf profile-name {
             description "GTP profile name";
             type string {
               length "1 .. 23";
             }
           }
         }
         case all {
           leaf all {
             description "List all GTP profiles";
             type empty;
           }
         }
       }
     }
   }
   rpc get-gtp-gsn-statitics-all {
     description "Show GTP GSN statistics";
     input {
       uses command-forwarding;
     }
     output {
       container gtp-show-statistics-all {
         uses gtp-show-statistics-all-block;
       }
     }
   }
   rpc get-gtp-handover-group {
     description "Show SGSN handover group";
     input {
       choice handover-group-name {
         case group-name {
           leaf group-name {
             description "Handover Group name";
             type string {
               length "1 .. 23";
             }
           }
         }
         case all {
           leaf all {
             description "List all handover-group";
             type empty;
           }
         }
       }
     }
     output {
       container gtp-show-handover-group {
         uses gtp-show-handover-group-block;
       }
     }
   }
   rpc get-gtp-ip-group {
     description "Show GTP ip group";
     input {
       choice ip-group-name {
         case group-name {
           leaf group-name {
             description "IP Group name";
             type string {
               length "1 .. 23";
             }
           }
         }
         case all {
           leaf all {
             description "List all ip-group";
             type empty;
           }
         }
       }
     }
     output {
       container gtp-show-ip-group {
         uses gtp-show-ip-group-block;
       }
     }
   }
   rpc get-gtp-message-ie-profile-v1 {
     description "Show GTPv1 message-ie profile";
     input {
       choice msgie-prof-v1-name {
         case msgie-profile-v1-name {
           leaf msgie-profile-v1-name {
             description "GTPv1 message-ie profile name";
             type string {
               length "1 .. 23";
             }
           }
         }
         case all {
           leaf all {
             description "List all GTPv1 message-ie profile";
             type empty;
           }
         }
       }
     }
     output {
       container gtp-show-msgie-prof-v1 {
         uses gtp-show-msgie-prof-v1-block;
       }
     }
   }
   rpc get-gtp-message-ie-profile-v2 {
     description "Show GTPv2 message-ie profile";
     input {
       choice msgie-prof-v2-name {
         case msgie-profile-v2-name {
           leaf msgie-profile-v2-name {
             description "GTPv2 message-ie profile name";
             type string {
               length "1 .. 23";
             }
           }
         }
         case all {
           leaf all {
             description "List all GTPv2 message-ie profile";
             type empty;
           }
         }
       }
     }
     output {
       container gtp-show-msgie-prof-v2 {
         uses gtp-show-msgie-prof-v2-block;
       }
     }
   }
   rpc get-gtp-grouped-ie-profile {
     description "Show GTP grouped-ie profile";
     input {
       choice grpie-prof-name {
         case grpie-profile-name {
           leaf grpie-profile-name {
             description "GTP grouped-ie profile name";
             type string {
               length "1 .. 23";
             }
           }
         }
         case all {
           leaf all {
             description "List all GTP grouped-ie profile";
             type empty;
           }
         }
       }
     }
     output {
       container gtp-show-grpie-prof {
         uses gtp-show-grpie-prof-block;
       }
     }
   }
   rpc get-gtp-ie-set {
     description "Show GTP IE set";
     input {
       choice ie-set-name_choice {
         case ie-set-name {
           leaf ie-set-name {
             description "GTP IE set name";
             type string {
               length "1 .. 23";
             }
           }
         }
         case all {
           leaf all {
             description "List all GTP IE set";
             type empty;
           }
         }
       }
     }
     output {
       container gtp-show-gtp-prof-ie-set {
         uses gtp-show-gtp-prof-ie-set-block;
       }
     }
   }
   rpc get-gtp-message-list {
     description "Show GTP IE set";
     input {
       choice msg-list-name_choice {
         case msg-list-name {
           leaf msg-list-name {
             description "GTP message list name";
             type string {
               length "1 .. 23";
             }
           }
         }
         case all {
           leaf all {
             description "List all GTP message list";
             type empty;
           }
         }
       }
     }
     output {
       container gtp-show-gtp-msg-list {
         uses gtp-show-gtp-msg-list-block;
       }
     }
   }
   rpc get-gtp-arl {
     description "Show GTP aggregate rate-limit policy";
     input {
       leaf default {
         description "Default Rate-Limit message list";
         type empty;
         mandatory true;
       }
     }
   }
   rpc get-gtp-apn-control {
     description "Show GTP apn-control profile";
     input {
       choice apn-ctrl-name_choice {
         case apn-ctrl-name {
           leaf apn-ctrl-name {
             description "GTP apn-control profile name";
             type string {
               length "1 .. 23";
             }
           }
         }
         case all {
           leaf all {
             description "List all GTP apn-control profile";
             type empty;
           }
         }
       }
     }
     output {
       container gtp-show-apn-control {
         uses gtp-show-apn-control-block;
       }
     }
   }
   rpc get-gtp-apn-control-group {
     description "Show GTP apn-control profile group";
     input {
       choice apn-ctrl-grp-name_choice {
         case apn-ctrl-grp-name {
           leaf apn-ctrl-grp-name {
             description "GTP apn-control profile group name";
             type string {
               length "1 .. 23";
             }
           }
         }
         case all {
           leaf all {
             description "List all GTP apn-control-group";
             type empty;
           }
         }
       }
     }
     output {
       container gtp-show-apn-control-group {
         uses gtp-show-apn-control-group-block;
       }
     }
   }
   rpc get-security-sctp-counters {
     description "Show security sctp counters";
     input {
       uses command-forwarding;
     }
     output {
       container sctp-show-counters {
         uses sctp-show-counters-block;
       }
     }
   }
   rpc get-sctp-counters-detail {
     description "Show the detailed sctp counter information";
     input {
       uses command-forwarding;
     }
   }
   rpc get-sctp-association {
     description "Show security sctp association";
     input {
       uses command-forwarding;
       leaf source-ip {
         description "Match association for source IP";
         type jt:ipaddr;
       }
       leaf source-port {
         description "Match association for source port";
         type union {
           type string {
             pattern "<.*>|$.*";
           }
           type uint32 {
             range "1 .. 65535";
           }
         }
       }
       leaf destination-ip {
         description "Match association for destination IP";
         type jt:ipaddr;
       }
       leaf destination-port {
         description "Match association for destination port";
         type union {
           type string {
             pattern "<.*>|$.*";
           }
           type uint32 {
             range "1 .. 65535";
           }
         }
       }
       leaf guid {
         description "Match association for globally unique identifier";
         type string;
       }
       leaf level {
         type enumeration {
           enum "summary" {
             description "Show output summary";
           }
         }
       }
     }
   }
   rpc get-sctp-association-all {
     description "Show all sctp association entries";
     input {
       uses command-forwarding;
     }
   }
   rpc get-sctp-association-init {
     description "Show init sctp association entries";
     input {
       uses command-forwarding;
     }
   }
   rpc get-metric-collect-information {
     description "Show AWS CloudWatch metric statistics";
     output {
       container metric-collect-information {
         uses metric-collect-information-block;
       }
     }
   }
   rpc get-log-collect-information {
     description "Show AWS CloudWatch log statistics";
     output {
       container log-collect-information {
         uses log-collect-information-block;
       }
     }
   }
   rpc get-cloud-ha-information {
     description "Display high-availability information";
     output {
       container cloud-ha-information {
         uses cloud-ha-information-block;
       }
     }
   }
   rpc get-ioc-np-cache-stats {
     description "Show IOC NP session cache information";
     input {
       uses command-forwarding;
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       container hakr-keychain-information {
         uses hakr-keychain-information-block;
       }
     }
   }
   rpc get-mka-session-information {
     description "Show MKA sessions information";
     input {
       leaf verbosity_level {
         default "brief";
         type enumeration {
           enum "summary" {
             description "Display summary output";
           }
           enum "brief" {
             description "Display brief output (default)";
           }
           enum "detail" {
             description "Display detailed output";
           }
         }
       }
     }
     output {
       container mka-session-information {
         uses mka-session-information-block;
       }
     }
   }
   rpc get-mka-session-interface-information {
     description "Show MKA session on this interface";
     input {
       leaf verbosity_level {
         default "brief";
         type enumeration {
           enum "summary" {
             description "Display summary output";
           }
           enum "brief" {
             description "Display brief output (default)";
           }
           enum "detail" {
             description "Display detailed output";
           }
         }
       }
       leaf interface-name {
         description "Show MKA session for this interface";
         default "all";
         type string {
         }
       }
     }
     output {
       container mka-session-information {
         uses mka-session-information-block;
       }
     }
   }
   rpc get-mka-statistics {
     description "Show MKA statistics";
     output {
       container mka-statistics {
         uses mka-statistics-block;
       }
     }
   }
   rpc get-mka-interface-statistics {
     description "Show MKA statistics on this interface";
     input {
       leaf interface-name {
         description "Show MKA statistics for this interface";
         default "all";
         type string {
         }
       }
     }
     output {
       container mka-statistics {
         uses mka-statistics-block;
       }
     }
   }
   rpc get-macsec-connection-information {
     description "Show MAC Security connections information";
     output {
       container macsec-connection-information {
         uses macsec-connection-information-block;
       }
     }
   }
   rpc get-macsec-connection-interface-information {
     description "Show MAC security connections on this interface";
     input {
       leaf interface-name {
         description "Show MAC security connections for this interface";
         default "all";
         type string {
         }
       }
     }
     output {
       container macsec-connection-information {
         uses macsec-connection-information-block;
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       container macsec-statistics {
         uses macsec-statistics-block;
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type string {
         }
       }
     }
     output {
       container macsec-statistics {
         uses macsec-statistics-block;
       }
     }
   }
   rpc get-macsec-crypto-algorithms {
     description "Show fips validated algorithms used by MACsec module from crypto library";
     output {
       container macsec-crypto-algorithms {
         uses macsec-crypto-algorithms-block;
       }
     }
   }
   rpc get-macsec-crypto-version {
     description "Show version of crypto library used by MACsec module";
     output {
       container macsec-crypto-version {
         uses macsec-crypto-version-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping security-alarm-information-block {
     leaf security-alarms-disabled {
       type empty;
       description "Security alarm subsystem disabled";
     }
     leaf no-security-alarms-active {
       type empty;
       description "No security alarms active";
     }
     leaf no-security-alarms-returned {
       type empty;
       description "No security alarms returned for this filter";
     }
     list security-alarm {
       leaf security-alarm-id {
         type string;
         description "Alarm ID";
       }
       leaf security-alarm-time {
         type string;
         description "Time of the alarm";
       }
       leaf security-alarm-message {
         type string;
         description "Full message of the alarm";
       }
       leaf security-alarm-type {
         type string;
         description "Alarm type";
       }
       leaf severity {
         type string;
         description "Syslog message severity";
       }
       container process {
         leaf name {
           type string;
           description "Syslog message tag name";
         }
         leaf pid {
           type int32;
           description "PID of the process that generated the event";
         }
       }
     }
   }
   grouping security-log-information-block {
     leaf security-logs-disabled {
       type empty;
       description "Security logging disabled";
     }
     leaf no-security-events {
       type empty;
       description "No security events have been logged";
     }
     leaf no-security-events-returned {
       type empty;
       description "No security events were logged matching this filter";
     }
     list security-event {
       leaf security-event-time {
         type string;
         description "Time of the event";
       }
       leaf security-event-message {
         type string;
         description "Full message of the event";
       }
       leaf security-event-id {
         type string;
         description "Event ID";
       }
       leaf severity {
         type string;
         description "Syslog message severity";
       }
       leaf security-event-result {
         type string;
         description "Result of this event (success or failure)";
       }
       leaf security-event-username {
         type string;
         description "Username associated with event";
       }
       leaf security-event-interface-name {
         type string;
         description "Interface name associated with event";
       }
       leaf security-event-protocol {
         type string;
         description "Protocol associated with event";
       }
       leaf security-event-policy-name {
         type string;
         description "Policy name associated with event";
       }
       leaf security-event-destination-address {
         type string;
         description "Destination address associated with event";
       }
       leaf security-event-destination-port {
         type int32;
         description "Destination port associated with event";
       }
       leaf security-event-source-address {
         type string;
         description "Source address associated with event";
       }
       leaf security-event-source-port {
         type int32;
         description "Source port associated with event";
       }
       container process {
         leaf name {
           type string;
           description "Syslog message tag name";
         }
         leaf pid {
           type int32;
           description "PID of the process that generated the event";
         }
       }
     }
   }
   grouping security-log-profile-template-block {
     leaf-list entry {
       type string;
     }
   }
   grouping security-log-profile-config-block {
     leaf-list entry {
       type string;
     }
   }
   grouping security-log-radius-stream-block {
     leaf security-log-radius-stream-stream-name {
       type string;
       description "Stream name";
     }
     leaf security-log-radius-stream-primary-ip {
       type string;
       description "Primary IP";
     }
     leaf security-log-radius-stream-primary-up {
       type string;
       description "Is primary up";
     }
     leaf security-log-radius-stream-primary-sent {
       type uint32;
       description "Log sent from primary server";
     }
     leaf security-log-radius-stream-primary-recv {
       type uint32;
       description "Log received by primary server";
     }
     leaf security-log-radius-stream-primary-retry {
       type uint32;
       description "Number of retry for by primary server";
     }
     leaf security-log-radius-stream-primary-failed {
       type uint32;
       description "Failed log count of primary server";
     }
     leaf security-log-radius-stream-backup-ip {
       type string;
       description "Backup IP";
     }
     leaf security-log-radius-stream-backup-up {
       type string;
       description "Is backup up";
     }
     leaf security-log-radius-stream-backup-sent {
       type uint32;
       description "Log sent from backup server";
     }
     leaf security-log-radius-stream-backup-recv {
       type uint32;
       description "Log received by backup server";
     }
     leaf security-log-radius-stream-backup-retry {
       type uint32;
       description "Number of retry for from backup server";
     }
     leaf security-log-radius-stream-backup-failed {
       type uint32;
       description "Failed log count for backup server";
     }
   }
   grouping casb-policy-information-block {
     container casb-policy-summary {
       description "Casb policy summary";
       leaf total-casb-policies {
         type int32;
         description "Total number of casb policies";
       }
       list casb-policy-list {
         leaf casb-policy-name {
           type string;
           description "Casb policy name";
         }
         leaf casb-policy-id {
           type int32;
           description "Casb policy ID";
         }
       }
     }
     list casb-policy-detail-per-pic {
       description "Casb policy details per pic";
       leaf casb-policy-pic-name {
         type string;
         description "Casb log activity";
       }
       list casb-policy-list-entry {
         description "Casb policy list entry";
         leaf casb-policy-name {
           type string;
           description "Casb policy name";
         }
         leaf casb-policy-id {
           type int32;
           description "Casb policy ID";
         }
       }
     }
   }
   grouping tpm-status-block {
     leaf tpm-enable-status {
       type string;
       description "TPM enable or disable status";
     }
     leaf tpm-ownership-status {
       type string;
       description "TPM ownership status";
     }
     leaf tpm-binding-key-status {
       type string;
       description "TPM binding key status";
     }
     leaf tpm-master-encryption-key-status {
       type string;
       description "TPM master encryption key status";
     }
     leaf tpm-family {
       type string;
       description "TPM Family";
     }
     leaf tpm-firmware-version {
       type string;
       description "TPM Firmware version";
     }
   }
   grouping hsm-status-block {
     leaf hsm-accessible-status {
       type string;
       description "HSM service accessible status";
     }
     leaf hsm-master-binding-key-status {
       type string;
       description "HSM master binding key status";
     }
     leaf hsm-master-encryption-key-status {
       type string;
       description "HSM master encryption key status";
     }
     leaf hsm-azure-key-vault {
       type string;
       description "Azure Key vault configured for vSRX";
     }
     leaf hsm-aws-dynamo-db {
       type string;
       description "AWS DynamoDB configured for vSRX";
     }
     leaf hsm-gcp-key-ring {
       type string;
       description "GCP Key Ring Resource ID configured for vSRX";
     }
   }
   grouping x509-pki-certificate-info-list-block {
     container x509-certificate-info {
       description "Detailed information about an X.509 certificate";
       leaf identifier {
         type string;
         description "Certificate identifier";
       }
       leaf signature-algorithm {
         type string;
         description "Algorithm used by the CA to sign the certificate";
       }
       leaf status {
         type string;
       }
       container public-key {
         leaf public-key-algorithm {
           type string;
           description "Algorithm used for creating the subject public key";
         }
         leaf public-key-length {
           type int32;
           description "Length of X.509 public";
         }
         leaf public-key-verification-status {
           type string;
           description "Verification status of X.509 public key";
         }
         leaf public-key-location {
           type string;
           description "Keypair generated locally or at cloud HSM";
         }
       }
       list fingerprint {
         leaf fingerprint-content {
           type string;
         }
         leaf fingerprint-hash-algorithm {
           type string;
         }
       }
       container issuer {
         container distinguished-name {
           leaf-list organization-name {
             type string;
             description "Organization";
           }
           leaf-list organizational-unit-name {
             type string;
             description "Organization unit";
           }
           leaf-list country-name {
             type string;
             description "Country name";
           }
           leaf-list state-or-province-name {
             type string;
             description "State";
           }
           leaf-list locality-name {
             type string;
             description "Locality";
           }
           leaf-list common-name {
             type string;
             description "Common name";
           }
           leaf-list email-address {
             type string;
             description "E-mail address";
           }
           leaf-list domain-component {
             type string;
             description "Domain component";
           }
           leaf-list dn-serial-number {
             type string;
             description "DN Serial number";
           }
         }
       }
       container subject {
         container distinguished-name {
           leaf-list organization-name {
             type string;
             description "Organization";
           }
           leaf-list organizational-unit-name {
             type string;
             description "Organization unit";
           }
           leaf-list country-name {
             type string;
             description "Country name";
           }
           leaf-list state-or-province-name {
             type string;
             description "State";
           }
           leaf-list locality-name {
             type string;
             description "Locality";
           }
           leaf-list common-name {
             type string;
             description "Common name";
           }
           leaf-list email-address {
             type string;
             description "E-mail address";
           }
           leaf-list domain-component {
             type string;
             description "Domain component";
           }
           leaf-list dn-serial-number {
             type string;
             description "DN Serial number";
           }
         }
       }
       leaf certificate-type {
         type string;
         description "X.509 certificate type";
       }
       leaf ca-profile {
         type string;
         description "CA Profile Name";
       }
       container issue-info {
         leaf recipient {
           type string;
         }
         leaf issued-by {
           type string;
         }
       }
       container validity {
         leaf not-before {
           type string;
           description "Start date of validity period";
         }
         leaf not-after {
           type string;
           description "End date of validity period";
         }
       }
       leaf version {
         type string;
         description "Certificate version";
       }
       leaf cert-chain {
         type string;
         description "Certificate Chain";
       }
       list serial-number-list {
         leaf serial-number-x509 {
           type string;
           description "Serial number of an X.509 certificate";
         }
         leaf serial-number-dec-x509 {
           type string;
           description "Serial number of an X.509 certificate in decimal";
         }
       }
       list public-key-contents-list {
         leaf key-contents {
           type string;
           description "Contents of an X.509 public key";
         }
       }
       list subject-string-list {
         leaf subject-string {
           type string;
           description "Cerificate's distinguished name";
         }
       }
       list alternate-subject-list {
         leaf alternate-subject {
           type string;
           description "Series of alternate subject in X.509 certificate";
         }
       }
       list key-usage-list {
         leaf key-usage {
           type string;
           description "Purpose for which X.509 key is used";
         }
       }
       list distribution-crl-list {
         leaf distribution-crl {
           type string;
           description "Information about a distribution CRL";
         }
       }
       list authority-information-access-ocsp-list {
         leaf authority-information-access-ocsp {
           type string;
           description "Information about ocsp authority-information-access locations";
         }
       }
       list certificate-policy-list {
         leaf certificate-policy {
           type string;
           description "List of certificate policy identifiers";
         }
       }
       container auto-re-enrollment {
         leaf auto-re-enrollment-status {
           type string;
           description "Auto-re-enrollment information";
         }
         leaf auto-re-enrollment-next-trigger-time {
           type string;
           description "Auto-re-enrollment next trigger time";
         }
       }
     }
   }
   grouping x509-pkid-crl-information-list-block {
     container pkid-x509-crl-information {
       description "Detailed information about X.509 certificate revocation list";
       leaf identifier {
         type string;
         description "Certificate identifier";
       }
       leaf crl-version {
         type string;
         description "CRL version";
       }
       leaf crl-number {
         type string;
         description "CRL sequence number";
       }
       leaf crl-issuer {
         type string;
         description "CRL issuer name";
       }
       container crl-validity {
         leaf effective-date {
           type string;
           description "Effective date of CRL";
         }
         leaf next-update {
           type string;
           description "Next update of CRL";
         }
         leaf last-download {
           type string;
           description "Last Download Time of CRL";
         }
       }
       list crl-revocation-list {
         leaf revoked-cert-serial-number {
           type string;
           description "Serial number of revoked certificate";
         }
         leaf crl-revocation-date {
           type string;
           description "Revocation date";
         }
       }
     }
   }
   grouping pki-statistics-block {
     leaf statistics-name {
       type string;
     }
     leaf statistics-value {
       type int32;
     }
   }
   grouping ssl-cloud-certificates-information-block {
     container ssl-cloud-certificate {
       leaf certificate-profile-name {
         type string;
         description "Certificate Profile Name";
       }
       leaf certificate-status {
         type string;
         description "Certificate Status";
       }
       container issue-info {
         leaf recipient {
           type string;
         }
         leaf issued-by {
           type string;
         }
       }
       container validity {
         description "Information about validity period for cloud certificate";
         leaf not-before {
           type string;
           description "Start date of validity period";
         }
         leaf not-after {
           type string;
           description "End date of validity period";
         }
       }
       container public-key {
         description "Information about an X.509 public key";
         leaf public-key-algorithm {
           type string;
           description "Algorithm used for creating the subject public key";
         }
         leaf public-key-length {
           type int32;
           description "Length of X.509 public";
         }
       }
     }
   }
   grouping pki-encryption-status-block {
     leaf pbk-status {
       type string;
       description "PKI binding key status";
     }
     leaf pek-status {
       type string;
       description "PKI encryption key status";
     }
   }
   grouping security-associations-information-block {
     list security-associations-block {
       leaf sa-name {
         type string;
         description "Name of the security association";
       }
       leaf sa-block-state {
         type string;
         description "Status of the SA configuration block";
       }
       container sa-tunnel-information {
         leaf sa-no-information {
           type empty;
           description "Output string when there are no security associations present";
         }
         leaf sa-local-gateway-interface {
           type string;
           description "Local gateway interface";
         }
         leaf sa-local-gateway {
           type jt:ipaddr;
           description "Local gateway address";
         }
         leaf sa-remote-gateway {
           type jt:ipaddr;
           description "Remote gateway address";
         }
         leaf sa-local-identity {
           type string;
           description "Local identity information";
         }
         leaf sa-remote-identity {
           type string;
           description "Remote identity information";
         }
         leaf sa-inside-interface {
           type string;
           description "Name of IPSec interface to internal network";
         }
         leaf sa-tunnel-mtu {
           type int32;
           description "MTU of the IPSec Tunnel";
         }
         leaf sa-udp-encapsulate {
           type string;
           description "UDP encapsulation related information";
         }
         leaf sa-udp-dst-port {
           type string;
           description "UDP encapsulation port related information";
         }
         leaf sa-detect-natt {
           type string;
           description "NAT-T is detected/not detected";
         }
         leaf sa-nat-keepalive {
           type int32;
           description "NAT-T keepalive interval in secs";
         }
       }
       list security-associations {
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
           description "SA Type";
         }
         leaf sa-protocol {
           type string;
           description "IPSec security protocol";
         }
         leaf sa-extended-seq-number {
           type string;
           description "Extended-Sequnce-Number";
         }
         leaf sa-state {
           type string;
           description "Status of the SA";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-anti-replay-service {
           type string;
           description "Anti-replay service";
         }
         leaf sa-replay-window-size {
           type int32;
           description "Replay window size";
         }
         leaf sa-copy-tos-from-inner-ip-header {
           type string;
           description "Copy ToS from inner ip header";
         }
         leaf sa-tos-value {
           type int32;
           description "ToS value";
         }
         leaf sa-copy-ttl-from-inner-ip-header {
           type string;
           description "Copy TTL from inner ip header";
         }
         leaf sa-ttl-value {
           type int32;
           description "TTL value";
         }
         leaf sa-authentication-key {
           type string;
           description "Authentication key in hexadecimal format";
         }
         leaf sa-encryption-key {
           type string;
           description "Encryption key in hexadecimal format";
         }
       }
     }
     container sa-tunnel-information {
     }
     list security-associations {
       leaf sa-extended-seq-number {
         type string;
         description "Extended-Sequnce-Number";
       }
     }
   }
   grouping usp-ipsec-total-statistics-information-block {
     container esp-statistics {
       leaf esp-encrypted-bytes {
         type uint64;
         description "ESP encrypted bytes information";
       }
       leaf esp-decrypted-bytes {
         type uint64;
         description "ESP decrypted bytes information";
       }
       leaf esp-encrypted-packets {
         type uint64;
         description "ESP encrypted packets information";
       }
       leaf esp-decrypted-packets {
         type uint64;
         description "ESP decrypted packets information";
       }
     }
     container ah-statistics {
       leaf ah-input-bytes {
         type uint64;
         description "AH input bytes information";
       }
       leaf ah-output-bytes {
         type uint64;
         description "AH output bytes information";
       }
       leaf ah-input-packets {
         type uint64;
         description "AH input packets information";
       }
       leaf ah-output-packets {
         type uint64;
         description "AH output packets information";
       }
     }
     container multisa-statistics {
       leaf multisa-fc-name {
         type string;
         description "COS Forward Class Name";
       }
       leaf multisa-encrypted-pkts {
         type uint64;
         description "SA Encrypted packets";
       }
       leaf multisa-decrypted-pkts {
         type uint64;
         description "SA Decrypted packets";
       }
       leaf multisa-encrypted-bytes {
         type uint64;
         description "SA Encrypted bytes";
       }
       leaf multisa-decrypted-bytes {
         type uint64;
         description "SA Decrypted bytes";
       }
     }
     container multinode-link-enc-statistics-block {
       container multinode-link-enc-statistics {
         description "Information about single processing unit";
         leaf multinode-link-enc-fpc-num {
           type int32;
           description "FPC";
         }
         leaf multinode-link-enc-pic-num {
           type int32;
           description "PIC";
         }
         list multinode-link-enc-thread-statistics {
           description "Statistics for ha-link encryption tunnel from one processing unit";
           leaf multinode-link-enc-thread-id {
             type int32;
             description "Thread ID of the PIC";
           }
           leaf multinode-link-enc-encrypted-pkts {
             type uint64;
             description "SA Encrypted packets";
           }
           leaf multinode-link-enc-decrypted-pkts {
             type uint64;
             description "SA Decrypted packets";
           }
           leaf multinode-link-enc-encrypted-bytes {
             type uint64;
             description "SA Encrypted bytes";
           }
           leaf multinode-link-enc-decrypted-bytes {
             type uint64;
             description "SA Decrypted bytes";
           }
         }
       }
     }
     container error-statistics {
       leaf ah-authentication-failures {
         type int32;
         description "AH authentication failures information";
       }
       leaf replay-errors {
         type int32;
         description "Replay error information";
       }
       leaf esp-authentication-failures {
         type int32;
         description "ESP authentication failures information";
       }
       leaf esp-decryption-failures {
         type int32;
         description "ESP decryption failures information";
       }
       leaf bad-headers {
         type int32;
         description "Bad header information";
       }
       leaf bad-trailers {
         type int32;
         description "Bad trailer information";
       }
       leaf invalid-spi-errors {
         type int32;
         description "Invalid SPI error information";
       }
       leaf ts-check-fail-errors {
         type int32;
         description "TS check fail error information";
       }
       leaf exceeds-tunnel-mtu {
         type int32;
         description "Exceeds Tunnel MTU";
       }
       leaf discard-errors {
         type int32;
         description "Discard error information";
       }
     }
     container d3p-statistics {
       leaf d3p-too-old-pkts {
         type uint64;
         description "D3P too old packets information";
       }
       leaf d3p-too-new-pkts {
         type uint64;
         description "D3P too new packets information";
       }
       leaf d3p-no-timestamp-pkts {
         type uint64;
         description "D3P no timestamp packets information";
       }
       leaf d3p-unexpected-pkts {
         type uint64;
         description "D3P unexpected packets information";
       }
       leaf d3p-type-err-pkts {
         type uint64;
         description "D3P wrong type packets information";
       }
       leaf d3p-len-err-pkts {
         type uint64;
         description "D3P wrong length information";
       }
       leaf d3p-next-hdr-err-pkts {
         type uint64;
         description "D3P wrong next header packets information";
       }
     }
     container exclude-statistics {
       leaf exclude-created-sess {
         type uint64;
         description "Exclude rule created sessions information";
       }
       leaf exclude-invalidated-sess {
         type uint64;
         description "Exclude rule invalidated sessions information";
       }
     }
     container dynamic-policy-statistics {
       leaf dynamic-policy-created-sess {
         type uint64;
         description "Dynamic policy created sessions information";
       }
       leaf dynamic-policy-invalidated-sess {
         type uint64;
         description "Dynamic policy invalidated sessions information";
       }
     }
     container failopen-statistics {
       leaf failopen-created-sess {
         type uint64;
         description "Fail-open rule created sessions information";
       }
       leaf failopen-invalidated-sess {
         type uint64;
         description "Fail-open rule invalidated sessions information";
       }
     }
     container failclose-statistics {
       leaf failclose-dropped-pkts {
         type uint64;
         description "Fail-close rule dropped packets information";
       }
     }
     leaf pic-name {
       type string;
       description "PIC name";
     }
     leaf service-set-name {
       type string;
       description "Service set name";
     }
     leaf local-gateway {
       type jt:ipaddr;
       description "Local gateway address";
     }
     leaf remote-gateway {
       type jt:ipaddr;
       description "Remote gateway address";
     }
     leaf tunnel-index {
       type int32;
       description "Tunnel index";
     }
     container usp-ipsec-service-set-statistics {
       leaf pic-name {
         type string;
         description "PIC name";
       }
       leaf service-set-name {
         type string;
         description "Service set name";
       }
       leaf local-gateway {
         type jt:ipaddr;
         description "Local gateway address";
       }
       leaf remote-gateway {
         type jt:ipaddr;
         description "Remote gateway address";
       }
       leaf tunnel-index {
         type int32;
         description "Tunnel index";
       }
       container forward-policy-mismatch-statistics {
         leaf policy-mismatch-packets-received {
           type uint64;
           description "Policy mismatch packets information";
         }
         leaf policy-mismatch-packets-sent {
           type uint64;
           description "Policy mismatch packets information";
         }
       }
       container esp-statistics {
         leaf esp-encrypted-bytes {
           type uint64;
           description "ESP encrypted bytes information";
         }
         leaf esp-decrypted-bytes {
           type uint64;
           description "ESP decrypted bytes information";
         }
         leaf esp-encrypted-packets {
           type uint64;
           description "ESP encrypted packets information";
         }
         leaf esp-decrypted-packets {
           type uint64;
           description "ESP decrypted packets information";
         }
       }
       container ah-statistics {
         leaf ah-input-bytes {
           type uint64;
           description "AH input bytes information";
         }
         leaf ah-output-bytes {
           type uint64;
           description "AH output bytes information";
         }
         leaf ah-input-packets {
           type uint64;
           description "AH input packets information";
         }
         leaf ah-output-packets {
           type uint64;
           description "AH output packets information";
         }
       }
       container d3p-statistics {
         leaf d3p-old-packets {
           type uint64;
           description "D3p packets information";
         }
         leaf d3p-new-packets {
           type uint64;
           description "D3p packets information";
         }
         leaf d3p-no-header-packets {
           type uint64;
           description "D3p packets information";
         }
         leaf d3p-unexpected-header-packets {
           type uint64;
           description "D3p packets information";
         }
       }
       container fail-open-statistics {
         leaf fail-open-packets-received {
           type uint64;
           description "Fail open packets information";
         }
         leaf fail-open-packets-sent {
           type uint64;
           description "Fail open packets information";
         }
       }
       container error-statistics {
         leaf ah-authentication-failures {
           type int32;
           description "AH authentication failures information";
         }
         leaf replay-errors {
           type int32;
           description "Replay error information";
         }
         leaf esp-authentication-failures {
           type int32;
           description "ESP authentication failures information";
         }
         leaf esp-decryption-failures {
           type int32;
           description "ESP decryption failures information";
         }
         leaf bad-headers {
           type int32;
           description "Bad header information";
         }
         leaf bad-trailers {
           type int32;
           description "Bad trailer information";
         }
         leaf replay-before-window-drops {
           type int32;
           description "Replay before window drop information";
         }
         leaf replay-pkts {
           type int32;
           description "Replayed pkt information";
         }
         leaf rule-lookup-fail {
           type int32;
           description "Rule lookup failure information";
         }
         leaf no-sa-errors {
           type int32;
           description "No SA error information";
         }
         leaf ip-integrity-errors {
           type int32;
           description "IP Integrity error information";
         }
         leaf exceeds-tunnel-mtu {
           type int32;
           description "Exceeds Tunnel MTU";
         }
         leaf flow-errors {
           type int32;
           description "Flow error information";
         }
         leaf misc-errors {
           type int32;
           description "Misc error information";
         }
         leaf discard-errors {
           type int32;
           description "Discard error information";
         }
         leaf invalid-spi-errors {
           type int32;
           description "Invalid SPI error information";
         }
         leaf ts-check-fail-errors {
           type int32;
           description "TS check fail error information";
         }
       }
     }
   }
   grouping ipsec-unestablished-tunnel-information-block {
     leaf total-inactive-tunnels {
       type int32;
       description "Total number of inactive tunnels";
     }
     leaf total-inactive-tunnels-with-establish-immediately {
       type int32;
       description "Total number of inactive tunnels";
     }
     container ipsec-security-associations {
       leaf sa-installation-state {
         type string;
         description "SA Installation State in Kernel";
       }
       leaf sa-nego-num {
         type int32;
         description "SA nego num";
       }
       leaf sa-nego-fail {
         type int32;
         description "SA nego fail num";
       }
       leaf sa-del-num {
         type int32;
         description "SA defer delete count";
       }
       leaf-list stats-name {
         type string;
       }
       leaf sa-flag {
         type int32;
         description "SA flags";
       }
       container sa-pair-location {
         leaf sa-pair-fpc {
           type int32;
           description "FPC number";
         }
         leaf sa-pair-pic {
           type int32;
           description "PIC number";
         }
         leaf sa-pair-kmd-instance {
           type int32;
           description "KMD instance number";
         }
       }
       container sa-pair-anchorship {
         leaf sa-pair-anchor-thread {
           type uint32;
           description "Thread anchorship information for SA";
         }
       }
       container sa-ipsec-tunnel-event-list {
       }
       leaf sa-tunnel-event-time {
         type string;
         description "Tunnel event occurred time";
       }
     }
     container ipsec-security-associations-block {
       leaf sa-configuration-type {
         type string;
         description "Type of security association configuration";
       }
       leaf sa-tunnel-dist-key {
         type string;
         description "IPsec tunnel distribution key";
       }
       leaf sa-tunnel-event-description {
         type string;
         description "Tunnel event description";
       }
       leaf sa-tunnel-event-num-times {
         type int32;
         description "Number of times tunnel event occurred";
       }
       container sa-advpn-info {
         leaf sa-type {
           type string;
           description "SA Type";
         }
         leaf sa-negotiation-role {
           type string;
           description "Negotiation Role of our end";
         }
       }
       container sa-df-bit-policy-name {
         leaf sa-df-bit {
           type string;
           description "Fragmentation bit";
         }
         leaf sa-copy-outer-dscp {
           type string;
           description "Copying outer IP Header DSCP & ECN to Inner IP Header";
         }
         leaf sa-bind-interface {
           type string;
           description "VPN bind-interface";
         }
         leaf sa-tunnel-mtu {
           type int32;
           description "MTU of the IPSec Tunnel";
         }
         leaf sa-policy-name {
           type string;
           description "Policy name";
         }
       }
       container sa-dev-info {
         leaf sa-port {
           type int32;
           description "Port";
         }
         leaf sa-nego-num {
           type int32;
           description "SA nego num";
         }
         leaf sa-nego-fail {
           type int32;
           description "SA nego fail num";
         }
         leaf sa-del-num {
           type int32;
           description "SA defer delete count";
         }
         leaf sa-flag {
           type int32;
           description "SA flags";
         }
         leaf-list stats-name {
           type string;
         }
       }
       container multi-sa-info {
         leaf multi-sa-cfg-sas {
           type int32;
           description "Number of SA configured for negitiation";
         }
         leaf multi-sa-nego-sas {
           type int32;
           description "Number of SAs negitiated with peer";
         }
       }
       container sa-ha-link-encryption {
         leaf sa-ha-link-type {
           type string;
           description "Type of HA Link encryption";
         }
       }
       container sa-anchorship {
         leaf sa-anchor-thread {
           type uint32;
           description "Thread anchorship information for SA";
         }
       }
       list sa-ts-remote-identity {
         leaf sa-ts-protocol {
           type string;
           description "Sa Ts Protocol";
         }
         leaf sa-ts-port {
           type string;
           description "Sa Ts Port";
         }
         leaf sa-ts-ip {
           type string;
           description "Sa Ts IP";
         }
       }
       list sa-ts-local-identity {
         leaf sa-ts-protocol {
           type string;
           description "Sa Ts Protocol";
         }
         leaf sa-ts-port {
           type string;
           description "Sa Ts Port";
         }
         leaf sa-ts-ip {
           type string;
           description "Sa Ts IP";
         }
       }
       container sa-tunnel-dist {
         leaf sa-tunnel-dist-key {
           type string;
           description "IPsec tunnel distribution key";
         }
       }
       container sa-ipsec-tunnel-event {
         leaf sa-tunnel-event-time {
           type string;
           description "Tunnel event occurred time";
         }
         leaf sa-tunnel-event-description {
           type string;
           description "Tunnel event description";
         }
         leaf sa-tunnel-event-num-times {
           type int32;
           description "Number of times tunnel event occurred";
         }
         leaf sa-tunnel-event-repeat-seq-description {
           type string;
           description "Tunnel event repeat sequence description";
         }
       }
       container sa-location {
         leaf sa-fpc {
           type int32;
           description "FPC number";
         }
         leaf sa-pic {
           type int32;
           description "PIC number";
         }
         leaf sa-kmd-instance {
           type int32;
           description "KMD instance number";
         }
       }
       container ipsec-security-associations {
         leaf sa-tunnel-index {
           type int32;
           description "Tunnel index";
         }
         leaf sa-port {
           type int32;
           description "Port";
         }
         leaf sa-remote-gateway {
           type jt:ipaddr;
           description "Remote gateway address";
         }
         leaf sa-pending-sas {
           type int32;
           description "Pending sas to negotiate with Peer";
         }
         leaf sa-installation-state {
           type string;
           description "SA Installation State in Kernel";
         }
         leaf sa-nego-num {
           type int32;
           description "SA nego num";
         }
         leaf sa-nego-fail {
           type int32;
           description "SA nego fail num";
         }
         leaf sa-del-num {
           type int32;
           description "SA defer delete count";
         }
         leaf-list stats-name {
           type string;
         }
         leaf sa-flag {
           type int32;
           description "SA flags";
         }
         container sa-pair-location {
           leaf sa-pair-fpc {
             type int32;
             description "FPC number";
           }
           leaf sa-pair-pic {
             type int32;
             description "PIC number";
           }
           leaf sa-pair-kmd-instance {
             type int32;
             description "KMD instance number";
           }
         }
         container sa-pair-anchorship {
           leaf sa-pair-anchor-thread {
             type uint32;
             description "Thread anchorship information for SA";
           }
         }
         container sa-ipsec-tunnel-event-list {
           container sa-ipsec-tunnel-event {
             leaf sa-tunnel-event-description {
               type string;
               description "Tunnel event description";
             }
             leaf sa-tunnel-event-num-times {
               type int32;
               description "Number of times tunnel event occurred";
             }
           }
         }
         leaf sa-tunnel-event {
           type string;
           description "Tunnel event description";
         }
         leaf sa-tunnel-event-num-times {
           type int32;
           description "Number of times tunnel event occurred";
         }
         leaf sa-tunnel-event-time {
           type string;
           description "Tunnel event occurred time";
         }
         leaf sa-direction {
           type string;
           description "Direction of the security association";
         }
         leaf sa-spi {
           type string;
           description "Security Parameter Index";
         }
         leaf sa-aux-spi {
           type string;
           description "Auxiliary Security Parameter Index";
         }
         leaf sa-mode {
           type string;
           description "Mode of the security association";
         }
         leaf sa-type {
           type string;
           description "SA Type";
         }
         leaf sa-state {
           type string;
           description "Status of the SA";
         }
         leaf sa-vpn-monitoring-state {
           type string;
           description "VPN Monitoring State";
         }
         leaf sa-vpn-monitoring-mode {
           type string;
           description "VPN Monitoring Mode";
         }
         leaf sa-vpn-monitoring-interval {
           type int32;
           description "VPN Monitoring Interval";
         }
         leaf sa-vpn-monitoring-threshold {
           type int32;
           description "VPN Monitoring Threshold";
         }
         leaf sa-protocol {
           type string;
           description "IPSec security protocol";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-hard-lifetime {
           type string;
           description "Remaining lifetime, in seconds or kilobytes, before hard lifetime expires";
         }
         leaf sa-lifesize-remaining {
           type string;
           description "Lifetime Remaining in Kilo Bytes";
         }
         leaf sa-anti-replay-service {
           type string;
           description "Anti-replay service";
         }
         leaf sa-replay-window-size {
           type int32;
           description "Replay window size";
         }
         leaf sa-extended-seq-number {
           type string;
           description "Extended-Sequnce-Number";
         }
         leaf sa-fc-name {
           type int32;
           description "COS Forward class Name";
         }
         leaf sa-tunnel-establishment {
           type string;
           description "IPsec Establish tunnels option";
         }
         leaf sa-ike-index {
           type int32;
           description "IKE SA index";
         }
       }
       leaf sa-tunnel-event {
         type string;
         description "Tunnel event description";
       }
     }
     container ipsec-gvpn-inactive-tunnel-info-block {
       leaf sa-gvpn-server {
         type string;
         description "Group VPN Server Address";
       }
       leaf sa-port {
         type int32;
         description "Port";
       }
       leaf sa-gvpn-groupid {
         type int32;
         description "Group VPN Group Id";
       }
       leaf sa-virtual-system {
         type string;
         description "Virtual System";
       }
       leaf sa-down-reason {
         type string;
         description "IPsec SA down reason";
       }
       leaf sa-configuration-type {
         type string;
         description "Type of security association configuration";
       }
       leaf sa-local-gateway {
         type jt:ipaddr;
         description "Local gateway address";
       }
       leaf sa-remote-gateway {
         type jt:ipaddr;
         description "Remote gateway address";
       }
       leaf sa-local-identity {
         type string;
         description "Local identity information";
       }
       leaf sa-remote-identity {
         type string;
         description "Remote identity information";
       }
       leaf sa-vpn-name {
         type string;
         description "VPN Name";
       }
       leaf sa-match-dir {
         type string;
         description "Group VPN rule match direction";
       }
       leaf sa-tunnel-mtu {
         type int32;
         description "MTU of the IPSec Tunnel";
       }
       leaf sa-recovery-probe {
         type int32;
         description "SA recover probe enabled";
       }
       leaf sa-rekey-needed {
         type string;
         description "SA rekey needed";
       }
       container ipsec-gvpn-sa-stats {
         leaf-list ipsec-sa-stats {
           type string;
           description "IPsec SA stats";
         }
       }
       container sa-df-bit-policy-name {
         leaf sa-df-bit {
           type string;
           description "Fragmentation bit";
         }
       }
       container gvpn-sa-down-reason {
         leaf sa-down-reason {
           type string;
           description "IPsec SA down reason";
         }
       }
     }
   }
   grouping ipsec-tunnel-event-statistics-block {
     leaf sa-tunnel-event-description {
       type string;
       description "Tunnel event description";
     }
     leaf sa-tunnel-event-num-times {
       type int32;
       description "Number of times tunnel event occurred";
     }
   }
   grouping ipsec-tunnel-distribution-information-block {
     container ipsec-tunnel-distribution {
       leaf ipsec-tunnel-dist-header-tunnel-id {
         type string;
         description "Name of tunnel Id header";
       }
       leaf ipsec-tunnel-dist-header-fpc {
         type string;
         description "Slot Number of FPC header ";
       }
       leaf ipsec-tunnel-dist-header-pic {
         type string;
         description "Slot number of PIC header ";
       }
       leaf ipsec-tunnel-dist-header-thread-id {
         type string;
         description "Name of thread-id header ";
       }
       leaf ipsec-tunnel-dist-header-dist-profile {
         type string;
         description "Tunnel diistribution profile info header";
       }
       container ipsec-tunnel-distribution-block {
         leaf sa-tunnel-id {
           type int32;
           description "Tunnel id";
         }
         leaf ipsec-fpc {
           type uint32;
           description "FPC slot used by Flow";
         }
         leaf ipsec-pic {
           type uint32;
           description "PIC slot used by Flow";
         }
         leaf ipsec-thread-id {
           type uint32;
           description "Thread Id used by Flow";
         }
         leaf sa-tunnel-dist-key {
           type string;
           description "IPsec tunnel distribution key";
         }
       }
     }
     container ipsec-tunnel-distribution-summary {
       leaf ipsec-tunnel-dist-header-num-of-tunnels {
         type string;
         description "Name of number of tunnels header ";
       }
       leaf ipsec-tunnel-dist-header-fpc {
         type string;
         description "Slot Number of FPC header ";
       }
       leaf ipsec-tunnel-dist-header-pic {
         type string;
         description "Slot number of PIC header ";
       }
       leaf ipsec-tunnel-dist-header-thread-id {
         type string;
         description "Name of thread-id header ";
       }
       leaf ipsec-tunnel-dist-header-dist-profile {
         type string;
         description "Tunnel diistribution profile info header";
       }
     }
     container ipsec-tunnel-distribution-summary-cpuload {
       leaf ipsec-tunnel-dist-header-num-of-tunnels {
         type string;
         description "Name of number of tunnels header ";
       }
       leaf ipsec-tunnel-dist-header-fpc {
         type string;
         description "Slot Number of FPC header ";
       }
       leaf ipsec-tunnel-dist-header-pic {
         type string;
         description "Slot number of PIC header ";
       }
       leaf ipsec-tunnel-dist-header-thread-id {
         type string;
         description "Name of thread-id header ";
       }
       leaf ipsec-tunnel-dist-header-cpu-load-m {
         type string;
         description "SPU 1 minute load header";
       }
       leaf ipsec-tunnel-dist-header-cpu-load-h {
         type string;
         description "SPU 1 hour load header";
       }
       leaf ipsec-tunnel-dist-header-cpu-load-d {
         type string;
         description "SPU 1 day load header";
       }
     }
     container ipsec-tunnel-distribution-block {
       leaf sa-tunnel-id {
         type int32;
         description "Tunnel id";
       }
       leaf ipsec-fpc {
         type uint32;
         description "FPC slot used by Flow";
       }
       leaf ipsec-pic {
         type uint32;
         description "PIC slot used by Flow";
       }
       leaf ipsec-thread-id {
         type uint32;
         description "Thread Id used by Flow";
       }
     }
     container ipsec-tunnel-distribution-summary-block {
       leaf ipsec-thread-number-of-tunnels {
         type uint32;
         description "Number of Tunnels anchored on the thread";
       }
       leaf ipsec-fpc {
         type uint32;
         description "FPC slot used by Flow";
       }
       leaf ipsec-pic {
         type uint32;
         description "PIC slot used by Flow";
       }
       leaf ipsec-thread-id {
         type uint32;
         description "Thread Id used by Flow";
       }
       leaf sa-tunnel-dist-key {
         type string;
         description "IPsec tunnel distribution key";
       }
     }
     container ipsec-tunnel-distribution-summary-cpuload-block {
       leaf ipsec-thread-number-of-tunnels {
         type uint32;
         description "Number of Tunnels anchored on the thread";
       }
       leaf ipsec-fpc {
         type uint32;
         description "FPC slot used by Flow";
       }
       leaf ipsec-pic {
         type uint32;
         description "PIC slot used by Flow";
       }
       leaf ipsec-thread-id {
         type uint32;
         description "Thread Id used by Flow";
       }
       leaf cpu-load-m {
         type string;
         description "SPU 1 minute load";
       }
       leaf cpu-load-h {
         type string;
         description "SPU 1 hour load";
       }
       leaf cpu-load-d {
         type string;
         description "SPU 1 day load";
       }
     }
   }
   grouping ike-peers-statistics-information-block {
     container ike-peer-information {
       leaf ike-peer-gateway-name {
         type string;
         description "Peer Gateway Name";
       }
       leaf ike-peer-active-count {
         type uint32;
         description "Peer Active count";
       }
       leaf ike-peer-in-progress-count {
         type uint32;
         description "Peer In-progress count";
       }
       leaf ike-peer-failed-count {
         type uint32;
         description "Peer Failed count";
       }
       leaf ike-peer-blocked-count {
         type uint32;
         description "Peer Blocked count";
       }
       leaf ike-peer-backoff-count {
         type uint32;
         description "Peer Backoff count";
       }
     }
   }
   grouping ike-peers-in-progress-information-block {
     container ike-peer-information {
       leaf ike-peer-index {
         type uint32;
         description "Peer Index";
       }
       leaf ike-peer-event-time {
         type string;
         description "Peer Event Time";
       }
       leaf ike-peer-remote-ip-address {
         type jt:ipaddr;
         description "Peer Remote IP Address";
       }
       leaf ike-peer-role {
         type string;
         description "Peer Role";
       }
       leaf ike-peer-gateway-name {
         type string;
         description "Peer Gateway Name";
       }
       leaf ike-peer-exchange-type {
         type string;
         description "Peer Exchange Type";
       }
       leaf ike-peer-authentication-method {
         type string;
         description "Peer Authentication method";
       }
       leaf ike-peer-remote-port {
         type uint32;
         description "Peer Remote Port";
       }
       leaf ike-peer-local-ip-address {
         type jt:ipaddr;
         description "Peer Local IP Address";
       }
       leaf ike-peer-local-port {
         type uint32;
         description "Peer Local Port";
       }
       leaf ike-peer-negotiation-phase {
         type string;
         description "Peer Negotiation phase";
       }
       leaf ike-peer-routing-instance {
         type string;
         description "Peer Routing Instance";
       }
       leaf ike-peer-natt-detection {
         type string;
         description "Peer NATT detection";
       }
     }
   }
   grouping ike-peers-failed-information-block {
     container ike-peer-information {
       leaf ike-peer-index {
         type uint32;
         description "Peer Index";
       }
       leaf ike-peer-event-time {
         type string;
         description "Peer Event Time";
       }
       leaf ike-peer-remote-ip-address {
         type jt:ipaddr;
         description "Peer Remote IP Address";
       }
       leaf ike-peer-role {
         type string;
         description "Peer Role";
       }
       leaf ike-peer-gateway-name {
         type string;
         description "Peer Gateway Name";
       }
       leaf ike-peer-negotiation-phase {
         type string;
         description "Peer Negotiation phase";
       }
       leaf ike-peer-fail-reason {
         type string;
         description "Peer Failure Reason";
       }
       leaf ike-peer-exchange-type {
         type string;
         description "Peer Exchange Type";
       }
       leaf ike-peer-authentication-method {
         type string;
         description "Peer Authentication method";
       }
       leaf ike-peer-remote-port {
         type uint32;
         description "Peer Remote Port";
       }
       leaf ike-peer-local-ip-address {
         type jt:ipaddr;
         description "Peer Local IP Address";
       }
       leaf ike-peer-local-port {
         type uint32;
         description "Peer Local Port";
       }
       leaf ike-peer-routing-instance {
         type string;
         description "Peer Routing Instance";
       }
       leaf ike-peer-natt-detection {
         type string;
         description "Peer NATT detection";
       }
       leaf ike-peer-remote-id {
         type string;
         description "Peer Remote IKE ID";
       }
       leaf ike-peer-remote-id-type {
         type string;
         description "Peer Remote IKE ID type";
       }
       leaf ike-peer-aaa-username {
         type string;
         description "Peer AAA Username";
       }
     }
   }
   grouping ike-peers-blocked-information-block {
     container ike-peer-information {
       leaf ike-peer-index {
         type uint32;
         description "Peer Index";
       }
       leaf ike-peer-event-time {
         type string;
         description "Peer Event Time";
       }
       leaf ike-peer-remote-ip-address {
         type jt:ipaddr;
         description "Peer Remote IP Address";
       }
       leaf ike-peer-role {
         type string;
         description "Peer Role";
       }
       leaf ike-peer-gateway-name {
         type string;
         description "Peer Gateway Name";
       }
       leaf ike-peer-blocklist-name {
         type string;
         description "Peer Blocklist Name";
       }
       leaf ike-peer-blocklist-rule-name {
         type string;
         description "Peer Blocklist Rule Name";
       }
       leaf ike-peer-exchange-type {
         type string;
         description "Peer Exchange Type";
       }
       leaf ike-peer-authentication-method {
         type string;
         description "Peer Authentication method";
       }
       leaf ike-peer-remote-port {
         type uint32;
         description "Peer Remote Port";
       }
       leaf ike-peer-local-ip-address {
         type jt:ipaddr;
         description "Peer Local IP Address";
       }
       leaf ike-peer-local-port {
         type uint32;
         description "Peer Local Port";
       }
       leaf ike-peer-negotiation-phase {
         type string;
         description "Peer Negotiation phase";
       }
       leaf ike-peer-routing-instance {
         type string;
         description "Peer Routing Instance";
       }
       leaf ike-peer-natt-detection {
         type string;
         description "Peer NATT detection";
       }
       leaf ike-peer-remote-id {
         type string;
         description "Peer Remote IKE ID";
       }
       leaf ike-peer-remote-id-type {
         type string;
         description "Peer Remote IKE ID type";
       }
     }
   }
   grouping ike-peers-backoff-information-block {
     container ike-peer-information {
       leaf ike-peer-index {
         type uint32;
         description "Peer Index";
       }
       leaf ike-peer-event-time {
         type string;
         description "Peer Event Time";
       }
       leaf ike-peer-backoff-time-left {
         type string;
         description "Peer Backoff Time Left";
       }
       leaf ike-peer-remote-ip-address {
         type jt:ipaddr;
         description "Peer Remote IP Address";
       }
       leaf ike-peer-role {
         type string;
         description "Peer Role";
       }
       leaf ike-peer-gateway-name {
         type string;
         description "Peer Gateway Name";
       }
       leaf ike-peer-fail-reason {
         type string;
         description "Peer Failure Reason";
       }
       leaf ike-peer-exchange-type {
         type string;
         description "Peer Exchange Type";
       }
       leaf ike-peer-authentication-method {
         type string;
         description "Peer Authentication method";
       }
       leaf ike-peer-remote-port {
         type uint32;
         description "Peer Remote Port";
       }
       leaf ike-peer-local-ip-address {
         type jt:ipaddr;
         description "Peer Local IP Address";
       }
       leaf ike-peer-local-port {
         type uint32;
         description "Peer Local Port";
       }
       leaf ike-peer-negotiation-phase {
         type string;
         description "Peer Negotiation phase";
       }
       leaf ike-peer-routing-instance {
         type string;
         description "Peer Routing Instance";
       }
       leaf ike-peer-natt-detection {
         type string;
         description "Peer NATT detection";
       }
       leaf ike-peer-remote-id {
         type string;
         description "Peer Remote IKE ID";
       }
       leaf ike-peer-remote-id-type {
         type string;
         description "Peer Remote IKE ID type";
       }
       leaf ike-peer-aaa-username {
         type string;
         description "Peer AAA Username";
       }
     }
   }
   grouping ike-show-pre-shared-key-information-block {
     leaf pre-shared-key {
       type string;
     }
   }
   grouping ike-config-management-statistics-information-block {
     container ike-config-gw-cfg-statistics {
       leaf ike-gw-cfg-shared {
         type int32;
       }
       leaf ike-gw-cfg-delete-action {
         type int32;
       }
       leaf ike-gw-cfg-ifd-down {
         type int32;
       }
       leaf ike-gw-cfg-ifl-down {
         type int32;
       }
       leaf ike-gw-cfg-remote-addr-type-mismatch {
         type int32;
       }
       leaf ike-gw-cfg-local-addr-type-mismatch {
         type int32;
       }
       leaf ike-gw-cfg-iff-down {
         type int32;
       }
       leaf ike-gw-cfg-ifa-primary-addr-down {
         type int32;
       }
       leaf ike-gw-cfg-ifa-conf-addr-down {
         type int32;
       }
       leaf ike-gw-cfg-srg-not-avail {
         type int32;
       }
       leaf ike-gw-cfg-ready {
         type int32;
       }
     }
     container ike-config-vpn-cfg-statistics {
       leaf ike-vpn-cfg-shared {
         type int32;
       }
       leaf ike-vpn-cfg-v4-iff-down {
         type int32;
       }
       leaf ike-vpn-cfg-v6-iff-down {
         type int32;
       }
       leaf ike-vpn-cfg-iff-down {
         type int32;
       }
       leaf ike-vpn-cfg-v4-ts-down {
         type int32;
       }
       leaf ike-vpn-cfg-v6-ts-down {
         type int32;
       }
       leaf ike-vpn-cfg-delete-shared-ts {
         type int32;
       }
       leaf ike-vpn-cfg-all-ts-inactive {
         type int32;
       }
       leaf ike-vpn-cfg-platform-cfg-not-ready {
         type int32;
       }
       leaf ike-vpn-cfg-platform-list-not-ready {
         type int32;
       }
       leaf ike-vpn-cfg-dist-profile-not-ready {
         type int32;
       }
       leaf ike-vpn-cfg-sa-key-req-not-processed {
         type int32;
       }
       leaf ike-vpn-cfg-ready {
         type int32;
       }
     }
     container ike-config-p1-cfg-object-share-statistics {
       leaf ike-p1-cfg-shared-count {
         type int32;
       }
       leaf ike-p1-cfg-add-send-to-iked-success {
         type int32;
       }
       leaf ike-p1-cfg-add-send-to-iked-fail {
         type int32;
       }
       leaf ike-p1-cfg-del-create-fail {
         type int32;
       }
       leaf ike-p1-cfg-del-send-to-iked-success {
         type int32;
       }
       leaf ike-p1-cfg-del-send-to-iked-fail {
         type int32;
       }
       leaf ike-p1-cfg-del-ignore {
         type int32;
       }
     }
     container ike-config-p2-cfg-object-share-statistics {
       leaf ike-p2-cfg-shared-count {
         type int32;
       }
       leaf ike-p2-cfg-add-send-to-iked-success {
         type int32;
       }
       leaf ike-p2-cfg-add-send-to-iked-fail {
         type int32;
       }
       leaf ike-p2-cfg-add-create-fail {
         type int32;
       }
       leaf ike-p2-cfg-add-fill-p2-fail {
         type int32;
       }
       leaf ike-p2-cfg-add-fill-ts-fail {
         type int32;
       }
       leaf ike-p2-cfg-add-fill-platform-info-fail {
         type int32;
       }
       leaf ike-p2-cfg-add-fill-svcs-platform-info-fail {
         type int32;
       }
       leaf ike-p2-cfg-add-fill-tunnel-dist-info-fail {
         type int32;
       }
       leaf ike-p2-cfg-del-create-fail {
         type int32;
       }
       leaf ike-p2-cfg-del-send-to-iked-success {
         type int32;
       }
       leaf ike-p2-cfg-del-send-to-iked-fail {
         type int32;
       }
       leaf ike-p2-cfg-del-update-ts-fail {
         type int32;
       }
       leaf ike-p2-cfg-del-unknown-action {
         type int32;
       }
     }
   }
   grouping ike-config-management-snmp-stats-block {
     container ike-snmp-ike-tun-mon-table-statistics {
       leaf ike-tun-mon-table-get-requests {
         type int32;
       }
       leaf ike-tun-mon-table-next-requests {
         type int32;
       }
       leaf ike-tun-mon-table-get-request-timeout {
         type int32;
       }
       leaf ike-tun-mon-table-next-request-timeout {
         type int32;
       }
       leaf ike-tun-mon-table-cache-timer-expire {
         type int32;
       }
       leaf ike-tun-mon-table-cache-delete {
         type int32;
       }
       leaf ike-tun-mon-table-lookup-calls {
         type int32;
       }
       leaf ike-tun-mon-table-lookup-invalid-key {
         type int32;
       }
       leaf ike-tun-mon-table-lookup-key-alloc-err {
         type int32;
       }
       leaf ike-tun-mon-table-lookup-send-req-fail {
         type int32;
       }
       leaf ike-tun-mon-table-next-lookup-calls {
         type int32;
       }
       leaf ike-tun-mon-table-next-lookup-invalid-key {
         type int32;
       }
       leaf ike-tun-mon-table-next-lookup-key-alloc-err {
         type int32;
       }
       leaf ike-tun-mon-table-next-lookup-req-sent-now {
         type int32;
       }
       leaf ike-tun-mon-table-next-lookup-send-req-fail {
         type int32;
       }
       leaf ike-tun-mon-table-next-lookup-req-sent-before {
         type int32;
       }
       leaf ike-tun-mon-table-next-lookup-response-sent {
         type int32;
       }
       leaf ike-tun-mon-table-get-key-calls {
         type int32;
       }
       leaf ike-tun-mon-table-get-key-null-data {
         type int32;
       }
       leaf ike-tun-mon-table-get-key-invalid-key {
         type int32;
       }
       leaf ike-tun-mon-table-get-responses {
         type int32;
       }
       leaf ike-tun-mon-table-get-response-null {
         type int32;
       }
       leaf ike-tun-mon-table-get-response-sent {
         type int32;
       }
       leaf ike-tun-mon-table-next-responses {
         type int32;
       }
       leaf ike-tun-mon-table-next-responses-null {
         type int32;
       }
       leaf ike-tun-mon-table-next-response-complete {
         type int32;
       }
       leaf ike-tun-mon-table-next-resp-ike-sa-add-mem-alloc-fail {
         type int32;
       }
       leaf ike-tun-mon-table-next-resp-ike-sa-add-fail {
         type int32;
       }
       leaf ike-tun-mon-table-next-resp-ike-sa-add-success {
         type int32;
       }
       leaf ike-tun-mon-table-next-response-sent {
         type int32;
       }
       leaf ike-tun-mon-table-next-req-sent {
         type int32;
       }
       leaf ike-tun-mon-table-next-send-req-fail {
         type int32;
       }
       leaf ike-tun-mon-table-next-null-response-sent {
         type int32;
       }
       leaf ike-tun-mon-table-iked-req-timeout {
         type int32;
       }
       leaf ike-tun-mon-table-start-req-sent-timer {
         type int32;
       }
       leaf ike-tun-mon-table-clear-req-sent-timer {
         type int32;
       }
       leaf ike-tun-mon-table-cache-start-timer {
         type int32;
       }
       leaf ike-tun-mon-table-get-value-calls {
         type int32;
       }
       leaf ike-tun-mon-table-get-value-errs {
         type int32;
       }
       leaf ike-tun-mon-table-local-gw-addr-type {
         type int32;
       }
       leaf ike-tun-mon-table-local-gw-addr {
         type int32;
       }
       leaf ike-tun-mon-table-state {
         type int32;
       }
       leaf ike-tun-mon-table-initiator-cookie {
         type int32;
       }
       leaf ike-tun-mon-table-responder-cookie {
         type int32;
       }
       leaf ike-tun-mon-table-local-role {
         type int32;
       }
       leaf ike-tun-mon-table-local-id-type {
         type int32;
       }
       leaf ike-tun-mon-table-local-id-value {
         type int32;
       }
       leaf ike-tun-mon-table-local-cert-name {
         type int32;
       }
       leaf ike-tun-mon-table-remote-id-type {
         type int32;
       }
       leaf ike-tun-mon-table-remote-id-value {
         type int32;
       }
       leaf ike-tun-mon-table-nego-mode {
         type int32;
       }
       leaf ike-tun-mon-table-diff-hellman-grp {
         type int32;
       }
       leaf ike-tun-mon-table-encrypt-algo {
         type int32;
       }
       leaf ike-tun-mon-table-hash-algo {
         type int32;
       }
       leaf ike-tun-mon-table-auth-method {
         type int32;
       }
       leaf ike-tun-mon-table-life-time {
         type int32;
       }
       leaf ike-tun-mon-table-active-time {
         type int32;
       }
       leaf ike-tun-mon-table-in-octets {
         type int32;
       }
       leaf ike-tun-mon-table-in-pkts {
         type int32;
       }
       leaf ike-tun-mon-table-out-octets {
         type int32;
       }
       leaf ike-tun-mon-table-out-pkts {
         type int32;
       }
       leaf ike-tun-mon-table-xauth-user-id {
         type int32;
       }
       leaf ike-tun-mon-table-dpd-down-count {
         type int32;
       }
       leaf ike-tun-mon-table-initiator-ikev2-ipsec-sa-rekey-request-out {
         type int32;
       }
       leaf ike-tun-mon-table-initiator-ikev2-ipsec-sa-rekey-response-in {
         type int32;
       }
       leaf ike-tun-mon-table-initiator-ikev2-ipsec-sa-rekey-no-proposal-chosen-in {
         type int32;
       }
       leaf ike-tun-mon-table-initiator-ikev2-ipsec-sa-rekey-invalid-ke-in {
         type int32;
       }
       leaf ike-tun-mon-table-initiator-ikev2-ipsec-sa-rekey-ts-unacceptable-in {
         type int32;
       }
       leaf ike-tun-mon-table-initiator-ikev2-ipsec-sa-rekey-res-verify-sa-fail {
         type int32;
       }
       leaf ike-tun-mon-table-initiator-ikev2-ipsec-sa-rekey-res-verify-dh-group-fail {
         type int32;
       }
       leaf ike-tun-mon-table-initiator-ikev2-ipsec-sa-rekey-res-verify-ts-fail {
         type int32;
       }
       leaf ike-tun-mon-table-initiator-ikev2-ipsec-sa-rekey-res-dh-compute-key-fail {
         type int32;
       }
       leaf ike-tun-mon-table-responder-ikev2-ipsec-sa-rekey-request-in {
         type int32;
       }
       leaf ike-tun-mon-table-responder-ikev2-ipsec-sa-rekey-response-out {
         type int32;
       }
       leaf ike-tun-mon-table-responder-ikev2-ipsec-sa-rekey-no-proposal-chosen-out {
         type int32;
       }
       leaf ike-tun-mon-table-responder-ikev2-ipsec-sa-rekey-invalid-ke-out {
         type int32;
       }
       leaf ike-tun-mon-table-responder-ikev2-ipsec-sa-rekey-ts-unacceptable-out {
         type int32;
       }
       leaf ike-tun-mon-table-responder-ikev2-ipsec-sa-rekey-res-dh-compute-key-fail {
         type int32;
       }
       leaf ike-tun-mon-table-gw-name {
         type int32;
       }
       leaf ike-tun-mon-table-tun-type {
         type int32;
       }
     }
     container ike-snmp-ipsec-tun-mon-table-statistics {
       leaf ipsec-tun-mon-table-get-requests {
         type int32;
       }
       leaf ipsec-tun-mon-table-next-requests {
         type int32;
       }
       leaf ipsec-tun-mon-table-get-request-timeout {
         type int32;
       }
       leaf ipsec-tun-mon-table-next-request-timeout {
         type int32;
       }
       leaf ipsec-tun-mon-table-cache-timer-expire {
         type int32;
       }
       leaf ipsec-tun-mon-table-cache-delete {
         type int32;
       }
       leaf ipsec-tun-mon-table-lookup-calls {
         type int32;
       }
       leaf ipsec-tun-mon-table-lookup-invalid-key {
         type int32;
       }
       leaf ipsec-tun-mon-table-lookup-key-alloc-err {
         type int32;
       }
       leaf ipsec-tun-mon-table-lookup-send-req-fail {
         type int32;
       }
       leaf ipsec-tun-mon-table-next-lookup-calls {
         type int32;
       }
       leaf ipsec-tun-mon-table-next-lookup-invalid-key {
         type int32;
       }
       leaf ipsec-tun-mon-table-next-lookup-key-alloc-err {
         type int32;
       }
       leaf ipsec-tun-mon-table-next-lookup-req-sent-now {
         type int32;
       }
       leaf ipsec-tun-mon-table-next-lookup-send-req-fail {
         type int32;
       }
       leaf ipsec-tun-mon-table-next-lookup-req-sent-before {
         type int32;
       }
       leaf ipsec-tun-mon-table-next-lookup-response-sent {
         type int32;
       }
       leaf ipsec-tun-mon-table-next-lookup-tunnel-not-found {
         type int32;
       }
       leaf ipsec-tun-mon-table-next-lookup-stats-valid-or-failed {
         type int32;
       }
       leaf ipsec-tun-mon-table-next-lookup-stats-send-req-fail {
         type int32;
       }
       leaf ipsec-tun-mon-table-next-lookup-stats-key-alloc-err {
         type int32;
       }
       leaf ipsec-tun-mon-table-next-lookup-stats-req-sent-now {
         type int32;
       }
       leaf ipsec-tun-mon-table-next-lookup-stats-req-sent-before {
         type int32;
       }
       leaf ipsec-tun-mon-table-get-key-calls {
         type int32;
       }
       leaf ipsec-tun-mon-table-get-key-null-data {
         type int32;
       }
       leaf ipsec-tun-mon-table-get-key-invalid-key {
         type int32;
       }
       leaf ipsec-tun-mon-table-get-responses {
         type int32;
       }
       leaf ipsec-tun-mon-table-get-response-null {
         type int32;
       }
       leaf ipsec-tun-mon-table-get-stats-send-req-fail {
         type int32;
       }
       leaf ipsec-tun-mon-table-get-stats-req-sent-now {
         type int32;
       }
       leaf ipsec-tun-mon-table-get-stats-req-sent-before {
         type int32;
       }
       leaf ipsec-tun-mon-table-next-responses {
         type int32;
       }
       leaf ipsec-tun-mon-table-next-responses-null {
         type int32;
       }
       leaf ipsec-tun-mon-table-next-req-sent {
         type int32;
       }
       leaf ipsec-tun-mon-table-next-send-req-fail {
         type int32;
       }
       leaf ipsec-tun-mon-table-next-null-response-sent {
         type int32;
       }
       leaf ipsec-tun-mon-table-next-response-complete {
         type int32;
       }
       leaf ipsec-tun-mon-table-next-resp-ipsec-tun-node-mem-alloc-fail {
         type int32;
       }
       leaf ipsec-tun-mon-table-next-resp-ike-sa-add-fail {
         type int32;
       }
       leaf ipsec-tun-mon-table-next-resp-ike-sa-add-success {
         type int32;
       }
       leaf ipsec-tun-mon-table-next-tunnel-not-found {
         type int32;
       }
       leaf ipsec-tun-mon-table-next-stats-valid-or-failed {
         type int32;
       }
       leaf ipsec-tun-mon-table-next-stats-req-sent-now {
         type int32;
       }
       leaf ipsec-tun-mon-table-next-stats-send-req-fail {
         type int32;
       }
       leaf ipsec-tun-mon-table-next-stats-req-sent-before {
         type int32;
       }
       leaf ipsec-tun-mon-table-pfe-start-timer {
         type int32;
       }
       leaf ipsec-tun-mon-table-clear-pfe-stats-timer {
         type int32;
       }
       leaf ipsec-tun-mon-table-iked-req-timeout {
         type int32;
       }
       leaf ipsec-tun-mon-table-stats-cb-calls {
         type int32;
       }
       leaf ipsec-tun-mon-table-stats-cb-next-req-sent-now {
         type int32;
       }
       leaf ipsec-tun-mon-table-stats-cb-next-send-req-fail {
         type int32;
       }
       leaf ipsec-tun-mon-table-stats-cb-next-req-sent-before {
         type int32;
       }
       leaf ipsec-tun-mon-table-stats-cb-next-tunnel-not-found {
         type int32;
       }
       leaf ipsec-tun-mon-table-stats-cb-next-stats-updated {
         type int32;
       }
       leaf ipsec-tun-mon-table-stats-cb-next-response-sent {
         type int32;
       }
       leaf ipsec-tun-mon-table-stats-cb-get-response-sent {
         type int32;
       }
       leaf ipsec-tun-mon-table-stats-timeout-cb-calls {
         type int32;
       }
       leaf ipsec-tun-mon-table-stats-timeout-cb-req-sent-now {
         type int32;
       }
       leaf ipsec-tun-mon-table-stats-timeout-cb-send-req-fail {
         type int32;
       }
       leaf ipsec-tun-mon-table-stats-timeout-cb-req-sent-before {
         type int32;
       }
       leaf ipsec-tun-mon-table-stats-timeout-cb-next-response-sent {
         type int32;
       }
       leaf ipsec-tun-mon-table-stats-timeout-cb-get-response-sent {
         type int32;
       }
       leaf ipsec-tun-mon-table-stats-timeout-cb-tunnel-not-found {
         type int32;
       }
       leaf ipsec-tun-mon-table-stats-timeout-cb-response-sent {
         type int32;
       }
       leaf ipsec-tun-mon-table-get-value-calls {
         type int32;
       }
       leaf ipsec-tun-mon-table-get-value-errs {
         type int32;
       }
       leaf ipsec-tun-mon-table-local-gw-addr-type {
         type int32;
       }
       leaf ipsec-tun-mon-table-local-gw-addr {
         type int32;
       }
       leaf ipsec-tun-mon-table-local-proxy-id {
         type int32;
       }
       leaf ipsec-tun-mon-table-remote-proxy-id {
         type int32;
       }
       leaf ipsec-tun-mon-table-type {
         type int32;
       }
       leaf ipsec-tun-mon-table-remote-peer-type {
         type int32;
       }
       leaf ipsec-tun-mon-table-out-encrypted-bytes {
         type int32;
       }
       leaf ipsec-tun-mon-table-out-encrypted-pkts {
         type int32;
       }
       leaf ipsec-tun-mon-table-in-decrypted-bytes {
         type int32;
       }
       leaf ipsec-tun-mon-table-in-decrypted-pkts {
         type int32;
       }
       leaf ipsec-tun-mon-table-ah-in-bytes {
         type int32;
       }
       leaf ipsec-tun-mon-table-ah-in-pkts {
         type int32;
       }
       leaf ipsec-tun-mon-table-ah-out-bytes {
         type int32;
       }
       leaf ipsec-tun-mon-table-ah-out-pkts {
         type int32;
       }
       leaf ipsec-tun-mon-table-replay-drop-pkts {
         type int32;
       }
       leaf ipsec-tun-mon-table-ah-auth-fails {
         type int32;
       }
       leaf ipsec-tun-mon-table-esp-auth-fails {
         type int32;
       }
       leaf ipsec-tun-mon-table-decrypt-fails {
         type int32;
       }
       leaf ipsec-tun-mon-table-bad-headers {
         type int32;
       }
       leaf ipsec-tun-mon-table-bad-trailers {
         type int32;
       }
       leaf ipsec-tun-mon-table-vpn-name {
         type int32;
       }
       leaf ipsec-tun-mon-table-ts-name {
         type int32;
       }
       leaf ipsec-tun-mon-table-multi-sa {
         type int32;
       }
       leaf ipsec-tun-mon-table-invalid-spi {
         type int32;
       }
       leaf ipsec-tun-mon-table-ts-check-fail {
         type int32;
       }
       leaf ipsec-tun-mon-table-exceeds-tunnel-mtu {
         type int32;
       }
       leaf ipsec-tun-mon-table-discarded {
         type int32;
       }
       leaf ipsec-tun-mon-table-tun-type {
         type int32;
       }
       leaf ipsec-tun-mon-table-ts-type {
         type int32;
       }
       leaf ipsec-tun-mon-table-local-ts {
         type int32;
       }
       leaf ipsec-tun-mon-table-remote-ts {
         type int32;
       }
       leaf ipsec-tun-mon-table-tunnel-mtu {
         type int32;
       }
       leaf ipsec-tun-mon-table-get-cc-ha-stat-success {
         type int32;
       }
       leaf ipsec-tun-mon-table-get-cc-ha-stat-fail {
         type int32;
       }
       leaf ipsec-tun-mon-table-next-cc-ha-stat-success {
         type int32;
       }
       leaf ipsec-tun-mon-table-next-cc-ha-stat-fail {
         type int32;
       }
       leaf ipsec-tun-mon-table-next-lookup-cc-ha-stat-success {
         type int32;
       }
       leaf ipsec-tun-mon-table-next-lookup-cc-ha-stat-fail {
         type int32;
       }
       leaf ipsec-tun-mon-table-lookup-global-cc-ha-stat-success {
         type int32;
       }
       leaf ipsec-tun-mon-table-lookup-global-cc-ha-stat-fail {
         type int32;
       }
       leaf ipsec-tun-mon-table-next-lookup-global-cc-ha-stat-success {
         type int32;
       }
       leaf ipsec-tun-mon-table-next-lookup-global-cc-ha-stat-fail {
         type int32;
       }
     }
     container ike-snmp-ipsec-sa-mon-table-statistics {
       leaf ipsec-sa-mon-table-get-requests {
         type int32;
       }
       leaf ipsec-sa-mon-table-next-requests {
         type int32;
       }
       leaf ipsec-sa-mon-table-get-request-timeout {
         type int32;
       }
       leaf ipsec-sa-mon-table-next-request-timeout {
         type int32;
       }
       leaf ipsec-sa-mon-table-cache-timer-expire {
         type int32;
       }
       leaf ipsec-sa-mon-table-cache-delete {
         type int32;
       }
       leaf ipsec-sa-mon-table-lookup-calls {
         type int32;
       }
       leaf ipsec-sa-mon-table-lookup-invalid-key {
         type int32;
       }
       leaf ipsec-sa-mon-table-lookup-key-alloc-err {
         type int32;
       }
       leaf ipsec-sa-mon-table-lookup-send-req-fail {
         type int32;
       }
       leaf ipsec-sa-mon-table-next-lookup-calls {
         type int32;
       }
       leaf ipsec-sa-mon-table-next-lookup-invalid-key {
         type int32;
       }
       leaf ipsec-sa-mon-table-next-lookup-key-alloc-err {
         type int32;
       }
       leaf ipsec-sa-mon-table-next-lookup-req-sent-now {
         type int32;
       }
       leaf ipsec-sa-mon-table-next-lookup-send-req-fail {
         type int32;
       }
       leaf ipsec-sa-mon-table-next-lookup-req-sent-before {
         type int32;
       }
       leaf ipsec-sa-mon-table-next-lookup-response-sent {
         type int32;
       }
       leaf ipsec-sa-mon-table-next-lookup-tunnel-not-found {
         type int32;
       }
       leaf ipsec-sa-mon-table-next-lookup-stats-valid-or-failed {
         type int32;
       }
       leaf ipsec-sa-mon-table-next-lookup-stats-send-req-fail {
         type int32;
       }
       leaf ipsec-sa-mon-table-next-lookup-stats-key-alloc-err {
         type int32;
       }
       leaf ipsec-sa-mon-table-next-lookup-stats-req-sent-now {
         type int32;
       }
       leaf ipsec-sa-mon-table-next-lookup-stats-req-sent-before {
         type int32;
       }
       leaf ipsec-sa-mon-table-get-key-calls {
         type int32;
       }
       leaf ipsec-sa-mon-table-get-key-null-data {
         type int32;
       }
       leaf ipsec-sa-mon-table-get-key-invalid-key {
         type int32;
       }
       leaf ipsec-sa-mon-table-get-responses {
         type int32;
       }
       leaf ipsec-sa-mon-table-get-response-complete {
         type int32;
       }
       leaf ipsec-sa-mon-table-get-response-null {
         type int32;
       }
       leaf ipsec-sa-mon-table-get-stats-send-req-fail {
         type int32;
       }
       leaf ipsec-sa-mon-table-get-stats-req-sent-now {
         type int32;
       }
       leaf ipsec-sa-mon-table-get-response-sent {
         type int32;
       }
       leaf ipsec-sa-mon-table-next-responses {
         type int32;
       }
       leaf ipsec-sa-mon-table-next-responses-null {
         type int32;
       }
       leaf ipsec-sa-mon-table-next-req-sent {
         type int32;
       }
       leaf ipsec-sa-mon-table-next-send-req-fail {
         type int32;
       }
       leaf ipsec-sa-mon-table-next-null-response-sent {
         type int32;
       }
       leaf ipsec-sa-mon-table-next-response-complete {
         type int32;
       }
       leaf ipsec-sa-mon-table-next-tunnel-not-found {
         type int32;
       }
       leaf ipsec-sa-mon-table-next-stats-valid-or-failed {
         type int32;
       }
       leaf ipsec-sa-mon-table-next-stats-req-sent-now {
         type int32;
       }
       leaf ipsec-sa-mon-table-next-stats-send-req-fail {
         type int32;
       }
       leaf ipsec-sa-mon-table-next-stats-req-sent-before {
         type int32;
       }
       leaf ipsec-sa-mon-table-next-response-sent {
         type int32;
       }
       leaf ipsec-sa-mon-table-stats-cb-calls {
         type int32;
       }
       leaf ipsec-sa-mon-table-stats-cb-next-req-sent-now {
         type int32;
       }
       leaf ipsec-sa-mon-table-stats-cb-next-send-req-fail {
         type int32;
       }
       leaf ipsec-sa-mon-table-stats-cb-next-req-sent-before {
         type int32;
       }
       leaf ipsec-sa-mon-table-stats-cb-next-tunnel-not-found {
         type int32;
       }
       leaf ipsec-sa-mon-table-stats-cb-next-stats-updated {
         type int32;
       }
       leaf ipsec-sa-mon-table-stats-cb-next-response-sent {
         type int32;
       }
       leaf ipsec-sa-mon-table-stats-cb-get-response-sent {
         type int32;
       }
       leaf ipsec-sa-mon-table-stats-timeout-cb-calls {
         type int32;
       }
       leaf ipsec-sa-mon-table-stats-timeout-cb-req-sent-now {
         type int32;
       }
       leaf ipsec-sa-mon-table-stats-timeout-cb-send-req-fail {
         type int32;
       }
       leaf ipsec-sa-mon-table-stats-timeout-cb-req-sent-before {
         type int32;
       }
       leaf ipsec-sa-mon-table-stats-timeout-cb-next-response-sent {
         type int32;
       }
       leaf ipsec-sa-mon-table-stats-timeout-cb-get-response-sent {
         type int32;
       }
       leaf ipsec-sa-mon-table-stats-timeout-cb-tunnel-not-found {
         type int32;
       }
       leaf ipsec-sa-mon-table-stats-timeout-cb-response-sent {
         type int32;
       }
       leaf ipsec-sa-mon-table-get-value-calls {
         type int32;
       }
       leaf ipsec-sa-mon-table-get-value-null-data {
         type int32;
       }
       leaf ipsec-sa-mon-table-get-value-errs {
         type int32;
       }
       leaf ipsec-sa-mon-table-protocol {
         type int32;
       }
       leaf ipsec-sa-mon-table-in-spi {
         type int32;
       }
       leaf ipsec-sa-mon-table-out-spi {
         type int32;
       }
       leaf ipsec-sa-mon-table-type {
         type int32;
       }
       leaf ipsec-sa-mon-table-encap-mode {
         type int32;
       }
       leaf ipsec-sa-mon-table-life-size {
         type int32;
       }
       leaf ipsec-sa-mon-table-life-time {
         type int32;
       }
       leaf ipsec-sa-mon-table-active-time {
         type int32;
       }
       leaf ipsec-sa-mon-table-life-time-threshold {
         type int32;
       }
       leaf ipsec-sa-mon-table-encrypt-algo {
         type int32;
       }
       leaf ipsec-sa-mon-table-auth-algo {
         type int32;
       }
       leaf ipsec-sa-mon-table-state {
         type int32;
       }
       leaf ipsec-sa-mon-table-fc-name {
         type int32;
       }
       leaf ipsec-sa-mon-table-esn-mode {
         type int32;
       }
     }
     container ike-snmp-ike-stats-scalar-obj-statistics {
       leaf ike-stats-scalar-obj-get-requests {
         type int32;
       }
       leaf ike-stats-scalar-obj-next-requests {
         type int32;
       }
       leaf ike-stats-scalar-obj-get-request-timeout {
         type int32;
       }
       leaf ike-stats-scalar-obj-next-request-timeout {
         type int32;
       }
       leaf ike-stats-scalar-obj-get-req-initiator-ikev2-sa-init {
         type int32;
       }
       leaf ike-stats-scalar-obj-next-req-initiator-ikev2-sa-init {
         type int32;
       }
       leaf ike-stats-scalar-obj-lookup-calls {
         type int32;
       }
       leaf ike-stats-scalar-obj-lookup-invalid-key {
         type int32;
       }
       leaf ike-stats-scalar-obj-lookup-key-alloc-err {
         type int32;
       }
       leaf ike-stats-scalar-obj-lookup-send-req-fail {
         type int32;
       }
       leaf ike-stats-scalar-obj-next-lookup-calls {
         type int32;
       }
       leaf ike-stats-scalar-obj-next-lookup-invalid-key {
         type int32;
       }
       leaf ike-stats-scalar-obj-next-lookup-key-alloc-err {
         type int32;
       }
       leaf ike-stats-scalar-obj-next-lookup-send-req-fail {
         type int32;
       }
       leaf ike-stats-scalar-obj-next-lookup-response-sent {
         type int32;
       }
       leaf ike-stats-scalar-obj-global-ike-stats-response-sent {
         type int32;
       }
       leaf ike-stats-scalar-obj-get-key-calls {
         type int32;
       }
       leaf ike-stats-scalar-obj-get-key-null-data {
         type int32;
       }
       leaf ike-stats-scalar-obj-get-value-calls {
         type int32;
       }
       leaf ike-stats-scalar-obj-ike-tunnels {
         type int32;
       }
       leaf ike-stats-scalar-obj-get-value-errs {
         type int32;
       }
       leaf ike-stats-scalar-obj-get-value-initiator-ikev2-sa-init {
         type int32;
       }
       leaf ike-stats-scalar-obj-get-value-initiator-ikev2-sa-null-data {
         type int32;
       }
       leaf ike-stats-scalar-obj-initiator-ike-sa-req-out {
         type int32;
       }
       leaf ike-stats-scalar-obj-initiator-ike-sa-res-in {
         type int32;
       }
       leaf ike-stats-scalar-obj-initiator-ike-sa-invalid-spi {
         type int32;
       }
       leaf ike-stats-scalar-obj-initiator-ike-sa-invalid-payload-in {
         type int32;
       }
       leaf ike-stats-scalar-obj-initiator-ike-sa-no-proposal-chosen-in {
         type int32;
       }
       leaf ike-stats-scalar-obj-initiator-ike-sa-verify-fail {
         type int32;
       }
       leaf ike-stats-scalar-obj-initiator-ike-sa-fill-fail {
         type int32;
       }
       leaf ike-stats-scalar-obj-initiator-ike-sa-dh-group-fail {
         type int32;
       }
       leaf ike-stats-scalar-obj-initiator-ike-sa-cookie-req-in {
         type int32;
       }
       leaf ike-stats-scalar-obj-initiator-ike-sa-dh-key-fail {
         type int32;
       }
       leaf ike-stats-scalar-obj-initiator-ike-sa-cookie-res-out {
         type int32;
       }
       leaf ike-stats-scalar-obj-get-value-initiator-ikev2-sa-init-errs {
         type int32;
       }
       leaf ike-stats-scalar-obj-get-req-responder-ikev2-sa-init {
         type int32;
       }
       leaf ike-stats-scalar-obj-next-req-responder-ikev2-sa-init {
         type int32;
       }
       leaf ike-stats-scalar-obj-get-value-responder-ikev2-sa-init {
         type int32;
       }
       leaf ike-stats-scalar-obj-get-value-responder-ikev2-sa-init-null-data {
         type int32;
       }
       leaf ike-stats-scalar-obj-responder-ike-sa-req-in {
         type int32;
       }
       leaf ike-stats-scalar-obj-responder-ike-sa-res-out {
         type int32;
       }
       leaf ike-stats-scalar-obj-responder-ike-sa-no-proposal-chosen-out {
         type int32;
       }
       leaf ike-stats-scalar-obj-responder-ike-sa-invalid-ke-payload-out {
         type int32;
       }
       leaf ike-stats-scalar-obj-responder-ike-sa-invalid-dh-group {
         type int32;
       }
       leaf ike-stats-scalar-obj-responder-ike-sa-gen-dh-key-fail {
         type int32;
       }
       leaf ike-stats-scalar-obj-responder-ike-sa-get-cas-fail {
         type int32;
       }
       leaf ike-stats-scalar-obj-responder-ike-sa-get-vid-fail {
         type int32;
       }
       leaf ike-stats-scalar-obj-responder-ike-sa-dh-compute-key-fail {
         type int32;
       }
       leaf ike-stats-scalar-obj-responder-ike-sa-cookie-req-out {
         type int32;
       }
       leaf ike-stats-scalar-obj-responder-ike-sa-cookie-res-in {
         type int32;
       }
       leaf ike-stats-scalar-obj-get-value-responder-ikev2-sa-init-errs {
         type int32;
       }
       leaf ike-stats-scalar-obj-get-req-initiator-ikev2-auth {
         type int32;
       }
       leaf ike-stats-scalar-obj-next-req-initiator-ikev2-auth {
         type int32;
       }
       leaf ike-stats-scalar-obj-get-value-initiator-ikev2-auth {
         type int32;
       }
       leaf ike-stats-scalar-obj-get-value-initiator-ikev2-auth-null-data {
         type int32;
       }
       leaf ike-stats-scalar-obj-initiator-ike-auth-req-out {
         type int32;
       }
       leaf ike-stats-scalar-obj-initiator-ike-auth-res-in {
         type int32;
       }
       leaf ike-stats-scalar-obj-initiator-ike-auth-no-proposal-chosen-in {
         type int32;
       }
       leaf ike-stats-scalar-obj-initiator-ike-auth-ts-unacceptable-in {
         type int32;
       }
       leaf ike-stats-scalar-obj-initiator-ike-auth-authentication-fail-in {
         type int32;
       }
       leaf ike-stats-scalar-obj-get-value-initiator-ikev2-auth-errs {
         type int32;
       }
       leaf ike-stats-scalar-obj-get-req-responder-ikev2-auth {
         type int32;
       }
       leaf ike-stats-scalar-obj-next-req-responder-ikev2-auth {
         type int32;
       }
       leaf ike-stats-scalar-obj-get-value-responder-ikev2-auth {
         type int32;
       }
       leaf ike-stats-scalar-obj-get-value-responder-ikev2-auth-null-data {
         type int32;
       }
       leaf ike-stats-scalar-obj-responder-ike-auth-req-in {
         type int32;
       }
       leaf ike-stats-scalar-obj-responder-ike-auth-res-out {
         type int32;
       }
       leaf ike-stats-scalar-obj-responder-ike-auth-no-proposal-chosen-out {
         type int32;
       }
       leaf ike-stats-scalar-obj-responder-ike-auth-ts-unacceptable-out {
         type int32;
       }
       leaf ike-stats-scalar-obj-responder-ike-auth-authentication-fail {
         type int32;
       }
       leaf ike-stats-scalar-obj-get-value-responder-ikev2-auth-errs {
         type int32;
       }
       leaf ike-stats-scalar-obj-get-req-initiator-ikev2-ike-sa-rekey {
         type int32;
       }
       leaf ike-stats-scalar-obj-next-req-initiator-ikev2-ike-sa-rekey {
         type int32;
       }
       leaf ike-stats-scalar-obj-get-value-initiator-ikev2-ike-sa-rekey {
         type int32;
       }
       leaf ike-stats-scalar-obj-get-value-initiator-ikev2-ike-sa-rekey-null-data {
         type int32;
       }
       leaf ike-stats-scalar-obj-initiator-ike-sa-rekey-req-out {
         type int32;
       }
       leaf ike-stats-scalar-obj-initiator-ike-sa-rekey-res-in {
         type int32;
       }
       leaf ike-stats-scalar-obj-initiator-ike-sa-rekey-no-proposal-chosen-in {
         type int32;
       }
       leaf ike-stats-scalar-obj-initiator-ike-sa-rekey-invalid-key-in {
         type int32;
       }
       leaf ike-stats-scalar-obj-initiator-ike-sa-rekey-dh-compute-key-fail {
         type int32;
       }
       leaf ike-stats-scalar-obj-initiator-ike-sa-rekey-verify-fail {
         type int32;
       }
       leaf ike-stats-scalar-obj-initiator-ike-sa-rekey-fill-fail {
         type int32;
       }
       leaf ike-stats-scalar-obj-initiator-ike-sa-rekey-dh-group-fail {
         type int32;
       }
       leaf ike-stats-scalar-obj-get-value-initiator-ikev2-ike-sa-rekey-errs {
         type int32;
       }
       leaf ike-stats-scalar-obj-get-req-responder-ikev2-ike-sa-rekey {
         type int32;
       }
       leaf ike-stats-scalar-obj-next-req-responder-ikev2-ike-sa-rekey {
         type int32;
       }
       leaf ike-stats-scalar-obj-get-value-responder-ikev2-ike-sa-rekey {
         type int32;
       }
       leaf ike-stats-scalar-obj-get-value-responder-ikev2-ike-sa-rekey-null-data {
         type int32;
       }
       leaf ike-stats-scalar-obj-responder-ike-sa-rekey-req-in {
         type int32;
       }
       leaf ike-stats-scalar-obj-responder-ike-sa-rekey-res-out {
         type int32;
       }
       leaf ike-stats-scalar-obj-responder-ike-sa-rekey-no-proposal-chosen-out {
         type int32;
       }
       leaf ike-stats-scalar-obj-responder-ike-sa-rekey-invalid-key-out {
         type int32;
       }
       leaf ike-stats-scalar-obj-responder-ike-sa-rekey-dh-compute-key-fail {
         type int32;
       }
       leaf ike-stats-scalar-obj-get-value-responder-ikev2-ike-sa-rekey-errs {
         type int32;
       }
       leaf ike-stats-scalar-obj-get-req-initiator-ikev2-ipsec-sa-rekey {
         type int32;
       }
       leaf ike-stats-scalar-obj-next-req-initiator-ikev2-ipsec-sa-rekey {
         type int32;
       }
       leaf ike-stats-scalar-obj-get-value-initiator-ikev2-ipsec-sa-rekey {
         type int32;
       }
       leaf ike-stats-scalar-obj-get-value-initiator-ikev2-ipsec-sa-rekey-null-data {
         type int32;
       }
       leaf ike-stats-scalar-obj-initiator-ipsec-sa-rekey-req-out {
         type int32;
       }
       leaf ike-stats-scalar-obj-initiator-ipsec-sa-rekey-res-in {
         type int32;
       }
       leaf ike-stats-scalar-obj-initiator-ipsec-sa-rekey-no-proposal-chosen-in {
         type int32;
       }
       leaf ike-stats-scalar-obj-initiator-ipsec-sa-rekey-invalid-key-in {
         type int32;
       }
       leaf ike-stats-scalar-obj-initiator-ipsec-sa-ts-unacceptable-in {
         type int32;
       }
       leaf ike-stats-scalar-obj-initiator-ipsec-sa-verify-fail {
         type int32;
       }
       leaf ike-stats-scalar-obj-initiator-ipsec-sa-rekey-dh-compute-key-fail {
         type int32;
       }
       leaf ike-stats-scalar-obj-initiator-ipsec-sa-rekey-dh-group-fail {
         type int32;
       }
       leaf ike-stats-scalar-obj-initiator-ipsec-sa-rekey-verify-ts-fail {
         type int32;
       }
       leaf ike-stats-scalar-obj-get-value-initiator-ikev2-ipsec-sa-rekey-errs {
         type int32;
       }
       leaf ike-stats-scalar-obj-get-req-responder-ikev2-ipsec-sa-rekey {
         type int32;
       }
       leaf ike-stats-scalar-obj-next-req-responder-ikev2-ipsec-sa-rekey {
         type int32;
       }
       leaf ike-stats-scalar-obj-get-value-responder-ikev2-ipsec-sa-rekey {
         type int32;
       }
       leaf ike-stats-scalar-obj-get-value-responder-ikev2-ipsec-sa-rekey-null-data {
         type int32;
       }
       leaf ike-stats-scalar-obj-responder-ipsec-sa-rekey-req-in {
         type int32;
       }
       leaf ike-stats-scalar-obj-responder-ipsec-sa-rekey-res-out {
         type int32;
       }
       leaf ike-stats-scalar-obj-responder-ipsec-sa-rekey-no-proposal-chosen-out {
         type int32;
       }
       leaf ike-stats-scalar-obj-responder-ipsec-sa-invalid-key-out {
         type int32;
       }
       leaf ike-stats-scalar-obj-responder-ipsec-sa-ts-unaceptable-out {
         type int32;
       }
       leaf ike-stats-scalar-obj-responder-ipsec-sa-dh-compute-key-fail {
         type int32;
       }
       leaf ike-stats-scalar-obj-get-value-responder-ikev2-ipsec-sa-rekey-errs {
         type int32;
       }
       leaf ike-stats-scalar-obj-get-req-ikev2-msg-fail {
         type int32;
       }
       leaf ike-stats-scalar-obj-next-req-ikev2-msg-fail {
         type int32;
       }
       leaf ike-stats-scalar-obj-get-value-ikev2-msg-fail {
         type int32;
       }
       leaf ike-stats-scalar-obj-get-value-ikev2-msg-fail-null-data {
         type int32;
       }
       leaf ike-stats-scalar-obj-msg-fail-discarded {
         type int32;
       }
       leaf ike-stats-scalar-obj-msg-fail-id-error {
         type int32;
       }
       leaf ike-stats-scalar-obj-msg-fail-integrity {
         type int32;
       }
       leaf ike-stats-scalar-obj-msg-fail-invalid-spi {
         type int32;
       }
       leaf ike-stats-scalar-obj-msg-fail-invalid-exchg-type {
         type int32;
       }
       leaf ike-stats-scalar-obj-msg-fail-invalid-length {
         type int32;
       }
       leaf ike-stats-scalar-obj-msg-fail-disorder {
         type int32;
       }
       leaf ike-stats-scalar-obj-get-value-ikev2-msg-fail-errs {
         type int32;
       }
       leaf ike-stats-scalar-obj-get-req-ipsec-tunnels {
         type int32;
       }
       leaf ike-stats-scalar-obj-next-req-ipsec-tunnels {
         type int32;
       }
       leaf ike-stats-scalar-obj-get-value-ipsec-tunnels {
         type int32;
       }
       leaf ike-stats-scalar-obj-get-value-ipsec-tunnels-null-data {
         type int32;
       }
       leaf ike-stats-scalar-obj-ipsec-tunnels {
         type int32;
       }
       leaf ike-stats-scalar-obj-get-value-ipsec-tunnels-errs {
         type int32;
       }
     }
     container ike-snmp-ha-link-ike-stats-scalar-obj-statistics {
       leaf ha-link-ike-stats-scalar-obj-get-req-initiator-ikev2-sa-init {
         type int32;
       }
       leaf ha-link-ike-stats-scalar-obj-next-req-initiator-ikev2-sa-init {
         type int32;
       }
       leaf ha-link-ike-stats-scalar-obj-next-lookup-calls {
         type int32;
       }
       leaf ha-link-ike-stats-scalar-obj-next-lookup-invalid-key {
         type int32;
       }
       leaf ha-link-ike-stats-scalar-obj-next-lookup-key-alloc-err {
         type int32;
       }
       leaf ha-link-ike-stats-scalar-obj-next-lookup-send-req-fail {
         type int32;
       }
       leaf ha-link-ike-stats-scalar-obj-next-lookup-response-sent {
         type int32;
       }
       leaf ha-link-ike-stats-scalar-obj-get-request-timeout {
         type int32;
       }
       leaf ha-link-ike-stats-scalar-obj-next-request-timeout {
         type int32;
       }
       leaf ha-link-ike-stats-scalar-obj-global-ike-stats-response-sent {
         type int32;
       }
       leaf ha-link-ike-stats-scalar-obj-get-value-initiator-ikev2-sa-init {
         type int32;
       }
       leaf ha-link-ike-stats-scalar-obj-get-value-initiator-ikev2-sa-null-data {
         type int32;
       }
       leaf ha-link-ike-stats-scalar-obj-initiator-ike-sa-req-out {
         type int32;
       }
       leaf ha-link-ike-stats-scalar-obj-initiator-ike-sa-res-in {
         type int32;
       }
       leaf ha-link-ike-stats-scalar-obj-initiator-ike-sa-invalid-spi {
         type int32;
       }
       leaf ha-link-ike-stats-scalar-obj-initiator-ike-sa-invalid-payload-in {
         type int32;
       }
       leaf ha-link-ike-stats-scalar-obj-initiator-ike-sa-no-proposal-chosen-in {
         type int32;
       }
       leaf ha-link-ike-stats-scalar-obj-initiator-ike-sa-verify-fail {
         type int32;
       }
       leaf ha-link-ike-stats-scalar-obj-initiator-ike-sa-fill-fail {
         type int32;
       }
       leaf ha-link-ike-stats-scalar-obj-initiator-ike-sa-dh-group-fail {
         type int32;
       }
       leaf ha-link-ike-stats-scalar-obj-initiator-ike-sa-cookie-req-in {
         type int32;
       }
       leaf ha-link-ike-stats-scalar-obj-initiator-ike-sa-cookie-res-out {
         type int32;
       }
       leaf ha-link-ike-stats-scalar-obj-get-value-initiator-ikev2-sa-init-errs {
         type int32;
       }
       leaf ha-link-ike-stats-scalar-obj-get-req-responder-ikev2-sa-init {
         type int32;
       }
       leaf ha-link-ike-stats-scalar-obj-next-req-responder-ikev2-sa-init {
         type int32;
       }
       leaf ha-link-ike-stats-scalar-obj-get-value-responder-ikev2-sa-init {
         type int32;
       }
       leaf ha-link-ike-stats-scalar-obj-get-value-responder-ikev2-sa-null-data {
         type int32;
       }
       leaf ha-link-ike-stats-scalar-obj-responder-ike-sa-req-in {
         type int32;
       }
       leaf ha-link-ike-stats-scalar-obj-responder-ike-sa-res-out {
         type int32;
       }
       leaf ha-link-ike-stats-scalar-obj-responder-ike-sa-no-proposal-chosen-out {
         type int32;
       }
       leaf ha-link-ike-stats-scalar-obj-responder-ike-sa-invalid-key-payload-out {
         type int32;
       }
       leaf ha-link-ike-stats-scalar-obj-responder-ike-sa-invalid-dh-group {
         type int32;
       }
       leaf ha-link-ike-stats-scalar-obj-responder-ike-sa-dh-gen-key-fail {
         type int32;
       }
       leaf ha-link-ike-stats-scalar-obj-responder-ike-sa-get-cas-fail {
         type int32;
       }
       leaf ha-link-ike-stats-scalar-obj-responder-ike-sa-get-vid-fail {
         type int32;
       }
       leaf ha-link-ike-stats-scalar-obj-responder-ike-sa-dh-compute-key-fail {
         type int32;
       }
       leaf ha-link-ike-stats-scalar-obj-responder-ike-sa-cookie-req-out {
         type int32;
       }
       leaf ha-link-ike-stats-scalar-obj-responder-ike-sa-cookie-res-in {
         type int32;
       }
       leaf ha-link-ike-stats-scalar-obj-get-value-responder-ikev2-sa-init-errs {
         type int32;
       }
       leaf ha-link-ike-stats-scalar-obj-get-req-initiator-ikev2-auth {
         type int32;
       }
       leaf ha-link-ike-stats-scalar-obj-next-req-initiator-ikev2-auth {
         type int32;
       }
       leaf ha-link-ike-stats-scalar-obj-get-value-initiator-ikev2-auth {
         type int32;
       }
       leaf ha-link-ike-stats-scalar-obj-get-value-initiator-ikev2-auth-null-data {
         type int32;
       }
       leaf ha-link-ike-stats-scalar-obj-initiator-ike-auth-req-out {
         type int32;
       }
       leaf ha-link-ike-stats-scalar-obj-initiator-ike-auth-res-in {
         type int32;
       }
       leaf ha-link-ike-stats-scalar-obj-initiator-ike-auth-no-proposal-chosen-in {
         type int32;
       }
       leaf ha-link-ike-stats-scalar-obj-initiator-ike-auth-ts-unacceptable-in {
         type int32;
       }
       leaf ha-link-ike-stats-scalar-obj-initiator-ike-auth-authentication-fail {
         type int32;
       }
       leaf ha-link-ike-stats-scalar-obj-get-value-initiator-ikev2-auth-errs {
         type int32;
       }
       leaf ha-link-ike-stats-scalar-obj-get-req-responder-ikev2-auth {
         type int32;
       }
       leaf ha-link-ike-stats-scalar-obj-next-req-responder-ikev2-auth {
         type int32;
       }
       leaf ha-link-ike-stats-scalar-obj-get-value-responder-ikev2-auth {
         type int32;
       }
       leaf ha-link-ike-stats-scalar-obj-get-value-responder-ikev2-auth-null-data {
         type int32;
       }
       leaf ha-link-ike-stats-scalar-obj-responder-ike-auth-req-in {
         type int32;
       }
       leaf ha-link-ike-stats-scalar-obj-responder-ike-auth-res-out {
         type int32;
       }
       leaf ha-link-ike-stats-scalar-obj-responder-ike-auth-no-proposal-chosen-out {
         type int32;
       }
       leaf ha-link-ike-stats-scalar-obj-responder-ike-auth-ts-unacceptable-out {
         type int32;
       }
       leaf ha-link-ike-stats-scalar-obj-responder-ike-auth-authentication-fail {
         type int32;
       }
       leaf ha-link-ike-stats-scalar-obj-get-value-responder-ikev2-auth-errs {
         type int32;
       }
       leaf ha-link-ike-stats-scalar-obj-lookup-calls {
         type int32;
       }
       leaf ha-link-ike-stats-scalar-obj-lookup-invalid-key {
         type int32;
       }
       leaf ha-link-ike-stats-scalar-obj-lookup-key-alloc-err {
         type int32;
       }
       leaf ha-link-ike-stats-scalar-obj-lookup-send-req-fail {
         type int32;
       }
       leaf ha-link-ike-stats-scalar-obj-get-req-initiator-ikev2-ike-sa-rekey {
         type int32;
       }
       leaf ha-link-ike-stats-scalar-obj-next-req-initiator-ikev2-ike-sa-rekey {
         type int32;
       }
       leaf ha-link-ike-stats-scalar-obj-get-value-initiator-ikev2-ike-sa-rekey {
         type int32;
       }
       leaf ha-link-ike-stats-scalar-obj-get-value-initiator-ikev2-ike-sa-rekey-null-data {
         type int32;
       }
       leaf ha-link-ike-stats-scalar-obj-initiator-ike-sa-rekey-req-out {
         type int32;
       }
       leaf ha-link-ike-stats-scalar-obj-initiator-ike-sa-rekey-res-in {
         type int32;
       }
       leaf ha-link-ike-stats-scalar-obj-initiator-ike-sa-rekey-no-proposal-chosen-in {
         type int32;
       }
       leaf ha-link-ike-stats-scalar-obj-initiator-ike-sa-rekey-invalid-key-in {
         type int32;
       }
       leaf ha-link-ike-stats-scalar-obj-initiator-ike-sa-rekey-dh-compute-key-fail {
         type int32;
       }
       leaf ha-link-ike-stats-scalar-obj-initiator-ike-sa-rekey-verify-fail {
         type int32;
       }
       leaf ha-link-ike-stats-scalar-obj-initiator-ike-sa-rekey-fill-fail {
         type int32;
       }
       leaf ha-link-ike-stats-scalar-obj-initiator-ike-sa-rekey-dh-group-fail {
         type int32;
       }
       leaf ha-link-ike-stats-scalar-obj-get-value-initiator-ikev2-ike-sa-rekey-errs {
         type int32;
       }
       leaf ha-link-ike-stats-scalar-obj-get-req-responder-ikev2-ike-sa-rekey {
         type int32;
       }
       leaf ha-link-ike-stats-scalar-obj-next-req-responder-ikev2-ike-sa-rekey {
         type int32;
       }
       leaf ha-link-ike-stats-scalar-obj-get-value-responder-ikev2-ike-sa-rekey {
         type int32;
       }
       leaf ha-link-ike-stats-scalar-obj-get-value-responder-ikev2-ike-sa-rekey-null-data {
         type int32;
       }
       leaf ha-link-ike-stats-scalar-obj-responder-ike-sa-rekey-req-in {
         type int32;
       }
       leaf ha-link-ike-stats-scalar-obj-responder-ike-sa-rekey-res-out {
         type int32;
       }
       leaf ha-link-ike-stats-scalar-obj-responder-ike-sa-rekey-no-proposal-chosen-out {
         type int32;
       }
       leaf ha-link-ike-stats-scalar-obj-responder-ike-sa-rekey-invalid-key-out {
         type int32;
       }
       leaf ha-link-ike-stats-scalar-obj-responder-ike-sa-rekey-dh-compute-key-fail {
         type int32;
       }
       leaf ha-link-ike-stats-scalar-obj-get-value-responder-ikev2-ike-sa-rekey-errs {
         type int32;
       }
       leaf ha-link-ike-stats-scalar-obj-get-req-initiator-ikev2-ipsec-sa-rekey {
         type int32;
       }
       leaf ha-link-ike-stats-scalar-obj-next-req-initiator-ikev2-ipsec-sa-rekey {
         type int32;
       }
       leaf ha-link-ike-stats-scalar-obj-get-value-initiator-ikev2-ipsec-sa-rekey {
         type int32;
       }
       leaf ha-link-ike-stats-scalar-obj-get-value-initiator-ikev2-ipsec-sa-rekey-null-data {
         type int32;
       }
       leaf ha-link-ike-stats-scalar-obj-initiator-ipsec-sa-rekey-req-out {
         type int32;
       }
       leaf ha-link-ike-stats-scalar-obj-initiator-ipsec-sa-rekey-res-in {
         type int32;
       }
       leaf ha-link-ike-stats-scalar-obj-initiator-ipsec-sa-rekey-no-proposal-chosen-in {
         type int32;
       }
       leaf ha-link-ike-stats-scalar-obj-initiator-ipsec-sa-rekey-invalid-key-in {
         type int32;
       }
       leaf ha-link-ike-stats-scalar-obj-initiator-ipsec-sa-ts-unacceptable-in {
         type int32;
       }
       leaf ha-link-ike-stats-scalar-obj-initiator-ipsec-sa-verify-fail {
         type int32;
       }
       leaf ha-link-ike-stats-scalar-obj-initiator-ipsec-sa-rekey-dh-compute-key-fail {
         type int32;
       }
       leaf ha-link-ike-stats-scalar-obj-initiator-ipsec-sa-rekey-dh-group-fail {
         type int32;
       }
       leaf ha-link-ike-stats-scalar-obj-initiator-ipsec-sa-rekey-verify-ts-fail {
         type int32;
       }
       leaf ha-link-ike-stats-scalar-obj-get-value-initiator-ikev2-ipsec-sa-rekey-errs {
         type int32;
       }
       leaf ha-link-ike-stats-scalar-obj-get-req-responder-ikev2-ipsec-sa-rekey {
         type int32;
       }
       leaf ha-link-ike-stats-scalar-obj-next-req-responder-ikev2-ipsec-sa-rekey {
         type int32;
       }
       leaf ha-link-ike-stats-scalar-obj-get-value-responder-ikev2-ipsec-sa-rekey {
         type int32;
       }
       leaf ha-link-ike-stats-scalar-obj-get-value-responder-ikev2-ipsec-sa-rekey-null-data {
         type int32;
       }
       leaf ha-link-ike-stats-scalar-obj-responder-ipsec-sa-rekey-req-in {
         type int32;
       }
       leaf ha-link-ike-stats-scalar-obj-responder-ipsec-sa-rekey-res-out {
         type int32;
       }
       leaf ha-link-ike-stats-scalar-obj-responder-ipsec-sa-rekey-no-proposal-chosen-out {
         type int32;
       }
       leaf ha-link-ike-stats-scalar-obj-responder-ipsec-sa-invalid-key-out {
         type int32;
       }
       leaf ha-link-ike-stats-scalar-obj-responder-ipsec-sa-ts-unaceptable-out {
         type int32;
       }
       leaf ha-link-ike-stats-scalar-obj-responder-ipsec-sa-dh-compute-key-fail {
         type int32;
       }
       leaf ha-link-ike-stats-scalar-obj-get-value-responder-ikev2-ipsec-sa-rekey-errs {
         type int32;
       }
       leaf ha-link-ike-stats-scalar-obj-get-req-ikev2-msg-fail {
         type int32;
       }
       leaf ha-link-ike-stats-scalar-obj-next-req-ikev2-msg-fail {
         type int32;
       }
       leaf ha-link-ike-stats-scalar-obj-get-value-ikev2-msg-fail {
         type int32;
       }
       leaf ha-link-ike-stats-scalar-obj-get-value-ikev2-msg-fail-null-data {
         type int32;
       }
       leaf ha-link-ike-stats-scalar-obj-msg-fail-discarded {
         type int32;
       }
       leaf ha-link-ike-stats-scalar-obj-msg-fail-id-error {
         type int32;
       }
       leaf ha-link-ike-stats-scalar-obj-msg-fail-integrity {
         type int32;
       }
       leaf ha-link-ike-stats-scalar-obj-msg-fail-invalid-spi {
         type int32;
       }
       leaf ha-link-ike-stats-scalar-obj-msg-fail-invalid-exchg-type {
         type int32;
       }
       leaf ha-link-ike-stats-scalar-obj-msg-fail-invalid-length {
         type int32;
       }
       leaf ha-link-ike-stats-scalar-obj-msg-fail-disorder {
         type int32;
       }
       leaf ha-link-ike-stats-scalar-obj-get-value-ikev2-msg-fail-errs {
         type int32;
       }
     }
     container ike-snmp-js-ipsec-tun-mon-table-statistics {
       leaf js-ipsec-tun-mon-table-get-requests {
         type int32;
       }
       leaf js-ipsec-tun-mon-table-next-requests {
         type int32;
       }
       leaf js-ipsec-tun-mon-table-get-request-timeout {
         type int32;
       }
       leaf js-ipsec-tun-mon-table-next-request-timeout {
         type int32;
       }
       leaf js-ipsec-tun-mon-table-lookup-calls {
         type int32;
       }
       leaf js-ipsec-tun-mon-table-lookup-invalid-key {
         type int32;
       }
       leaf js-ipsec-tun-mon-table-lookup-key-alloc-err {
         type int32;
       }
       leaf js-ipsec-tun-mon-table-lookup-send-req-fail {
         type int32;
       }
       leaf js-ipsec-tun-mon-table-get-value-calls {
         type int32;
       }
       leaf js-ipsec-tun-mon-table-tunnel-policy-name {
         type int32;
       }
       leaf js-ipsec-tun-mon-table-tunnel-type {
         type int32;
       }
       leaf js-ipsec-tun-mon-table-tunnel-cfg-mon-state {
         type int32;
       }
       leaf js-ipsec-tun-mon-table-tunnel-state {
         type int32;
       }
       leaf js-ipsec-tun-mon-table-get-value-errs {
         type int32;
       }
       leaf js-ipsec-tun-mon-table-next-lookup-calls {
         type int32;
       }
       leaf js-ipsec-tun-mon-table-next-lookup-invalid-key {
         type int32;
       }
       leaf js-ipsec-tun-mon-table-next-lookup-key-alloc-err {
         type int32;
       }
       leaf js-ipsec-tun-mon-table-next-lookup-send-req-fail {
         type int32;
       }
       leaf js-ipsec-tun-mon-table-next-lookup-req-sent-now {
         type int32;
       }
       leaf js-ipsec-tun-mon-table-next-lookup-req-sent-before {
         type int32;
       }
       leaf js-ipsec-tun-mon-table-next-lookup-response-sent {
         type int32;
       }
       leaf js-ipsec-tun-mon-table-get-key-calls {
         type int32;
       }
       leaf js-ipsec-tun-mon-table-get-snmp-key-null-data {
         type int32;
       }
       leaf js-ipsec-tun-mon-table-get-tun-key-null-data {
         type int32;
       }
       leaf js-ipsec-tun-mon-table-get-key-invalid-key {
         type int32;
       }
     }
     container ike-snmp-ipsec-stats-scalar-obj-statistics {
       leaf ipsec-stats-scalar-obj-get-requests {
         type int32;
       }
       leaf ipsec-stats-scalar-obj-next-requests {
         type int32;
       }
       leaf ipsec-stats-scalar-obj-lookup-calls {
         type int32;
       }
       leaf ipsec-stats-scalar-obj-lookup-invalid-key {
         type int32;
       }
       leaf ipsec-stats-scalar-obj-lookup-invalid-key-zero {
         type int32;
       }
       leaf ipsec-stats-scalar-obj-lookup-cache-valid {
         type int32;
       }
       leaf ipsec-stats-scalar-obj-lookup-key-alloc-err {
         type int32;
       }
       leaf ipsec-stats-scalar-obj-lookup-send-req-fail {
         type int32;
       }
       leaf ipsec-stats-scalar-obj-lookup-send-req-sent {
         type int32;
       }
       leaf ipsec-stats-scalar-obj-get-value-calls {
         type int32;
       }
       leaf ipsec-stats-scalar-obj-get-value-null-data {
         type int32;
       }
       leaf ipsec-stats-scalar-obj-out-encrpyt-bytes {
         type int32;
       }
       leaf ipsec-stats-scalar-obj-out-encrpyt-pkts {
         type int32;
       }
       leaf ipsec-stats-scalar-obj-in-decrypt-bytes {
         type int32;
       }
       leaf ipsec-stats-scalar-obj-in-decrypt-pkts {
         type int32;
       }
       leaf ipsec-stats-scalar-obj-ah-in-bytes {
         type int32;
       }
       leaf ipsec-stats-scalar-obj-ah-in-pkts {
         type int32;
       }
       leaf ipsec-stats-scalar-obj-ah-out-bytes {
         type int32;
       }
       leaf ipsec-stats-scalar-obj-ah-out-pkts {
         type int32;
       }
       leaf ipsec-stats-scalar-obj-replay-drop-pkts {
         type int32;
       }
       leaf ipsec-stats-scalar-obj-ah-auth-fails {
         type int32;
       }
       leaf ipsec-stats-scalar-obj-esp-auth-fails {
         type int32;
       }
       leaf ipsec-stats-scalar-obj-decrypt-fails {
         type int32;
       }
       leaf ipsec-stats-scalar-obj-bad-headers {
         type int32;
       }
       leaf ipsec-stats-scalar-obj-bad-trailers {
         type int32;
       }
       leaf ipsec-stats-scalar-obj-discarded {
         type int32;
       }
       leaf ipsec-stats-scalar-obj-invalid-spi {
         type int32;
       }
       leaf ipsec-stats-scalar-obj-ts-check-fail {
         type int32;
       }
       leaf ipsec-stats-scalar-obj-exceeds-tunnel-mtu {
         type int32;
       }
       leaf ipsec-stats-scalar-obj-get-value-errs {
         type int32;
       }
       leaf ipsec-stats-scalar-obj-next-lookup-calls {
         type int32;
       }
       leaf ipsec-stats-scalar-obj-next-lookup-invalid-key {
         type int32;
       }
       leaf ipsec-stats-scalar-obj-next-lookup-valid-cache {
         type int32;
       }
       leaf ipsec-stats-scalar-obj-next-lookup-key-alloc-err {
         type int32;
       }
       leaf ipsec-stats-scalar-obj-next-lookup-send-req-fail {
         type int32;
       }
       leaf ipsec-stats-scalar-obj-next-lookup-req-sent-now {
         type int32;
       }
       leaf ipsec-stats-scalar-obj-next-lookup-req-sent-before {
         type int32;
       }
       leaf ipsec-stats-scalar-obj-get-key-calls {
         type int32;
       }
       leaf ipsec-stats-scalar-obj-get-key-null-data {
         type int32;
       }
       leaf ipsec-stats-scalar-obj-get-request-timeout {
         type int32;
       }
       leaf ipsec-stats-scalar-obj-next-request-timeout {
         type int32;
       }
       leaf ipsec-stats-scalar-obj-stats-timeout-cb-calls {
         type int32;
       }
       leaf ipsec-stats-scalar-obj-stats-timeout-cb-res-fail {
         type int32;
       }
       leaf ipsec-stats-scalar-obj-stats-timeout-cb-response-sent {
         type int32;
       }
     }
     container ike-snmp-ha-link-ipsec-stats-scalar-obj-statistics {
       leaf ha-link-ipsec-stats-scalar-obj-get-requests {
         type int32;
       }
       leaf ha-link-ipsec-stats-scalar-obj-next-requests {
         type int32;
       }
       leaf ha-link-ipsec-stats-scalar-obj-lookup-calls {
         type int32;
       }
       leaf ha-link-ipsec-stats-scalar-obj-lookup-invalid-key {
         type int32;
       }
       leaf ha-link-ipsec-stats-scalar-obj-lookup-invalid-key-zero {
         type int32;
       }
       leaf ha-link-ipsec-stats-scalar-obj-lookup-cache-valid {
         type int32;
       }
       leaf ha-link-ipsec-stats-scalar-obj-lookup-key-alloc-err {
         type int32;
       }
       leaf ha-link-ipsec-stats-scalar-obj-lookup-send-req-fail {
         type int32;
       }
       leaf ha-link-ipsec-stats-scalar-obj-lookup-send-req-sent {
         type int32;
       }
       leaf ha-link-ipsec-stats-scalar-obj-get-value-calls {
         type int32;
       }
       leaf ha-link-ipsec-stats-scalar-obj-get-value-null-data {
         type int32;
       }
       leaf ha-link-ipsec-stats-scalar-obj-out-encrpyt-bytes {
         type int32;
       }
       leaf ha-link-ipsec-stats-scalar-obj-out-encrpyt-pkts {
         type int32;
       }
       leaf ha-link-ipsec-stats-scalar-obj-in-decrypt-bytes {
         type int32;
       }
       leaf ha-link-ipsec-stats-scalar-obj-in-decrypt-pkts {
         type int32;
       }
       leaf ha-link-ipsec-stats-scalar-obj-ah-in-bytes {
         type int32;
       }
       leaf ha-link-ipsec-stats-scalar-obj-ah-in-pkts {
         type int32;
       }
       leaf ha-link-ipsec-stats-scalar-obj-ah-out-bytes {
         type int32;
       }
       leaf ha-link-ipsec-stats-scalar-obj-ah-out-pkts {
         type int32;
       }
       leaf ha-link-ipsec-stats-scalar-obj-replay-drop-pkts {
         type int32;
       }
       leaf ha-link-ipsec-stats-scalar-obj-ah-auth-fails {
         type int32;
       }
       leaf ha-link-ipsec-stats-scalar-obj-esp-auth-fails {
         type int32;
       }
       leaf ha-link-ipsec-stats-scalar-obj-decrypt-fails {
         type int32;
       }
       leaf ha-link-ipsec-stats-scalar-obj-bad-headers {
         type int32;
       }
       leaf ha-link-ipsec-stats-scalar-obj-bad-trailers {
         type int32;
       }
       leaf ha-link-ipsec-stats-scalar-obj-discarded {
         type int32;
       }
       leaf ha-link-ipsec-stats-scalar-obj-invalid-spi {
         type int32;
       }
       leaf ha-link-ipsec-stats-scalar-obj-ts-check-fail {
         type int32;
       }
       leaf ha-link-ipsec-stats-scalar-obj-exceeds-tunnel-mtu {
         type int32;
       }
       leaf ha-link-ipsec-stats-scalar-obj-get-value-errs {
         type int32;
       }
       leaf ha-link-ipsec-stats-scalar-obj-next-lookup-calls {
         type int32;
       }
       leaf ha-link-ipsec-stats-scalar-obj-next-lookup-invalid-key {
         type int32;
       }
       leaf ha-link-ipsec-stats-scalar-obj-next-lookup-valid-cache {
         type int32;
       }
       leaf ha-link-ipsec-stats-scalar-obj-next-lookup-key-alloc-err {
         type int32;
       }
       leaf ha-link-ipsec-stats-scalar-obj-next-lookup-send-req-fail {
         type int32;
       }
       leaf ha-link-ipsec-stats-scalar-obj-next-lookup-req-sent-now {
         type int32;
       }
       leaf ha-link-ipsec-stats-scalar-obj-next-lookup-req-sent-before {
         type int32;
       }
       leaf ha-link-ipsec-stats-scalar-obj-get-request-timeout {
         type int32;
       }
       leaf ha-link-ipsec-stats-scalar-obj-next-request-timeout {
         type int32;
       }
       leaf ha-link-ipsec-stats-scalar-obj-get-key-calls {
         type int32;
       }
       leaf ha-link-ipsec-stats-scalar-obj-get-key-null-data {
         type int32;
       }
       leaf ha-link-ipsec-stats-scalar-obj-stats-timeout-cb-calls {
         type int32;
       }
       leaf ha-link-ipsec-stats-scalar-obj-stats-timeout-cb-res-fail {
         type int32;
       }
       leaf ha-link-ipsec-stats-scalar-obj-stats-timeout-cb-response-sent {
         type int32;
       }
     }
     container ike-snmp-ike-peer-addr-table-statistics {
       leaf ike-peer-addr-table-get-requests {
         type int32;
       }
       leaf ike-peer-addr-table-next-requests {
         type int32;
       }
       leaf ike-peer-addr-table-get-request-timeout {
         type int32;
       }
       leaf ike-peer-addr-table-next-request-timeout {
         type int32;
       }
       leaf ike-peer-addr-table-lookup-calls {
         type int32;
       }
       leaf ike-peer-addr-table-lookup-invalid-key {
         type int32;
       }
       leaf ike-peer-addr-table-lookup-invalid-active-support {
         type int32;
       }
       leaf ike-peer-addr-table-lookup-key-alloc-err {
         type int32;
       }
       leaf ike-peer-addr-table-lookup-send-req-fail {
         type int32;
       }
       leaf ike-peer-addr-table-get-value-calls {
         type int32;
       }
       leaf ike-peer-addr-table-get-value-null-data {
         type int32;
       }
       leaf ike-peer-addr-table-addr-state {
         type int32;
       }
       leaf ike-peer-addr-table-remote-gw-addr-type {
         type int32;
       }
       leaf ike-peer-addr-table-remote-gw-addr {
         type int32;
       }
       leaf ike-peer-addr-table-remote-port {
         type int32;
       }
       leaf ike-peer-addr-table-local-gw-addr-type {
         type int32;
       }
       leaf ike-peer-addr-table-local-gw-addr {
         type int32;
       }
       leaf ike-peer-addr-table-local-port {
         type int32;
       }
       leaf ike-peer-addr-table-routing-instance {
         type int32;
       }
       leaf ike-peer-addr-table-addr-index {
         type int32;
       }
       leaf ike-peer-addr-table-get-value-errs {
         type int32;
       }
       leaf ike-peer-addr-table-next-lookup-calls {
         type int32;
       }
       leaf ike-peer-addr-table-next-lookup-invalid-key {
         type int32;
       }
       leaf ike-peer-addr-table-next-lookup-response-sent {
         type int32;
       }
       leaf ike-peer-addr-table-next-lookup-key-alloc-err {
         type int32;
       }
       leaf ike-peer-addr-table-next-lookup-send-req-fail {
         type int32;
       }
       leaf ike-peer-addr-table-next-lookup-req-sent-now {
         type int32;
       }
       leaf ike-peer-addr-table-next-lookup-req-sent-before {
         type int32;
       }
       leaf ike-peer-addr-table-get-key-calls {
         type int32;
       }
       leaf ike-peer-addr-table-get-key-null-data {
         type int32;
       }
       leaf ike-peer-addr-table-next-responses {
         type int32;
       }
       leaf ike-peer-addr-table-next-responses-null {
         type int32;
       }
       leaf ike-peer-addr-table-next-response-complete {
         type int32;
       }
       leaf ike-peer-addr-table-next-response-sent {
         type int32;
       }
       leaf ike-peer-addr-table-next-send-req-fail {
         type int32;
       }
       leaf ike-peer-addr-table-next-null-response-sent {
         type int32;
       }
       leaf ike-peer-addr-table-next-req-sent {
         type int32;
       }
       leaf ike-peer-addr-table-next-resp-peer-addr-add-mem-alloc-fail {
         type int32;
       }
       leaf ike-peer-addr-table-next-resp-peer-addr-add-fail {
         type int32;
       }
       leaf ike-peer-addr-table-next-resp-peer-addr-add-success {
         type int32;
       }
       leaf ike-peer-addr-table-next-resp-ike-stats-mem-alloc-fail {
         type int32;
       }
       leaf ike-peer-addr-table-next-resp-active-ike-sa-list-mem-alloc-fail {
         type int32;
       }
       leaf ike-peer-addr-table-next-resp-active-ipsec-sa-list-mem-alloc-fail {
         type int32;
       }
       leaf ike-peer-addr-table-start-req-sent-timer {
         type int32;
       }
       leaf ike-peer-addr-table-clear-req-sent-timer {
         type int32;
       }
       leaf ike-peer-addr-table-iked-req-timeout {
         type int32;
       }
       leaf ike-peer-addr-table-cache-start-timer {
         type int32;
       }
       leaf ike-peer-addr-table-cache-delete {
         type int32;
       }
       leaf ike-peer-addr-table-get-response {
         type int32;
       }
       leaf ike-peer-addr-table-get-response-null {
         type int32;
       }
       leaf ike-peer-addr-table-cache-timer-expire {
         type int32;
       }
     }
     container ike-snmp-ike-peer-id-table-statistics {
       leaf ike-peer-id-table-get-requests {
         type int32;
       }
       leaf ike-peer-id-table-next-requests {
         type int32;
       }
       leaf ike-peer-id-table-lookup-calls {
         type int32;
       }
       leaf ike-peer-id-table-lookup-invalid-key {
         type int32;
       }
       leaf ike-peer-id-table-lookup-invalid-active-state {
         type int32;
       }
       leaf ike-peer-id-table-get-value-calls {
         type int32;
       }
       leaf ike-peer-id-table-get-value-null-data {
         type int32;
       }
       leaf ike-peer-id-table-state {
         type int32;
       }
       leaf ike-peer-id-table-remote-id-type {
         type int32;
       }
       leaf ike-peer-id-table-remote-id-value {
         type int32;
       }
       leaf ike-peer-id-table-local-id-type {
         type int32;
       }
       leaf ike-peer-id-table-local-id-value {
         type int32;
       }
       leaf ike-peer-id-table-aaa-user-name {
         type int32;
       }
       leaf ike-peer-id-table-index {
         type int32;
       }
       leaf ike-peer-id-table-get-value-errs {
         type int32;
       }
       leaf ike-peer-id-table-next-lookup-calls {
         type int32;
       }
       leaf ike-peer-id-table-next-lookup-invalid-key {
         type int32;
       }
       leaf ike-peer-id-table-next-lookup-response-sent {
         type int32;
       }
       leaf ike-peer-id-table-next-lookup-key-alloc-err {
         type int32;
       }
       leaf ike-peer-id-table-next-lookup-send-req-fail {
         type int32;
       }
       leaf ike-peer-id-table-next-lookup-req-sent-now {
         type int32;
       }
       leaf ike-peer-id-table-next-lookup-req-sent-before {
         type int32;
       }
       leaf ike-peer-id-table-next-resp-peer-id-add-mem-alloc-fail {
         type int32;
       }
       leaf ike-peer-id-table-next-resp-peer-id-add-fail {
         type int32;
       }
       leaf ike-peer-id-table-next-resp-peer-id-add-success {
         type int32;
       }
       leaf ike-peer-id-table-get-key-calls {
         type int32;
       }
       leaf ike-peer-id-table-get-key-null-data {
         type int32;
       }
     }
     container ike-snmp-ike-peer-stats-table-statistics {
       leaf ike-peer-stats-table-get-requests {
         type int32;
       }
       leaf ike-peer-stats-table-next-requests {
         type int32;
       }
       leaf ike-peer-stats-table-lookup-calls {
         type int32;
       }
       leaf ike-peer-stats-table-lookup-invalid-key {
         type int32;
       }
       leaf ike-peer-stats-table-lookup-invalid-active-state {
         type int32;
       }
       leaf ike-peer-stats-table-lookup-key-alloc-err {
         type int32;
       }
       leaf ike-peer-stats-table-lookup-send-req-fail {
         type int32;
       }
       leaf ike-peer-stats-table-get-value-calls {
         type int32;
       }
       leaf ike-peer-stats-table-get-value-null-data {
         type int32;
       }
       leaf ike-peer-stats-table-state {
         type int32;
       }
       leaf ike-peer-stats-table-index {
         type int32;
       }
       leaf ike-peer-stats-table-remote-gw-addr-type {
         type int32;
       }
       leaf ike-peer-stats-table-remote-gw-addr {
         type int32;
       }
       leaf ike-peer-stats-table-remote-port {
         type int32;
       }
       leaf ike-peer-stats-table-local-gw-addr-type {
         type int32;
       }
       leaf ike-peer-stats-table-local-gw-addr {
         type int32;
       }
       leaf ike-peer-stats-table-local-port {
         type int32;
       }
       leaf ike-peer-stats-table-local-id-type {
         type int32;
       }
       leaf ike-peer-stats-table-local-id-value {
         type int32;
       }
       leaf ike-peer-stats-table-remote-id-type {
         type int32;
       }
       leaf ike-peer-stats-table-remote-id-value {
         type int32;
       }
       leaf ike-peer-stats-table-routing-instance {
         type int32;
       }
       leaf ike-peer-stats-table-aaa-user-name {
         type int32;
       }
       leaf ike-peer-stats-table-gw-name {
         type int32;
       }
       leaf ike-peer-stats-table-initiator-ike-sa-req-out {
         type int32;
       }
       leaf ike-peer-stats-table-initiator-ike-sa-res-in {
         type int32;
       }
       leaf ike-peer-stats-table-initiator-ike-sa-res-invalid-ike-spi {
         type int32;
       }
       leaf ike-peer-stats-table-initiator-ike-sa-invalid-ke-payload-in {
         type int32;
       }
       leaf ike-peer-stats-table-initiator-ike-sa-no-proposal-chosen-in {
         type int32;
       }
       leaf ike-peer-stats-table-initiator-ike-sa-res-verify-sa-fail {
         type int32;
       }
       leaf ike-peer-stats-table-initiator-ike-sa-fill-fail {
         type int32;
       }
       leaf ike-peer-stats-table-initiator-ike-sa-dh-group-fail {
         type int32;
       }
       leaf ike-peer-stats-table-initiator-ike-sa-cookie-req-in {
         type int32;
       }
       leaf ike-peer-stats-table-initiator-ike-sa-cookie-res-out {
         type int32;
       }
       leaf ike-peer-stats-table-initiator-ike-sa-dh-compute-key-fail {
         type int32;
       }
       leaf ike-peer-stats-table-responder-ike-sa-req-in {
         type int32;
       }
       leaf ike-peer-stats-table-responder-ike-sa-res-out {
         type int32;
       }
       leaf ike-peer-stats-table-responder-ike-sa-no-proposal-chosen-out {
         type int32;
       }
       leaf ike-peer-stats-table-responder-ike-sa-invalid-ke-payload-out {
         type int32;
       }
       leaf ike-peer-stats-table-responder-ike-sa-invalid-dh-group-conf {
         type int32;
       }
       leaf ike-peer-stats-table-responder-ike-sa-res-dh-gen-key-fail {
         type int32;
       }
       leaf ike-peer-stats-table-responder-ike-sa-res-get-cas-fail {
         type int32;
       }
       leaf ike-peer-stats-table-responder-ike-sa-res-get-vid-fail {
         type int32;
       }
       leaf ike-peer-stats-table-responder-ike-sa-dh-compute-key-fail {
         type int32;
       }
       leaf ike-peer-stats-table-responder-ike-sa-cookie-req-out {
         type int32;
       }
       leaf ike-peer-stats-table-responder-ike-sa-cookie-res-in {
         type int32;
       }
       leaf ike-peer-stats-table-initiator-ike-auth-req-out {
         type int32;
       }
       leaf ike-peer-stats-table-initiator-ike-auth-res-in {
         type int32;
       }
       leaf ike-peer-stats-table-initiator-ike-auth-no-proposal-chosen-in {
         type int32;
       }
       leaf ike-peer-stats-table-initiator-ike-auth-ts-unacceptable-in {
         type int32;
       }
       leaf ike-peer-stats-table-initiator-ike-auth-authentication-failed-in {
         type int32;
       }
       leaf ike-peer-stats-table-responder-ike-req-in {
         type int32;
       }
       leaf ike-peer-stats-table-responder-ike-auth-res-out {
         type int32;
       }
       leaf ike-peer-stats-table-responder-ike-auth-authentication-failed-out {
         type int32;
       }
       leaf ike-peer-stats-table-responder-ike-auth-no-proposal-chosen-out {
         type int32;
       }
       leaf ike-peer-stats-table-responder-ike-auth-ts-unacceptable-out {
         type int32;
       }
       leaf ike-peer-stats-table-initiator-ike-sa-rekey-req-out {
         type int32;
       }
       leaf ike-peer-stats-table-initiator-ike-sa-rekey-res-in {
         type int32;
       }
       leaf ike-peer-stats-table-initiator-ike-sa-rekey-no-proposal-chosen-in {
         type int32;
       }
       leaf ike-peer-stats-table-initiator-ike-sa-rekey-invalid-key-in {
         type int32;
       }
       leaf ike-peer-stats-table-initiator-ike-sa-rekey-res-verify-sa-fail {
         type int32;
       }
       leaf ike-peer-stats-table-initiator-ike-sa-rekey-res-fill-ike-sa-fail {
         type int32;
       }
       leaf ike-peer-stats-table-initiator-ike-sa-rekey-res-verify-dh-group-fail {
         type int32;
       }
       leaf ike-peer-stats-table-initiator-ike-sa-rekey-res-dh-compute-key-fail {
         type int32;
       }
       leaf ike-peer-stats-table-responder-ike-sa-rekey-req-in {
         type int32;
       }
       leaf ike-peer-stats-table-responder-ike-sa-rekey-res-out {
         type int32;
       }
       leaf ike-peer-stats-table-responder-ike-sa-rekey-no-proposal-chosen-out {
         type int32;
       }
       leaf ike-peer-stats-table-responder-ike-sa-rekey-invalid-key-out {
         type int32;
       }
       leaf ike-peer-stats-table-responder-ike-sa-rekey-dh-compute-key-fail {
         type int32;
       }
       leaf ike-peer-stats-table-initiator-ipsec-sa-rekey-req-out {
         type int32;
       }
       leaf ike-peer-stats-table-initiator-ipsec-sa-rekey-res-in {
         type int32;
       }
       leaf ike-peer-stats-table-initiator-ipsec-sa-rekey-no-proposal-chosen-in {
         type int32;
       }
       leaf ike-peer-stats-table-initiator-ipsec-sa-rekey-invalid-key-in {
         type int32;
       }
       leaf ike-peer-stats-table-initiator-ipsec-sa-rekey-ts-unacceptable-in {
         type int32;
       }
       leaf ike-peer-stats-table-initiator-ipsec-sa-rekey-res-verify-sa-fail {
         type int32;
       }
       leaf ike-peer-stats-table-initiator-ipsec-sa-rekey-res-verify-dh-group-fail {
         type int32;
       }
       leaf ike-peer-stats-table-initiator-ipsec-sa-rekey-res-verify-ts-fail {
         type int32;
       }
       leaf ike-peer-stats-table-initiator-ipsec-sa-rekey-dh-compute-key-fail {
         type int32;
       }
       leaf ike-peer-stats-table-responder-ipsec-sa-rekey-req-in {
         type int32;
       }
       leaf ike-peer-stats-table-responder-ipsec-sa-rekey-res-out {
         type int32;
       }
       leaf ike-peer-stats-table-responder-ipsec-sa-rekey-no-proposal-chosen-out {
         type int32;
       }
       leaf ike-peer-stats-table-responder-ipsec-sa-rekey-invalid-key-out {
         type int32;
       }
       leaf ike-peer-stats-table-responder-ipsec-sa-rekey-ts-unacceptable-out {
         type int32;
       }
       leaf ike-peer-stats-table-responder-ipsec-sa-rekey-dh-compute-key-fail {
         type int32;
       }
       leaf ike-peer-stats-table-tun-type {
         type int32;
       }
       leaf ike-peer-stats-table-get-value-errs {
         type int32;
       }
       leaf ike-peer-stats-table-next-lookup-calls {
         type int32;
       }
       leaf ike-peer-stats-table-next-lookup-invalid-key {
         type int32;
       }
       leaf ike-peer-stats-table-next-lookup-response-sent {
         type int32;
       }
       leaf ike-peer-stats-table-next-lookup-key-alloc-err {
         type int32;
       }
       leaf ike-peer-stats-table-next-lookup-send-req-fail {
         type int32;
       }
       leaf ike-peer-stats-table-next-lookup-req-sent-now {
         type int32;
       }
       leaf ike-peer-stats-table-next-lookup-req-sent-before {
         type int32;
       }
       leaf ike-peer-stats-table-next-resp-peer-index-add-mem-alloc-fail {
         type int32;
       }
       leaf ike-peer-stats-table-next-resp-peer-index-add-fail {
         type int32;
       }
       leaf ike-peer-stats-table-next-resp-peer-index-add-success {
         type int32;
       }
       leaf ike-peer-stats-table-get-key-calls {
         type int32;
       }
       leaf ike-peer-stats-table-get-key-null-data {
         type int32;
       }
     }
     container ike-snmp-peer-ike-sa-corr-table-statistics {
       leaf peer-ike-sa-corr-table-get-requests {
         type int32;
       }
       leaf peer-ike-sa-corr-table-next-requests {
         type int32;
       }
       leaf peer-ike-sa-corr-table-lookup-calls {
         type int32;
       }
       leaf peer-ike-sa-corr-table-lookup-invalid-key {
         type int32;
       }
       leaf peer-ike-sa-corr-table-lookup-key-alloc-err {
         type int32;
       }
       leaf peer-ike-sa-corr-table-lookup-send-req-fail {
         type int32;
       }
       leaf peer-ike-sa-corr-table-get-value-calls {
         type int32;
       }
       leaf peer-ike-sa-corr-table-get-value-null-data {
         type int32;
       }
       leaf peer-ike-sa-corr-table-tun-mon-index {
         type int32;
       }
       leaf peer-ike-sa-corr-table-next-lookup-calls {
         type int32;
       }
       leaf peer-ike-sa-corr-table-next-lookup-invalid-key {
         type int32;
       }
       leaf peer-ike-sa-corr-table-next-lookup-response-sent {
         type int32;
       }
       leaf peer-ike-sa-corr-table-next-lookup-key-alloc-err {
         type int32;
       }
       leaf peer-ike-sa-corr-table-next-lookup-send-req-fail {
         type int32;
       }
       leaf peer-ike-sa-corr-table-next-lookup-req-sent-now {
         type int32;
       }
       leaf peer-ike-sa-corr-table-next-lookup-req-sent-before {
         type int32;
       }
       leaf peer-ike-sa-corr-table-next-resp-peer-ike-sa-add-mem-alloc-fail {
         type int32;
       }
       leaf peer-ike-sa-corr-table-next-resp-peer-ike-sa-add-fail {
         type int32;
       }
       leaf peer-ike-sa-corr-table-next-resp-peer-ike-sa-add-success {
         type int32;
       }
       leaf peer-ike-sa-corr-table-get-key-calls {
         type int32;
       }
       leaf peer-ike-sa-corr-table-get-key-null-data {
         type int32;
       }
     }
     container ike-snmp-peer-ipsec-tun-corr-table-statistics {
       leaf peer-ipsec-tun-corr-table-get-requests {
         type int32;
       }
       leaf peer-ipsec-tun-corr-table-next-requests {
         type int32;
       }
       leaf peer-ipsec-tun-corr-table-lookup-calls {
         type int32;
       }
       leaf peer-ipsec-tun-corr-table-lookup-invalid-key {
         type int32;
       }
       leaf peer-ipsec-tun-corr-table-lookup-key-alloc-err {
         type int32;
       }
       leaf peer-ipsec-tun-corr-table-lookup-send-req-fail {
         type int32;
       }
       leaf peer-ipsec-tun-corr-table-get-value-calls {
         type int32;
       }
       leaf peer-ipsec-tun-corr-table-get-value-null-data {
         type int32;
       }
       leaf peer-ipsec-tun-corr-table-tun-mon-index {
         type int32;
       }
       leaf peer-ipsec-tun-corr-table-next-lookup-calls {
         type int32;
       }
       leaf peer-ipsec-tun-corr-table-next-lookup-invalid-key {
         type int32;
       }
       leaf peer-ipsec-tun-corr-table-next-lookup-response-sent {
         type int32;
       }
       leaf peer-ipsec-tun-corr-table-next-lookup-key-alloc-err {
         type int32;
       }
       leaf peer-ipsec-tun-corr-table-next-lookup-send-req-fail {
         type int32;
       }
       leaf peer-ipsec-tun-corr-table-next-lookup-req-sent-now {
         type int32;
       }
       leaf peer-ipsec-tun-corr-table-next-lookup-req-sent-before {
         type int32;
       }
       leaf peer-ipsec-tun-corr-table-next-resp-peer-ipsec-tunnel-add-mem-alloc-fail {
         type int32;
       }
       leaf peer-ipsec-tun-corr-table-next-resp-peer-ipsec-tunnel-add-fail {
         type int32;
       }
       leaf peer-ipsec-tun-corr-table-next-resp-peer-ipsec-tunnel-add-success {
         type int32;
       }
     }
   }
   grouping ike-config-management-memory-stats-block {
     container ike-config-memory-statistics {
       leaf ike-m-sadb-key {
         type int32;
       }
       leaf ike-m-sockaddr {
         type int32;
       }
       leaf ike-m-proposal {
         type int32;
       }
       leaf ike-m-proposal-list {
         type int32;
       }
       leaf ike-m-ipsec-vpn-cfg {
         type int32;
       }
       leaf ike-m-svc-set-cfg {
         type int32;
       }
       leaf ike-m-vpn-cfg-name-list {
         type int32;
       }
       leaf ike-m-proxy-id {
         type int32;
       }
       leaf ike-m-profile {
         type int32;
       }
       leaf ike-m-filter {
         type int32;
       }
       leaf ike-m-filter-name {
         type int32;
       }
       leaf ike-m-ipsec-ike-params {
         type int32;
       }
       leaf ike-m-ike-params {
         type int32;
       }
       leaf ike-m-ipsec-ike-key {
         type int32;
       }
       leaf ike-m-psk-key {
         type int32;
       }
       leaf ike-m-psk-id {
         type int32;
       }
       leaf ike-m-ike-id {
         type int32;
       }
       leaf ike-m-ike-id-list {
         type int32;
       }
       leaf ike-m-ike-proxy-id-pair-list {
         type int32;
       }
       leaf ike-m-misc-ike-id {
         type int32;
       }
       leaf ike-m-misc {
         type int32;
       }
       leaf ike-m-ipaddr-str {
         type int32;
       }
       leaf ike-m-port-str {
         type int32;
       }
       leaf ike-m-ipsec-sa-life {
         type int32;
       }
       leaf ike-m-ipsec-algo-name {
         type int32;
       }
       leaf ike-m-ipsec-algo {
         type int32;
       }
       leaf ike-m-ipsec-proposal {
         type int32;
       }
       leaf ike-m-ipsec-proposal-list {
         type int32;
       }
       leaf ike-m-ca-cfg {
         type int32;
       }
       leaf ike-m-ca-profile {
         type int32;
       }
       leaf ike-m-file-name {
         type int32;
       }
       leaf ike-m-svc-intf {
         type int32;
       }
       leaf ike-m-route {
         type int32;
       }
       leaf ike-m-stats {
         type int32;
       }
       leaf ike-m-ipsec-tunnel-key {
         type int32;
       }
       leaf ike-m-ike-gateway {
         type int32;
       }
       leaf ike-m-cfg-index {
         type int32;
       }
       leaf ike-m-p1-cfg {
         type int32;
       }
       leaf ike-m-p2-cfg {
         type int32;
       }
       leaf ike-m-trace-cfg {
         type int32;
       }
       leaf ike-m-bind-int-cfg {
         type int32;
       }
       leaf ike-m-dpd {
         type int32;
       }
       leaf ike-m-ip-addr {
         type int32;
       }
       leaf ike-m-vpnref-list {
         type int32;
       }
       leaf ike-m-pltref-list {
         type int32;
       }
       leaf ike-m-sreq {
         type int32;
       }
       leaf ike-m-ike-res {
         type int32;
       }
       leaf ike-m-ipsec-res {
         type int32;
       }
       leaf ike-m-stats-res {
         type int32;
       }
       leaf ike-m-location {
         type int32;
       }
       leaf ike-m-time-rec {
         type int32;
       }
       leaf ike-m-io-rec {
         type int32;
       }
       leaf ike-m-ijcl-clntctx {
         type int32;
       }
       leaf ike-m-ijcl-prodinfo {
         type int32;
       }
       leaf ike-m-ijcl-clntmsg {
         type int32;
       }
       leaf ike-m-ts-list {
         type int32;
       }
       leaf ike-m-ts-cfg {
         type int32;
       }
       leaf ike-m-ip-port {
         type int32;
       }
       leaf ike-m-ip-subnet {
         type int32;
       }
       leaf ike-m-p2-list {
         type int32;
       }
       leaf ike-m-iked-plat-info {
         type int32;
       }
       leaf ike-m-if-info {
         type int32;
       }
       leaf ike-m-proto-msg {
         type int32;
       }
       leaf ike-m-ui-spu-data-to-re {
         type int32;
       }
       leaf ike-m-ui-bucket {
         type int32;
       }
       leaf ike-m-ui-ipc-context {
         type int32;
       }
       leaf ike-m-ui-sorting-node {
         type int32;
       }
       leaf ike-m-ui-bucket-data {
         type int32;
       }
       leaf ike-m-policy {
         type int32;
       }
       leaf ike-m-ui-ipsec-stats {
         type int32;
       }
       leaf ike-m-cert {
         type int32;
       }
       leaf ike-m-dynamic-ike-id {
         type int32;
       }
       leaf ike-m-bind-intf-list {
         type int32;
       }
       leaf ike-m-bpool-cfg {
         type int32;
       }
       leaf ike-m-bpool-entry {
         type int32;
       }
       leaf ike-m-natt {
         type int32;
       }
       leaf ike-m-ike-cfg {
         type int32;
       }
       leaf ike-m-bad-spi {
         type int32;
       }
       leaf ike-m-idle-time {
         type int32;
       }
       leaf ike-m-anti-replay {
         type int32;
       }
       leaf ike-m-udp-encap {
         type int32;
       }
       leaf ike-m-remote-addr {
         type int32;
       }
       leaf ike-m-ike-frag {
         type int32;
       }
       leaf ike-m-snmp {
         type int32;
       }
       leaf ike-m-int-sa-enc-key-res {
         type int32;
       }
       leaf ike-m-plat-cfg {
         type int32;
       }
       leaf ike-m-dist-profile-cfg {
         type int32;
       }
       leaf ike-m-ts-name-list {
         type int32;
       }
       leaf ike-m-trap-cfg {
         type int32;
       }
       leaf ike-m-ts-name {
         type int32;
       }
       leaf ike-m-parse-ipsec-sa-cfg {
         type int32;
       }
       leaf ike-m-active-ipsec-sa-cfg {
         type int32;
       }
       leaf ike-m-ipsec-sa {
         type int32;
       }
     }
   }
   grouping ike-config-management-manual-sa-stats-block {
     container ike-config-manual-sa-cfg-statistics {
       leaf ike-config-apply-info-sec-assoc-del-all {
         type int32;
       }
       leaf ike-config-apply-info-sec-assoc-del-one-find-fail {
         type int32;
       }
       leaf ike-config-apply-info-sec-assoc-new {
         type int32;
       }
       leaf ike-config-apply-info-sec-assoc-change {
         type int32;
       }
       leaf ike-config-apply-info-sec-assoc-change-del-sa {
         type int32;
       }
       leaf ike-config-apply-info-sec-assoc-no-change {
         type int32;
       }
       leaf ike-config-apply-info-sec-assoc-create-fail {
         type int32;
       }
       leaf ike-config-apply-info-sec-assoc-authkey-fail {
         type int32;
       }
       leaf ike-config-apply-info-sec-assoc-encrkey-fail {
         type int32;
       }
       leaf ike-config-apply-info-sec-assoc-create-sa-in-fail {
         type int32;
       }
       leaf ike-config-apply-info-sec-assoc-create-sa-out-fail {
         type int32;
       }
       leaf ike-config-apply-info-sec-assoc-unsupported-mode-dir-fail {
         type int32;
       }
       leaf ike-config-sec-assoc-dup-add-kernel {
         type int32;
       }
       leaf ike-config-sec-assoc-prepare-info-fail {
         type int32;
       }
       leaf ike-config-sec-assoc-add-to-kernel-fail {
         type int32;
       }
       leaf ike-config-sec-assoc-fetch-from-kernel-fail {
         type int32;
       }
       leaf ike-config-sec-assoc-add-to-kernel-success {
         type int32;
       }
       leaf ike-config-sec-assoc-del-sa-not-installed {
         type int32;
       }
       leaf ike-config-sec-assoc-del-sa-fail {
         type int32;
       }
       leaf ike-config-sec-assoc-del-sa-index-fail {
         type int32;
       }
       leaf ike-config-sec-assoc-del-sa-success {
         type int32;
       }
       leaf ike-config-sec-assoc-del-sa-index-success {
         type int32;
       }
       leaf ike-config-sec-assoc-del-blob-cfg-not-exist {
         type int32;
       }
       leaf ike-config-sec-assoc-del-blob-mode-not-match {
         type int32;
       }
       leaf ike-config-sec-assoc-del-blob-sa-type-not-match {
         type int32;
       }
       leaf ike-config-sec-assoc-del-blob-proto-not-match {
         type int32;
       }
       leaf ike-config-sec-assoc-del-blob-spi-not-match {
         type int32;
       }
       leaf ike-config-sec-assoc-del-blob-auth-info-not-match {
         type int32;
       }
       leaf ike-config-sec-assoc-del-blob-encr-info-not-match {
         type int32;
       }
       leaf ike-config-sec-assoc-blob-cfg-match {
         type int32;
       }
     }
   }
   grouping ike-security-associations-information-block {
     list ike-security-associations {
       leaf ike-sa-index {
         type uint32;
         description "Index";
       }
       leaf ike-sa-state {
         type string;
         description "Status of the SA";
       }
       leaf ike-sa-initiator-cookie {
         type string;
         description "IKE SA initiator cookie";
       }
       leaf ike-sa-responder-cookie {
         type string;
         description "IKE SA responder cookie";
       }
       leaf ike-sa-exchange-type {
         type string;
         description "Exchange type";
       }
       leaf ike-sa-remote-address {
         type jt:ipaddr;
         description "Remote address";
       }
       container ike-sa-algorithms {
         leaf ike-sa-sig-key-length {
           type uint32;
           description "Signature Key Length";
         }
       }
       container ike-sa-traffic-statistics {
         leaf ike-sa-output-invalid-spi-packets {
           type int32;
           description "Number of invalid SPI notifications send";
         }
         leaf ike-sa-input-invalid-spi-packets {
           type int32;
           description "Number of invalid SPI notifications received";
         }
         leaf ike-sa-input-frag-packets {
           type int32;
           description "Input fragmentation packets, including retransmissions";
         }
         leaf ike-sa-output-frag-packets {
           type int32;
           description "Output fragmentation packets, including retransmissions";
         }
       }
       container ike-sa-misc {
         leaf ike-sa-num-ipsec-rekeys {
           type int32;
           description "Number of IPSec rekeys using this SA";
         }
         leaf ike-sa-exchange-type {
           type string;
           description "Exchange type";
         }
       }
       container ike-sa-payload-statistics {
         leaf ike-sa-delete-payloads-received {
           type int32;
           description "Number of delete payloads received";
         }
         leaf ike-sa-delete-payloads-sent {
           type int32;
           description "Number of delete payloads sent";
         }
         leaf ike-sa-r-u-there-payloads-received {
           type int32;
           description "Number of DPD R-U-THERE payloads received";
         }
         leaf ike-sa-r-u-there-payloads-sent {
           type int32;
           description "Number of DPD R-U-THERE payloads sent";
         }
         leaf ike-sa-r-u-there-ack-payloads-received {
           type int32;
           description "Number of DPD R-U-THERE-ACK payloads received";
         }
         leaf ike-sa-r-u-there-ack-payloads-sent {
           type int32;
           description "Number of DPD R-U-THERE-ACK payloads sent";
         }
         leaf ike-sa-r-u-there-ack-payloads-missed {
           type int32;
           description "Number of DPD R-U-THERE-ACK payloads missed";
         }
         leaf ike-sa-r-u-there-ack-payloads-maximum-delay {
           type int32;
           description "Worst case delay for the DPD R-U-THERE-ACK";
         }
         leaf ike-sa-r-u-there-ack-seq-payloads-missed {
           type int32;
           description "Number of DPD R-U-THERE-ACK payloads missed in sequence";
         }
         leaf ike-sa-dpd-request-payloads-received {
           type int32;
           description "Number of DPD request payloads received";
         }
         leaf ike-sa-dpd-request-payloads-sent {
           type int32;
           description "Number of DPD request payloads sent";
         }
         leaf ike-sa-dpd-response-payloads-received {
           type int32;
           description "Number of DPD response payloads received";
         }
         leaf ike-sa-dpd-response-payloads-sent {
           type int32;
           description "Number of DPD response payloads sent";
         }
         leaf ike-sa-dpd-response-payloads-missed {
           type int32;
           description "Number of DPD response payloads missed";
         }
         leaf ike-sa-dpd-response-payloads-maximum-delay {
           type int32;
           description "Worst case delay for the DPD response";
         }
         leaf ike-sa-dpd-response-seq-payloads-missed {
           type int32;
           description "Number of DPD response payloads missed in sequence";
         }
         leaf ike-sa-invalid-spi-notifications-received {
           type int32;
           description "Number of invalid SPI notifications received";
         }
         leaf ike-sa-invalid-spi-notifications-sent {
           type int32;
           description "Number of invalid SPI notifications sent";
         }
       }
       container ike-sa-stats-information {
       }
       leaf ike-sa-reauthlifetime {
         type string;
         description "Remaining IKE Hard lifetime before re-authentication, in seconds";
       }
       leaf ike-sa-ike-frag {
         type string;
         description "IKE Fragmentation Flag";
       }
       leaf ike-sa-frag-size {
         type int32;
         description "IKE Fragmentation Size";
       }
       leaf ike-sa-routing-instance {
         type string;
         description "Local-gateway routing instance";
       }
       leaf ike-sa-local-gateway-interface {
         type string;
         description "Local gateway  interface";
       }
       leaf ike-ike-id {
         type string;
         description "IKE ID";
       }
     }
     container ike-sa-stats-information {
     }
     container ike-security-associations-block {
       list ike-security-associations {
         container ike-sa-algorithms {
           leaf ike-sa-sig-key-length {
             type uint32;
             description "Signature Key Length";
           }
           leaf ike-sa-authentication-algorithm {
             type string;
             description "Authentication algorithm";
           }
           leaf ike-sa-encryption-algorithm {
             type string;
             description "Encryption algorithm";
           }
           leaf ike-sa-prf-algorithm {
             type string;
             description "PRF algorithm";
           }
           leaf ike-sa-dhgroup {
             type string;
             description "DH group";
           }
         }
         container ike-sa-traffic-statistics {
           leaf ike-sa-output-invalid-spi-packets {
             type int32;
             description "Number of invalid SPI notifications send";
           }
           leaf ike-sa-input-invalid-spi-packets {
             type int32;
             description "Number of invalid SPI notifications received";
           }
           leaf ike-sa-input-frag-packets {
             type int32;
             description "Input fragmentation packets, including retransmissions";
           }
           leaf ike-sa-output-frag-packets {
             type int32;
             description "Output fragmentation packets, including retransmissions";
           }
           leaf ike-sa-input-bytes {
             type int32;
             description "Input bytes, including retransmissions";
           }
           leaf ike-sa-output-bytes {
             type int32;
             description "Output bytes, including retransmissions";
           }
           leaf ike-sa-input-packets {
             type int32;
             description "Input packets, including retransmissions";
           }
           leaf ike-sa-output-packets {
             type int32;
             description "Output packets, including retransmissions";
           }
         }
         container ike-sa-misc {
           leaf ike-sa-num-ipsec-rekeys {
             type int32;
             description "Number of IPSec rekeys using this SA";
           }
           leaf ike-sa-exchange-type {
             type string;
             description "Exchange type";
           }
           leaf ike-sa-flags {
             type string;
             description "IKE SA flags";
           }
           leaf ike-sa-num-ipsec-sas-created {
             type int32;
             description "Number of IPSec SAs created using this SA";
           }
           leaf ike-sa-num-ipsec-sas-deleted {
             type int32;
             description "Number of IPSec SAs deleted using this SA";
           }
           leaf ike-sa-num-phase2-negotiations {
             type int32;
             description "Number of negotiations in progress on this SA";
           }
           leaf ike-ipsec-sa-tunnel-ids {
             type string;
             description "Ipsec SA tunnel Indexes";
           }
         }
         container ike-sa-payload-statistics {
           leaf ike-sa-delete-payloads-received {
             type int32;
             description "Number of delete payloads received";
           }
           leaf ike-sa-delete-payloads-sent {
             type int32;
             description "Number of delete payloads sent";
           }
           leaf ike-sa-r-u-there-payloads-received {
             type int32;
             description "Number of DPD R-U-THERE payloads received";
           }
           leaf ike-sa-r-u-there-payloads-sent {
             type int32;
             description "Number of DPD R-U-THERE payloads sent";
           }
           leaf ike-sa-r-u-there-ack-payloads-received {
             type int32;
             description "Number of DPD R-U-THERE-ACK payloads received";
           }
           leaf ike-sa-r-u-there-ack-payloads-sent {
             type int32;
             description "Number of DPD R-U-THERE-ACK payloads sent";
           }
           leaf ike-sa-r-u-there-ack-payloads-missed {
             type int32;
             description "Number of DPD R-U-THERE-ACK payloads missed";
           }
           leaf ike-sa-r-u-there-ack-payloads-maximum-delay {
             type int32;
             description "Worst case delay for the DPD R-U-THERE-ACK";
           }
           leaf ike-sa-r-u-there-ack-seq-payloads-missed {
             type int32;
             description "Number of DPD R-U-THERE-ACK payloads missed in sequence";
           }
           leaf ike-sa-dpd-request-payloads-received {
             type int32;
             description "Number of DPD request payloads received";
           }
           leaf ike-sa-dpd-request-payloads-sent {
             type int32;
             description "Number of DPD request payloads sent";
           }
           leaf ike-sa-dpd-response-payloads-received {
             type int32;
             description "Number of DPD response payloads received";
           }
           leaf ike-sa-dpd-response-payloads-sent {
             type int32;
             description "Number of DPD response payloads sent";
           }
           leaf ike-sa-dpd-response-payloads-missed {
             type int32;
             description "Number of DPD response payloads missed";
           }
           leaf ike-sa-dpd-response-payloads-maximum-delay {
             type int32;
             description "Worst case delay for the DPD response";
           }
           leaf ike-sa-dpd-response-seq-payloads-missed {
             type int32;
             description "Number of DPD response payloads missed in sequence";
           }
           leaf ike-sa-invalid-spi-notifications-received {
             type int32;
             description "Number of invalid SPI notifications received";
           }
           leaf ike-sa-invalid-spi-notifications-sent {
             type int32;
             description "Number of invalid SPI notifications sent";
           }
         }
         container ike-sa-stats-information {
           container ikev2-ipsec-sa-rekey-stats {
             leaf ikev2-initiator-ipsec-sa-rekey-request-out {
               type int32;
               description "Number of IPsec SA rekey CREATE_CHILD_SA request sent by Initiator";
             }
             leaf ikev2-responder-ipsec-sa-rekey-request-in {
               type int32;
               description "Number of IPsec SA rekey CREATE_CHILD_SA request recv by Responder";
             }
             leaf ikev2-initiator-ipsec-sa-rekey-response-in {
               type int32;
               description "Number of IPsec SA rekey CREATE_CHILD_SA response recv by Initiator";
             }
             leaf ikev2-responder-ipsec-sa-rekey-response-out {
               type int32;
               description "Number of IPsec SA rekey CREATE_CHILD_SA response sent by Responder";
             }
             leaf ikev2-initiator-ipsec-sa-rekey-no-proposal-chosen-in {
               type int32;
               description "Number of IPsec SA rekey NO_PROPSAL_CHOSEN notify recv by Initiator";
             }
             leaf ikev2-responder-ipsec-sa-rekey-no-proposal-chosen-out {
               type int32;
               description "Number of IPsec SA rekey NO_PROPSAL_CHOSEN notify sent by Responder";
             }
             leaf ikev2-initiator-ipsec-sa-rekey-invalid-key-in {
               type int32;
               description "Number of IPsec SA rekey INVALID_KE_PAYLOAD notify recv by Initiator";
             }
             leaf ikev2-responder-ipsec-sa-rekey-invalid-key-out {
               type int32;
               description "Number of IPsec SA rekey INVALID_KE_PAYLOAD notify sent by Responder";
             }
             leaf ikev2-initiator-ipsec-sa-rekey-ts-unacceptable-in {
               type int32;
               description "Number of IPsec SA rekey TS_UNACCEPTABLE notify recv by Initiator";
             }
             leaf ikev2-responder-ipsec-sa-rekey-ts-unacceptable-out {
               type int32;
               description "Number of IPsec SA rekey TS_UNACCEPTABLE notify sent by Responder";
             }
             leaf ikev2-initiator-ipsec-sa-rekey-res-dh-compute-key-fail {
               type int32;
               description "Number of IPsec SA rekey response, DH compute key failed at Initiator";
             }
             leaf ikev2-responder-ipsec-sa-rekey-res-dh-compute-key-fail {
               type int32;
               description "Number of IPsec SA rekey response, DH compute key failed at Responder";
             }
             leaf ikev2-initiator-ipsec-sa-rekey-res-verify-sa-fail {
               type int32;
               description "Number of IPsec SA rekey response, verify of peer SA failed at Initiator";
             }
             leaf ikev2-initiator-ipsec-sa-rekey-res-verify-dh-group-fail {
               type int32;
               description "Number of IPsec SA rekey response, verify of DH group failed at Initiator";
             }
             leaf ikev2-initiator-ipsec-sa-rekey-res-verify-ts-fail {
               type int32;
               description "Number of IPsec SA rekey response, verify of TS failed at Initiator";
             }
           }
         }
         leaf ike-sa-reauthlifetime {
           type string;
           description "Remaining IKE Hard lifetime before re-authentication, in seconds";
         }
         leaf ike-sa-ike-frag {
           type string;
           description "IKE Fragmentation Flag";
         }
         leaf ike-sa-frag-size {
           type int32;
           description "IKE Fragmentation Size";
         }
         leaf ike-sa-routing-instance {
           type string;
           description "Local-gateway routing instance";
         }
         leaf ike-sa-local-gateway-interface {
           type string;
           description "Local gateway  interface";
         }
         leaf ike-ike-id {
           type string;
           description "IKE ID";
         }
         leaf ike-sa-role {
           type string;
           description "Role of our end";
         }
         leaf ike-sa-state {
           type string;
           description "Status of the SA";
         }
         leaf ike-sa-initiator-cookie {
           type string;
           description "IKE SA initiator cookie";
         }
         leaf ike-sa-responder-cookie {
           type string;
           description "IKE SA responder cookie";
         }
         leaf ike-sa-exchange-type {
           type string;
           description "Exchange type";
         }
         leaf ike-sa-authentication-method {
           type string;
         }
         leaf ike-sa-local-address {
           type jt:ipaddr;
           description "Local address";
         }
         leaf ike-sa-local-port {
           type int32;
           description "Local port";
         }
         leaf ike-sa-remote-address {
           type jt:ipaddr;
           description "Remote address";
         }
         leaf ike-sa-remote-port {
           type int32;
           description "Remote port";
         }
         leaf ike-sa-lifetime {
           type string;
           description "Remaining lifetime before expiration, in seconds or kilobytes";
         }
         leaf ike-sa-srg-id {
           type int32;
           description "SRG ID";
         }
         leaf ike-sa-remote-client-info {
           type string;
           description "Remote access client information ";
         }
         leaf ike-trusted-ca-profile-name {
           type string;
           description "Trusted CA profile";
         }
         leaf ike-trusted-ca-group-name {
           type string;
           description "Trusted CA group";
         }
         container ike-ppk-profile {
           leaf ike-ppk-profile-name {
             type string;
             description "Indicates the PPK profile name configured for IKE Peer";
           }
           leaf ike-ppk-profile-optional {
             type string;
             description "Indicates whether PPK profile is configured as optional or not ";
           }
           leaf ike-ppk-profile-state {
             type string;
             description "Indicates whether PPK is used for IKE SA after negotiation";
           }
         }
         container ike-xauth-user-info {
           leaf ike-ike-id {
             type string;
             description "IKE ID";
           }
           leaf ike-xauth-username {
             type string;
             description "AAA username";
           }
           leaf ike-xauth-user-assigned-ip {
             type jt:ipaddr;
             description "IP assigned to AAA user";
           }
           leaf ike-xauth-user-assigned-ipv6 {
             type jt:ipaddr;
             description "IPv6 assigned to AAA user";
           }
         }
         list ike-sa-phase2-information {
           leaf ike-sa-phase2-type {
             type string;
             description "Type of phase 2 negotiation";
           }
           leaf ike-sa-role {
             type string;
             description "Role of our end";
           }
           leaf ike-sa-msg-id {
             type int32;
             description "Message ID of the quick mode negotiation";
           }
           leaf ike-sa-local-address {
             type jt:ipaddr;
             description "Local address";
           }
           leaf ike-sa-local-port {
             type int32;
             description "Local port";
           }
           leaf ike-sa-remote-address {
             type jt:ipaddr;
             description "Remote address";
           }
           leaf ike-sa-remote-port {
             type int32;
             description "Remote port";
           }
           leaf ike-sa-local-id {
             type string;
             description "Local end identity in phase 2";
           }
           leaf ike-sa-remote-id {
             type string;
             description "Remote end identity in phase 2";
           }
           leaf ike-sa-flags {
             type string;
             description "IKE SA flags";
           }
         }
       }
       leaf ike-sa-remote-address {
         type jt:ipaddr;
         description "Remote address";
       }
       leaf ike-sa-index {
         type uint32;
         description "Index";
       }
       leaf ike-gw-name {
         type string;
         description "Gateway Name";
       }
       container ike-sa-location {
         leaf ike-sa-fpc {
           type int32;
           description "FPC number";
         }
         leaf ike-sa-pic {
           type int32;
           description "PIC number";
         }
         leaf ike-sa-kmd-instance {
           type int32;
           description "KMD instance number";
         }
       }
       container ike-sa-advpn-info {
         leaf ike-sa-type {
           type string;
           description "SA Type";
         }
         leaf ike-sa-advpn-local-capability {
           type string;
           description "Shortcut Local Capability";
         }
         leaf ike-sa-advpn-peer-capability {
           type string;
           description "Shortcut Peer Capability";
         }
       }
       container ike-sa-advpn-suggester-shortcut-statistics {
         leaf ike-sa-advpn-shortcut-suggestions-sent {
           type int32;
           description "Number of Shortcut Suggestions sent";
         }
         leaf ike-sa-advpn-shortcut-suggestions-response-accepted {
           type int32;
           description "Number of Responses accepted for Shortcut Suggestions sent";
         }
         leaf ike-sa-advpn-shortcut-suggestions-response-declined {
           type int32;
           description "Number of Responses declined for Shortcut Suggestions sent";
         }
       }
       container ike-sa-advpn-partner-shortcut-statistics {
         leaf ike-sa-advpn-shortcut-suggestions-received {
           type int32;
           description "Number of Shortcut Suggestions received";
         }
         leaf ike-sa-advpn-shortcut-suggestions-accepted {
           type int32;
           description "Number of Shortcut Suggestions accepted";
         }
         leaf ike-sa-advpn-shortcut-suggestions-declined {
           type int32;
           description "Number of Shortcut Suggestions declined";
         }
       }
     }
   }
   grouping ike-active-peers-information-block {
     container ike-active-peers {
       leaf ike-sa-remote-address {
         type jt:ipaddr;
         description "Remote address";
       }
       leaf ike-sa-remote-port {
         type int32;
         description "Remote port";
       }
       leaf ike-ike-id {
         type string;
         description "IKE ID";
       }
       leaf ike-xauth-role {
         type string;
         description "AAA role of server or client";
       }
       leaf ike-xauth-username {
         type string;
         description "AAA username";
       }
       leaf ike-xauth-user-assigned-ip {
         type jt:ipaddr;
         description "IP assigned to AAA user";
       }
       leaf ike-xauth-user-assigned-ipv6 {
         type jt:ipaddr;
         description "IPv6 assigned to AAA user";
       }
     }
     container ike-active-peers-block {
       container ike-peer-stats-information {
         container ikev2-ike-sa-init-exchange-stats {
           leaf ikev2-initiator-ike-sa-init-request-out {
             type int32;
             description "Number of IKE_SA_INIT request messages sent by Initiator";
           }
           leaf ikev2-responder-ike-sa-init-request-in {
             type int32;
             description "Number of IKE_SA_INIT request messages received by Responder";
           }
           leaf ikev2-initiator-ike-sa-init-response-in {
             type int32;
             description "Number of IKE_SA_INIT response messages received by Initiator";
           }
           leaf ikev2-responder-ike-sa-init-response-out {
             type int32;
             description "Number of IKE_SA_INIT response messages sent by Responder";
           }
           leaf ikev2-initiator-ike-sa-init-invalid-ke-payload-in {
             type int32;
             description "Number of IKE_SA_INIT INVALID_KE_PAYLOAD notify recv by Initiator";
           }
           leaf ikev2-responder-ike-sa-init-invalid-ke-payload-out {
             type int32;
             description "Number of IKE_SA_INIT INVALID_KE_PAYLOAD notify sent by Responder";
           }
           leaf ikev2-initiator-ike-sa-init-no-proposal-chosen-in {
             type int32;
             description "Number of IKE_SA_INIT NO_PROPSAL_CHOSEN notify recv by Initiator";
           }
           leaf ikev2-responder-ike-sa-init-no-proposal-chosen-out {
             type int32;
             description "Number of IKE_SA_INIT NO_PROPSAL_CHOSEN notify sent by Responder";
           }
           leaf ikev2-initiator-ike-sa-init-cookie-request-in {
             type int32;
             description "Number of IKE_SA_INIT COOKIE notify request recv by Initiator";
           }
           leaf ikev2-responder-ike-sa-init-cookie-request-out {
             type int32;
             description "Number of IKE_SA_INIT COOKIE notify request sent by Responder";
           }
           leaf ikev2-initiator-ike-sa-init-cookie-response-out {
             type int32;
             description "Number of IKE_SA_INIT COOKIE notify response sent by Initiator";
           }
           leaf ikev2-responder-ike-sa-init-cookie-response-in {
             type int32;
             description "Number of IKE_SA_INIT COOKIE notify response recv by Responder";
           }
           leaf ikev2-initiator-ike-sa-init-res-invalid-ike-spi {
             type int32;
             description "Number of IKE_SA_INIT response with Invalid SPI, recv by Initiator";
           }
           leaf ikev2-responder-ike-sa-init-res-dh-gen-key-fail {
             type int32;
             description "Number of IKE_SA_INIT response, DH gen key failed at Responder";
           }
           leaf ikev2-initiator-ike-sa-init-res-verify-sa-fail {
             type int32;
             description "Number of IKE_SA_INIT response, verify of peer SA failed at Initiator";
           }
           leaf ikev2-responder-ike-sa-init-res-invalid-dh-group-conf {
             type int32;
             description "Number of IKE_SA_INIT response, Invalid DH group configured at Responder";
           }
           leaf ikev2-initiator-ike-sa-init-res-ike-sa-fill-fail {
             type int32;
             description "Number of IKE_SA_INIT response, IKE SA fill operation failed at Initiator";
           }
           leaf ikev2-responder-ike-sa-init-res-get-cas-fail {
             type int32;
             description "Number of IKE_SA_INIT response, get CAs failed at Responder";
           }
           leaf ikev2-initiator-ike-sa-init-res-verify-dh-group-fail {
             type int32;
             description "Number of IKE_SA_INIT response, verification of DH group failed at Initiator";
           }
           leaf ikev2-responder-ike-sa-init-res-get-vid-fail {
             type int32;
             description "Number of IKE_SA_INIT response, get Vendor ID request failed at Responder";
           }
           leaf ikev2-initiator-ike-sa-init-res-dh-compute-key-fail {
             type int32;
             description "Number of IKE_SA_INIT response, DH compute key failed at Initiator";
           }
           leaf ikev2-responder-ike-sa-init-res-dh-compute-key-fail {
             type int32;
             description "Number of IKE_SA_INIT response, DH compute key failed at Responder";
           }
         }
         container ikev2-ike-auth-exchange-stats {
           leaf ikev2-initiator-ike-auth-request-out {
             type int32;
             description "Number of IKE_AUTH request messages sent by Initiator";
           }
           leaf ikev2-responder-ike-auth-request-in {
             type int32;
             description "Number of IKE_AUTH request messages received by Responder";
           }
           leaf ikev2-initiator-ike-auth-response-in {
             type int32;
             description "Number of IKE_AUTH response messages received by Initiator";
           }
           leaf ikev2-responder-ike-auth-response-out {
             type int32;
             description "Number of IKE_AUTH response messages sent by Responder";
           }
           leaf ikev2-initiator-ike-auth-no-proposal-chosen-in {
             type int32;
             description "Number of IKE_AUTH NO_PROPSAL_CHOSEN notify recv by Initiator";
           }
           leaf ikev2-responder-ike-auth-no-proposal-chosen-out {
             type int32;
             description "Number of IKE_AUTH NO_PROPSAL_CHOSEN notify sent by Responder";
           }
           leaf ikev2-initiator-ike-auth-ts-unacceptable-in {
             type int32;
             description "Number of IKE_AUTH TS_UNACCEPTABLE notify recv by Initiator";
           }
           leaf ikev2-responder-ike-auth-ts-unacceptable-out {
             type int32;
             description "Number of IKE_AUTH TS_UNACCEPTABLE notify sent by Responder";
           }
           leaf ikev2-initiator-ike-auth-authentication-failed-in {
             type int32;
             description "Number of IKE_AUTH AUTHENTICATION_FAILED notify recv by Initiator";
           }
           leaf ikev2-responder-ike-auth-authentication-failed-out {
             type int32;
             description "Number of IKE_AUTH AUTHENTICATION_FAILED notify sent by Responder";
           }
         }
         container ikev2-ike-sa-rekey-stats {
           leaf ikev2-initiator-ike-sa-rekey-request-out {
             type int32;
             description "Number of IKE SA rekey CREATE_CHILD_SA request sent by Initiator";
           }
           leaf ikev2-responder-ike-sa-rekey-request-in {
             type int32;
             description "Number of IKE SA rekey CREATE_CHILD_SA request recv by Responder";
           }
           leaf ikev2-initiator-ike-sa-rekey-response-in {
             type int32;
             description "Number of IKE SA rekey CREATE_CHILD_SA response recv by Initiator";
           }
           leaf ikev2-responder-ike-sa-rekey-response-out {
             type int32;
             description "Number of IKE SA rekey CREATE_CHILD_SA response sent by Responder";
           }
           leaf ikev2-initiator-ike-sa-rekey-no-proposal-chosen-in {
             type int32;
             description "Number of IKE SA rekey NO_PROPSAL_CHOSEN notify recv by Initiator";
           }
           leaf ikev2-responder-ike-sa-rekey-no-proposal-chosen-out {
             type int32;
             description "Number of IKE SA rekey NO_PROPSAL_CHOSEN notify sent by Responder";
           }
           leaf ikev2-initiator-ike-sa-rekey-invalid-key-in {
             type int32;
             description "Number of IKE SA rekey INVALID_KE_PAYLOAD notify recv by Initiator";
           }
           leaf ikev2-responder-ike-sa-rekey-invalid-key-out {
             type int32;
             description "Number of IKE SA rekey INVALID_KE_PAYLOAD notify sent by Responder";
           }
           leaf ikev2-initiator-ike-sa-rekey-res-dh-compute-key-fail {
             type int32;
             description "Number of IKE SA rekey response, DH compute key failed at Initiator";
           }
           leaf ikev2-responder-ike-sa-rekey-res-dh-compute-key-fail {
             type int32;
             description "Number of IKE SA rekey response, DH compute key failed at Responder";
           }
           leaf ikev2-initiator-ike-sa-rekey-res-verify-sa-fail {
             type int32;
             description "Number of IKE SA rekey response, verify of peer SA failed at Initiator";
           }
           leaf ikev2-initiator-ike-sa-rekey-res-fill-ike-sa-fail {
             type int32;
             description "Number of IKE SA rekey response, fill IKE SA failed at Initiator";
           }
           leaf ikev2-initiator-ike-sa-rekey-res-verify-dh-group-fail {
             type int32;
             description "Number of IKE SA rekey response, verify of DH group failed at Initiator";
           }
         }
         container ikev2-ipsec-sa-rekey-stats {
           leaf ikev2-initiator-ipsec-sa-rekey-request-out {
             type int32;
             description "Number of IPsec SA rekey CREATE_CHILD_SA request sent by Initiator";
           }
           leaf ikev2-responder-ipsec-sa-rekey-request-in {
             type int32;
             description "Number of IPsec SA rekey CREATE_CHILD_SA request recv by Responder";
           }
           leaf ikev2-initiator-ipsec-sa-rekey-response-in {
             type int32;
             description "Number of IPsec SA rekey CREATE_CHILD_SA response recv by Initiator";
           }
           leaf ikev2-responder-ipsec-sa-rekey-response-out {
             type int32;
             description "Number of IPsec SA rekey CREATE_CHILD_SA response sent by Responder";
           }
           leaf ikev2-initiator-ipsec-sa-rekey-no-proposal-chosen-in {
             type int32;
             description "Number of IPsec SA rekey NO_PROPSAL_CHOSEN notify recv by Initiator";
           }
           leaf ikev2-responder-ipsec-sa-rekey-no-proposal-chosen-out {
             type int32;
             description "Number of IPsec SA rekey NO_PROPSAL_CHOSEN notify sent by Responder";
           }
           leaf ikev2-initiator-ipsec-sa-rekey-invalid-key-in {
             type int32;
             description "Number of IPsec SA rekey INVALID_KE_PAYLOAD notify recv by Initiator";
           }
           leaf ikev2-responder-ipsec-sa-rekey-invalid-key-out {
             type int32;
             description "Number of IPsec SA rekey INVALID_KE_PAYLOAD notify sent by Responder";
           }
           leaf ikev2-initiator-ipsec-sa-rekey-ts-unacceptable-in {
             type int32;
             description "Number of IPsec SA rekey TS_UNACCEPTABLE notify recv by Initiator";
           }
           leaf ikev2-responder-ipsec-sa-rekey-ts-unacceptable-out {
             type int32;
             description "Number of IPsec SA rekey TS_UNACCEPTABLE notify sent by Responder";
           }
           leaf ikev2-initiator-ipsec-sa-rekey-res-dh-compute-key-fail {
             type int32;
             description "Number of IPsec SA rekey response, DH compute key failed at Initiator";
           }
           leaf ikev2-responder-ipsec-sa-rekey-res-dh-compute-key-fail {
             type int32;
             description "Number of IPsec SA rekey response, DH compute key failed at Responder";
           }
           leaf ikev2-initiator-ipsec-sa-rekey-res-verify-sa-fail {
             type int32;
             description "Number of IPsec SA rekey response, verify of peer SA failed at Initiator";
           }
           leaf ikev2-initiator-ipsec-sa-rekey-res-verify-dh-group-fail {
             type int32;
             description "Number of IPsec SA rekey response, verify of DH group failed at Initiator";
           }
           leaf ikev2-initiator-ipsec-sa-rekey-res-verify-ts-fail {
             type int32;
             description "Number of IPsec SA rekey response, verify of TS failed at Initiator";
           }
         }
       }
       leaf ike-sa-remote-address {
         type jt:ipaddr;
         description "Remote address";
       }
       leaf ike-sa-remote-port {
         type int32;
         description "Remote port";
       }
       leaf ike-ike-id {
         type string;
         description "IKE ID";
       }
       leaf ike-xauth-role {
         type string;
         description "AAA role of server or client";
       }
       leaf ike-xauth-username {
         type string;
         description "AAA username";
       }
       container ike-peer-local-information {
         leaf ike-sa-local-gateway-interface {
           type string;
           description "Local gateway  interface";
         }
         leaf ike-sa-routing-instance {
           type string;
           description "Local-gateway routing instance";
         }
         leaf ike-sa-local-address {
           type jt:ipaddr;
           description "Local address";
         }
         leaf ike-sa-local-port {
           type int32;
           description "Local port";
         }
         leaf ike-sa-local-ike-id {
           type string;
         }
       }
       container ike-active-peers {
         leaf ike-xauth-user-assigned-ip {
           type jt:ipaddr;
           description "IP assigned to AAA user";
         }
         leaf ike-xauth-user-assigned-mask {
           type jt:ipaddr;
           description "IP mask assigned to AAA user";
         }
         leaf ike-xauth-user-assigned-dns {
           type jt:ipaddr;
           description "DNS assigned to AAA user";
         }
         leaf ike-xauth-user-assigned-dns2 {
           type jt:ipaddr;
           description "DNS2 assigned to AAA user";
         }
         leaf ike-xauth-user-assigned-wins {
           type jt:ipaddr;
           description "WINS assigned to AAA user";
         }
         leaf ike-xauth-user-assigned-wins2 {
           type jt:ipaddr;
           description "WINS2 assigned to AAA user";
         }
         leaf ike-xauth-user-assigned-ipv6 {
           type jt:ipaddr;
           description "IPv6 assigned to AAA user";
         }
         leaf ike-xauth-user-assigned-v6prefix {
           type uint32;
           description "IPv6 mask assigned to AAA user";
         }
         leaf ike-xauth-user-assigned-v6dns {
           type jt:ipaddr;
           description "Ipv6 DNS assigned to AAA user";
         }
         leaf ike-xauth-user-assigned-v6dns2 {
           type jt:ipaddr;
           description "Ipv6 DNS2 assigned to AAA user";
         }
         leaf ike-user-last-remote-ip {
           type jt:ipaddr;
           description "Remote IP of last vpn connection";
         }
         leaf ike-user-last-remote-port {
           type int32;
           description "Remote port of last vpn connection";
         }
         leaf ike-p1sa-id-list {
           type string;
           description "List of IKE SA indexes";
         }
         leaf ike-peer-ike-sa-negotiated {
           type int32;
           description "Number IKE SA negotiated since the peer connects";
         }
         leaf ike-peer-active-ipsec-sa {
           type int32;
           description "Number IPSec SA active from the peer";
         }
         leaf ike-ipsec-sa-id-list {
           type string;
           description "List of IPSec SA indexes";
         }
         leaf ike-dpd-cfg-mode {
           type string;
           description "DPD config-mode can be either optimized or probe-idle-tunnel";
         }
         leaf ike-dpd-cfg-interval {
           type string;
           description "The time between DPD probe messages";
         }
         leaf ike-dpd-cfg-threshold {
           type string;
           description "Maximum number of DPD retransmissions";
         }
         leaf ike-dpd-cfg-p1sa-index {
           type string;
           description "Index of phase-1 sa";
         }
         leaf ike-dpd-cfg-flags {
           type string;
           description "DPD related Flags(WAITING_FOR_REPLY, WAITING_FOR_P1SA, REMOTE_ACCESS)";
         }
         leaf ike-dpd-stats-req {
           type string;
           description "DPD probe requests sent";
         }
         leaf ike-dpd-stats-resp {
           type string;
           description "DPD probe responses received";
         }
         leaf ike-dpd-stats {
           type string;
           description "DPD statistics";
         }
       }
     }
   }
   grouping security-ike-debug-info-block {
     leaf ike-debug-status {
       type string;
       description "Show current enabled IKE debug information";
     }
     leaf ike-debug-flag {
       type string;
       description "IKE debug flag";
     }
     leaf ike-debug-level {
       type int32;
       description "IKE debug level";
     }
     leaf ike-sa-local-address {
       type jt:ipaddr;
       description "Local address";
     }
     leaf ike-sa-remote-address {
       type jt:ipaddr;
       description "Remote address";
     }
   }
   grouping iked-tunnel-mapping-information-block {
     list iked-tunnel-map {
       leaf gateway-id {
         type int32;
         description "Gateway id";
       }
       leaf gateway-name {
         type string;
         description "Gateway name";
       }
       leaf spu-fpc {
         type int32;
       }
       leaf spu-pic {
         type int32;
       }
       leaf iked-instance {
         type int32;
       }
     }
     list iked-tunnel-map-summary {
       leaf spu-fpc {
         type int32;
       }
       leaf spu-pic {
         type int32;
       }
       leaf spu-load {
         type int32;
       }
     }
   }
   grouping ipsec-security-associations-information-block {
     leaf total-active-tunnels {
       type int32;
       description "Total number of active tunnels";
     }
     leaf total-ipsec-sas {
       type int32;
       description "Total number of IPsec sas";
     }
     container ipsec-security-associations {
       leaf sa-installation-state {
         type string;
         description "SA Installation State in Kernel";
       }
       leaf sa-nego-num {
         type int32;
         description "SA nego num";
       }
       leaf sa-nego-fail {
         type int32;
         description "SA nego fail num";
       }
       leaf sa-del-num {
         type int32;
         description "SA defer delete count";
       }
       leaf-list stats-name {
         type string;
       }
       leaf sa-flag {
         type int32;
         description "SA flags";
       }
       container sa-pair-location {
         leaf sa-pair-fpc {
           type int32;
           description "FPC number";
         }
         leaf sa-pair-pic {
           type int32;
           description "PIC number";
         }
         leaf sa-pair-kmd-instance {
           type int32;
           description "KMD instance number";
         }
       }
       container sa-pair-anchorship {
         leaf sa-pair-anchor-thread {
           type uint32;
           description "Thread anchorship information for SA";
         }
       }
       container sa-ipsec-tunnel-event-list {
       }
       leaf sa-tunnel-event-time {
         type string;
         description "Tunnel event occurred time";
       }
     }
     container ipsec-security-associations-block {
       leaf sa-configuration-type {
         type string;
         description "Type of security association configuration";
       }
       leaf sa-tunnel-dist-key {
         type string;
         description "IPsec tunnel distribution key";
       }
       leaf sa-tunnel-event-description {
         type string;
         description "Tunnel event description";
       }
       leaf sa-tunnel-event-num-times {
         type int32;
         description "Number of times tunnel event occurred";
       }
       container sa-advpn-info {
         leaf sa-type {
           type string;
           description "SA Type";
         }
         leaf sa-negotiation-role {
           type string;
           description "Negotiation Role of our end";
         }
       }
       container sa-df-bit-policy-name {
         leaf sa-df-bit {
           type string;
           description "Fragmentation bit";
         }
         leaf sa-copy-outer-dscp {
           type string;
           description "Copying outer IP Header DSCP & ECN to Inner IP Header";
         }
         leaf sa-bind-interface {
           type string;
           description "VPN bind-interface";
         }
         leaf sa-tunnel-mtu {
           type int32;
           description "MTU of the IPSec Tunnel";
         }
         leaf sa-policy-name {
           type string;
           description "Policy name";
         }
         leaf sa-anchor-interface {
           type string;
           description "VPN Anchor interface";
         }
       }
       container sa-dev-info {
         leaf sa-port {
           type int32;
           description "Port";
         }
         leaf sa-nego-num {
           type int32;
           description "SA nego num";
         }
         leaf sa-nego-fail {
           type int32;
           description "SA nego fail num";
         }
         leaf sa-del-num {
           type int32;
           description "SA defer delete count";
         }
         leaf sa-flag {
           type int32;
           description "SA flags";
         }
         leaf-list stats-name {
           type string;
         }
       }
       container multi-sa-info {
         leaf multi-sa-cfg-sas {
           type int32;
           description "Number of SA configured for negitiation";
         }
         leaf multi-sa-nego-sas {
           type int32;
           description "Number of SAs negitiated with peer";
         }
       }
       container sa-ha-link-encryption {
         leaf sa-ha-link-type {
           type string;
           description "Type of HA Link encryption";
         }
       }
       container sa-anchorship {
         leaf sa-anchor-thread {
           type uint32;
           description "Thread anchorship information for SA";
         }
       }
       list sa-ts-remote-identity {
         leaf sa-ts-protocol {
           type string;
           description "Sa Ts Protocol";
         }
         leaf sa-ts-port {
           type string;
           description "Sa Ts Port";
         }
         leaf sa-ts-ip {
           type string;
           description "Sa Ts IP";
         }
       }
       list sa-ts-local-identity {
         leaf sa-ts-protocol {
           type string;
           description "Sa Ts Protocol";
         }
         leaf sa-ts-port {
           type string;
           description "Sa Ts Port";
         }
         leaf sa-ts-ip {
           type string;
           description "Sa Ts IP";
         }
       }
       container sa-tunnel-dist {
         leaf sa-tunnel-dist-key {
           type string;
           description "IPsec tunnel distribution key";
         }
       }
       container sa-ipsec-tunnel-event {
         leaf sa-tunnel-event-time {
           type string;
           description "Tunnel event occurred time";
         }
         leaf sa-tunnel-event-description {
           type string;
           description "Tunnel event description";
         }
         leaf sa-tunnel-event-num-times {
           type int32;
           description "Number of times tunnel event occurred";
         }
         leaf sa-tunnel-event-repeat-seq-description {
           type string;
           description "Tunnel event repeat sequence description";
         }
       }
       container sa-location {
         leaf sa-fpc {
           type int32;
           description "FPC number";
         }
         leaf sa-pic {
           type int32;
           description "PIC number";
         }
         leaf sa-kmd-instance {
           type int32;
           description "KMD instance number";
         }
       }
       container ipsec-security-associations {
         leaf sa-direction {
           type string;
           description "Direction of the security association";
         }
         leaf sa-tunnel-index {
           type int32;
           description "Tunnel index";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-vpn-monitoring-state {
           type string;
           description "VPN Monitoring State";
         }
         leaf sa-virtual-system {
           type string;
           description "Virtual System";
         }
         leaf sa-port {
           type int32;
           description "Port";
         }
         leaf sa-remote-gateway {
           type jt:ipaddr;
           description "Remote gateway address";
         }
         leaf sa-installation-state {
           type string;
           description "SA Installation State in Kernel";
         }
         leaf sa-nego-num {
           type int32;
           description "SA nego num";
         }
         leaf sa-nego-fail {
           type int32;
           description "SA nego fail num";
         }
         leaf sa-del-num {
           type int32;
           description "SA defer delete count";
         }
         leaf-list stats-name {
           type string;
         }
         leaf sa-flag {
           type int32;
           description "SA flags";
         }
         container sa-pair-location {
           leaf sa-pair-fpc {
             type int32;
             description "FPC number";
           }
           leaf sa-pair-pic {
             type int32;
             description "PIC number";
           }
           leaf sa-pair-kmd-instance {
             type int32;
             description "KMD instance number";
           }
         }
         container sa-pair-anchorship {
           leaf sa-pair-anchor-thread {
             type uint32;
             description "Thread anchorship information for SA";
           }
         }
         container sa-ipsec-tunnel-event-list {
         }
         leaf sa-tunnel-event-time {
           type string;
           description "Tunnel event occurred time";
         }
         leaf sa-aux-spi {
           type string;
           description "Auxiliary Security Parameter Index";
         }
         leaf sa-mode {
           type string;
           description "Mode of the security association";
         }
         leaf sa-type {
           type string;
           description "SA Type";
         }
         leaf sa-state {
           type string;
           description "Status of the SA";
         }
         leaf sa-vpn-monitoring-mode {
           type string;
           description "VPN Monitoring Mode";
         }
         leaf sa-vpn-monitoring-interval {
           type int32;
           description "VPN Monitoring Interval";
         }
         leaf sa-vpn-monitoring-threshold {
           type int32;
           description "VPN Monitoring Threshold";
         }
         leaf sa-authentication-algorithm {
           type string;
           description "Authentication algorithm";
         }
         leaf sa-encryption-algorithm {
           type string;
           description "Encryption algorithm";
         }
         leaf sa-soft-lifetime {
           type string;
           description "Remaining lifetime, in seconds or kilobytes, before soft lifetime expires";
         }
         leaf sa-anti-replay-service {
           type string;
           description "Anti-replay service";
         }
         leaf sa-replay-window-size {
           type int32;
           description "Replay window size";
         }
         leaf sa-extended-seq-number {
           type string;
           description "Extended-Sequnce-Number";
         }
         leaf sa-fc-name {
           type int32;
           description "COS Forward class Name";
         }
         leaf sa-tunnel-establishment {
           type string;
           description "IPsec Establish tunnels option";
         }
         leaf sa-ike-index {
           type int32;
           description "IKE SA index";
         }
       }
       leaf sa-tunnel-event {
         type string;
         description "Tunnel event description";
       }
       leaf sa-tunnel-index {
         type int32;
         description "Tunnel index";
       }
       leaf sa-virtual-system {
         type string;
         description "Virtual System";
       }
       leaf sa-vpn-name {
         type string;
         description "VPN Name";
       }
       leaf sa-local-gateway {
         type jt:ipaddr;
         description "Local gateway address";
       }
       leaf sa-remote-gateway {
         type jt:ipaddr;
         description "Remote gateway address";
       }
       leaf sa-traffic-selector-name {
         type string;
         description "Traffic Selector Name";
       }
       leaf sa-local-identity {
         type string;
         description "Local identity information";
       }
       leaf sa-remote-identity {
         type string;
         description "Remote identity information";
       }
       leaf sa-ts-type {
         type string;
       }
       leaf sa-ike-version {
         type string;
         description "IKE version number used in negotiation";
       }
       leaf sa-is-quantum-secured {
         type string;
         description "Quantum security state of the SA: Indicates whether the IPsec SAs are quantum-secured or not";
       }
       leaf sa-pfs-group {
         type string;
         description "PFS group";
       }
       leaf sa-srg-id {
         type int32;
         description "SRG ID";
       }
       leaf sa-passive-mode-tunneling {
         type string;
         description "Passive mode tunneling";
       }
       leaf sa-bypass-traffic-selector-match {
         type string;
         description "Bypass traffic selector match lookup for passive mode tunnel";
       }
       leaf iked-svc-set-name {
         type string;
         description "Name of the service set";
       }
       container sa-ipsec-tunnel-events {
         leaf sa-tunnel-event-time {
           type string;
           description "Tunnel event occurred time";
         }
         leaf sa-tunnel-event {
           type string;
           description "Tunnel event description";
         }
         leaf sa-tunnel-event-num-times {
           type int32;
           description "Number of times tunnel event occurred";
         }
       }
     }
     container ipsec-gvpn-security-associations-block {
       leaf sa-configuration-type {
         type string;
         description "Type of security association configuration";
       }
       container ipsec-gvpn-sa-stats {
         leaf-list ipsec-sa-stats {
           type string;
           description "IPsec SA stats";
         }
       }
       container ipsec-security-associations {
         leaf sa-direction {
           type string;
           description "Direction of the security association";
         }
         leaf sa-tunnel-index {
           type int32;
           description "Tunnel index";
         }
         leaf sa-gvpn-server {
           type string;
           description "Group VPN Server Address";
         }
         leaf sa-port {
           type int32;
           description "Port";
         }
         leaf sa-protocol {
           type string;
           description "IPSec security protocol";
         }
         leaf sa-esp-encryption-algorithm {
           type string;
           description "ESP Encryption Algorithm";
         }
         leaf sa-hmac-algorithm {
           type string;
           description "HMAC Authentication Algorithm";
         }
         leaf sa-spi {
           type string;
           description "Security Parameter Index";
         }
         leaf sa-hard-lifetime {
           type string;
           description "Remaining lifetime, in seconds or kilobytes, before hard lifetime expires";
         }
         leaf sa-lifesize-remaining {
           type string;
           description "Lifetime Remaining in Kilo Bytes";
         }
         leaf sa-gvpn-groupid {
           type int32;
           description "Group VPN Group Id";
         }
         leaf sa-virtual-system {
           type string;
           description "Virtual System";
         }
         leaf sa-installation-state {
           type string;
           description "SA Installation State in Kernel";
         }
         leaf sa-nego-num {
           type int32;
           description "SA nego num";
         }
         leaf sa-nego-fail {
           type int32;
           description "SA nego fail num";
         }
         leaf sa-del-num {
           type int32;
           description "SA defer delete count";
         }
         leaf-list stats-name {
           type string;
         }
         leaf sa-flag {
           type int32;
           description "SA flags";
         }
         container sa-pair-location {
           leaf sa-pair-fpc {
             type int32;
             description "FPC number";
           }
           leaf sa-pair-pic {
             type int32;
             description "PIC number";
           }
           leaf sa-pair-kmd-instance {
             type int32;
             description "KMD instance number";
           }
         }
         container sa-pair-anchorship {
           leaf sa-pair-anchor-thread {
             type uint32;
             description "Thread anchorship information for SA";
           }
         }
         container sa-ipsec-tunnel-event-list {
         }
         leaf sa-tunnel-event-time {
           type string;
           description "Tunnel event occurred time";
         }
         leaf sa-aux-spi {
           type string;
           description "Auxiliary Security Parameter Index";
         }
         leaf sa-mode {
           type string;
           description "Mode of the security association";
         }
         leaf sa-type {
           type string;
           description "SA Type";
         }
         leaf sa-state {
           type string;
           description "Status of the SA";
         }
         leaf sa-soft-lifetime {
           type string;
           description "Remaining lifetime, in seconds or kilobytes, before soft lifetime expires";
         }
         leaf sa-activate-lifetime {
           type string;
           description "Activate time";
         }
         leaf sa-anti-replay-service {
           type string;
           description "Anti-replay service";
         }
       }
       container sa-child-tunnel-id-policy {
         leaf sa-tunnel-id {
           type int32;
           description "Tunnel id";
         }
         container sa-child-policy-list {
           leaf sa-policy-source-prefix {
             type string;
             description "Group VPN child SA policy source prefix";
           }
           leaf sa-policy-dest-prefix {
             type string;
             description "Group VPN child SA policy destination prefix";
           }
         }
       }
       leaf sa-virtual-system {
         type string;
         description "Virtual System";
       }
       leaf sa-vpn-name {
         type string;
         description "VPN Name";
       }
       leaf sa-local-gateway {
         type jt:ipaddr;
         description "Local gateway address";
       }
       leaf sa-remote-gateway {
         type jt:ipaddr;
         description "Remote gateway address";
       }
       leaf sa-local-identity {
         type string;
         description "Local identity information";
       }
       leaf sa-remote-identity {
         type string;
         description "Remote identity information";
       }
       leaf sa-gvpn-groupid {
         type int32;
         description "Group VPN Group Id";
       }
       leaf sa-match-dir {
         type string;
         description "Group VPN rule match direction";
       }
       leaf sa-tunnel-mtu {
         type int32;
         description "MTU of the IPSec Tunnel";
       }
       leaf sa-gvpn-vrf-name {
         type string;
         description "SA routing instance name";
       }
       leaf sa-recovery-probe {
         type int32;
         description "SA recover probe enabled";
       }
       container sa-df-bit-policy-name {
         leaf sa-df-bit {
           type string;
           description "Fragmentation bit";
         }
       }
       container ipsec-gvpn-sa-flags {
         leaf sa-rekey-needed {
           type string;
           description "SA rekey needed";
         }
       }
       container sa-location {
         leaf sa-fpc {
           type int32;
           description "FPC number";
         }
         leaf sa-pic {
           type int32;
           description "PIC number";
         }
         leaf sa-kmd-instance {
           type int32;
           description "KMD instance number";
         }
       }
       leaf sa-gvpn-forward-policy-mismatch {
         type string;
         description "State of fowarding policy mismatch packets";
       }
     }
   }
   grouping gvpn-policy-information-block {
     leaf sa-vpn-name {
       type string;
       description "VPN Name";
     }
     leaf sa-gvpn-groupid {
       type int32;
       description "Group VPN Group Id";
     }
     leaf sa-tunnel-id {
       type int32;
       description "Tunnel id";
     }
     leaf gvpn-policy-type {
       type string;
       description "Group VPN policy type";
     }
     leaf sa-policy-source-prefix {
       type string;
       description "Group VPN child SA policy source prefix";
     }
     leaf sa-policy-dest-prefix {
       type string;
       description "Group VPN child SA policy destination prefix";
     }
     container ipsec-gvpn-sa-zone-pair {
       leaf from-zone {
         type string;
         description "From-zone name";
       }
       leaf to-zone {
         type string;
         description "To-zone name";
       }
     }
   }
   grouping security-group-vpn-server-stats-block {
     leaf group-vpn-group-name {
       type string;
       description "Group Name";
     }
     leaf group-vpn-group-id {
       type int32;
       description "Group Id";
     }
     leaf-list group-vpn-stats {
       type string;
       description "Statistics";
     }
     container server-stats {
       container group-vpn-stats {
         leaf group-vpn-pull-succeeded {
           type int32;
           description "Pull Succeeded";
         }
         leaf group-vpn-pull-failed {
           type int32;
           description "Pull Failed";
         }
         leaf group-vpn-pull-exceed-member-threshold {
           type int32;
           description "Pull Exceed Member Threshold";
         }
         leaf group-vpn-push-sent {
           type int32;
           description "Push Sent";
         }
         leaf group-vpn-push-acknowledged {
           type int32;
           description "Push Acknowledged";
         }
         leaf group-vpn-push-unacknowledged {
           type int32;
           description "Push Unacknowledged";
         }
       }
     }
   }
   grouping internal-sa-information-block {
     leaf internal-sa-status {
       type string;
       description "Internal SA Status";
     }
   }
   grouping idp-application-system-cache-information-block {
     list idp-application-system-cache-pic {
       leaf pic-name {
         type string;
         description "Pic name";
       }
       list idp-application-system-cache-statistics {
         leaf virtual-system-identifier {
           type uint32;
           description "Virtual system identifier";
         }
         leaf ipv6-address {
           type jt:ipv6addr;
           description "IPV6 address";
         }
         leaf port {
           type uint32;
           description "Application identification port";
         }
         leaf protocol {
           type string;
           description "IP protocol";
         }
         leaf idp-service {
           type string;
           description "IDP service type";
         }
         leaf idp-application {
           type string;
           description "IDP application type";
         }
         leaf ip-address {
           type jt:ipaddr;
           description "IP address";
         }
       }
     }
   }
   grouping idp-version-information-block {
     leaf idp-policy-name {
       type string;
       description "IDP active policy name";
     }
     leaf idp-detector-version {
       type string;
       description "IDP running detector version";
     }
     leaf idp-sigdb-version {
       type string;
       description "IDP compiled signature database version";
     }
   }
   grouping idp-policy-commit-status-block {
     leaf policy-commit-status-detail {
       type string;
       description "Policy commit status output";
     }
   }
   grouping idp-security-package-proxy-profile-block {
     leaf security-package-proxy-profile-name {
       type string;
       description "Security package proxy profile";
     }
     leaf proxy-protocol {
       type string;
       description "Protocol used for download request";
     }
     leaf proxy-host {
       type string;
       description "Ip address of proxy server";
     }
     leaf proxy-port {
       type uint32;
       description "Port of proxy server";
     }
   }
   grouping idp-security-package-information-block {
     leaf security-package-version {
       type string;
       description "Security package version";
     }
     leaf detector-version {
       type string;
       description "Detector version";
     }
     leaf policy-template-version {
       type string;
       description "Policy template version";
     }
     leaf security-package-rollback-version {
       type string;
       description "Security package version of rollback";
     }
     leaf security-package-rollback-detector-version {
       type string;
       description "Detector version of rollback";
     }
     leaf security-package-validation-failed-version {
       type string;
       description "Last known security-package-version which failed in data plane validation";
     }
     leaf security-package-validation-failed-detector-version {
       type string;
       description "Last known security-package-detector-version which failed in data plane validation";
     }
   }
   grouping idp-jist-package-information-block {
     leaf jist-package-version {
       type string;
       description "JIST package version";
     }
   }
   grouping idp-recent-security-package-information-block {
     leaf-list recent-security-package-version {
       type string;
       description "Security package last-known-good version";
     }
   }
   grouping idp-memory-information-block {
     list idp-memory-per-spu-information {
       leaf pic-name {
         type string;
         description "Pic name";
       }
       leaf total-idp-data-plane-memory-in-mb {
         type uint32;
       }
       leaf total-idp-data-plane-memory-used-in-mb {
         type uint32;
       }
       leaf total-idp-data-plane-memory-used-in-kb {
         type uint32;
       }
       leaf total-idp-data-plane-memory-used-in-percentage {
         type string;
       }
       leaf total-idp-data-plane-memory-available-in-mb {
         type uint32;
       }
       leaf total-idp-data-plane-memory-available-in-kb {
         type uint32;
       }
       leaf total-idp-data-plane-memory-available-in-percentage {
         type string;
       }
     }
   }
   grouping idp-subscriber-policy-list-block {
     list idp-subscriber-policy-per-pic-information {
       description "IDP  subscriber policy per pic information";
       leaf pic-name {
         type string;
         description "Pic name";
       }
       list idp-policy-list-entry {
         description "Information about policy list entry";
         leaf id {
           type uint32;
           description "Process id";
         }
         leaf policy-name {
           type string;
           description "Name of the policy";
         }
         leaf sessions {
           type uint32;
           description "Number of session";
         }
         leaf memory {
           type uint32;
           description "Memory";
         }
         leaf idp-detector-versions {
           type string;
           description "IDP detector version";
         }
       }
     }
   }
   grouping idp-status-information-block {
     container idp-uptime {
       leaf idp-status {
         type string;
       }
       leaf date-time {
         type string;
         description "IDP peak packets(or Kbits) per second";
       }
       leaf time-length {
         type string;
       }
     }
     container idp-packets-per-second-information {
       leaf idp-packets-per-second {
         type uint32;
       }
       leaf idp-peak-packets-per-second {
         type uint32;
       }
       leaf date-time {
         type string;
         description "IDP peak packets(or Kbits) per second";
       }
     }
     container idp-kbits-per-second-information {
       leaf idp-kbits-per-second {
         type uint32;
       }
       leaf idp-peak-kbits-per-second {
         type uint32;
       }
       leaf date-time {
         type string;
         description "IDP peak packets(or Kbits) per second";
       }
     }
     container idp-latency {
       leaf minimum-latency-time {
         type string;
       }
       leaf maximum-latency-time {
         type string;
       }
       leaf average-latency-time {
         type string;
       }
     }
     container idp-packet-count {
       leaf icmp-packet-count {
         type uint32;
       }
       leaf tcp-packet-count {
         type uint32;
       }
       leaf udp-packet-count {
         type uint32;
       }
       leaf other-packet-count {
         type uint32;
       }
     }
     container idp-icmp-flow-count {
       leaf current-icmp-flow-count {
         type uint32;
       }
       leaf maximum-icmp-flow-count {
         type uint32;
       }
       leaf date-time {
         type string;
         description "IDP peak packets(or Kbits) per second";
       }
       leaf maximum-icmp-flow-count-time {
         type string;
       }
     }
     container idp-tcp-flow-count {
       leaf current-tcp-flow-count {
         type uint32;
       }
       leaf maximum-tcp-flow-count {
         type uint32;
       }
       leaf date-time {
         type string;
         description "IDP peak packets(or Kbits) per second";
       }
       leaf maximum-tcp-flow-count-time {
         type string;
       }
     }
     container idp-udp-flow-count {
       leaf current-udp-flow-count {
         type uint32;
       }
       leaf maximum-udp-flow-count {
         type uint32;
       }
       leaf date-time {
         type string;
         description "IDP peak packets(or Kbits) per second";
       }
       leaf maximum-udp-flow-count-time {
         type string;
       }
     }
     container idp-other-flow-count {
       leaf current-other-flow-count {
         type uint32;
       }
       leaf maximum-other-flow-count {
         type uint32;
       }
       leaf date-time {
         type string;
         description "IDP peak packets(or Kbits) per second";
       }
       leaf maximum-other-flow-count-time {
         type string;
       }
     }
     container idp-session-count {
       leaf icmp-session-count {
         type uint32;
       }
       leaf tcp-session-count {
         type uint32;
       }
       leaf udp-session-count {
         type uint32;
       }
       leaf other-session-count {
         type uint32;
       }
     }
     container idp-ssl-session-information {
       leaf ssl-session-count {
         type uint32;
       }
     }
     container idp-intel-inspect-mode-information {
       leaf pic-name {
         type string;
         description "Pic name";
       }
       leaf intel-inspect-mode {
         type string;
       }
     }
     container idp-intelligent-offload-information {
       leaf idp-intelligent-offload-status {
         type string;
       }
     }
   }
   grouping idp-detail-status-information-block {
     list idp-status-detail-per-spu-information {
       description "IDP status per PIC information";
       container idp-spu-uptime {
         leaf pic-name {
           type string;
           description "Pic name";
         }
         leaf idp-status {
           type string;
         }
         leaf date-time {
           type string;
           description "IDP peak packets(or Kbits) per second";
         }
         leaf time-length {
           type string;
         }
       }
       container idp-packets-spu-per-second-information {
         leaf idp-packets-per-second {
           type uint32;
         }
         leaf idp-peak-packets-per-second {
           type uint32;
         }
         leaf date-time {
           type string;
           description "IDP peak packets(or Kbits) per second";
         }
       }
       container idp-kbits-spu-per-second-information {
         leaf idp-kbits-per-second {
           type uint32;
         }
         leaf idp-peak-kbits-per-second {
           type uint32;
         }
         leaf date-time {
           type string;
           description "IDP peak packets(or Kbits) per second";
         }
       }
       container idp-spu-latency {
         leaf minimum-latency-time {
           type string;
         }
         leaf maximum-latency-time {
           type string;
         }
         leaf average-latency-time {
           type string;
         }
       }
       container idp-spu-packet-count {
         leaf icmp-packet-count {
           type uint32;
         }
         leaf tcp-packet-count {
           type uint32;
         }
         leaf udp-packet-count {
           type uint32;
         }
         leaf other-packet-count {
           type uint32;
         }
       }
       container idp-spu-icmp-flow-count {
         leaf current-icmp-flow-count {
           type uint32;
         }
         leaf maximum-icmp-flow-count {
           type uint32;
         }
         leaf date-time {
           type string;
           description "IDP peak packets(or Kbits) per second";
         }
         leaf maximum-icmp-flow-count-time {
           type string;
         }
       }
       container idp-spu-tcp-flow-count {
         leaf current-tcp-flow-count {
           type uint32;
         }
         leaf maximum-tcp-flow-count {
           type uint32;
         }
         leaf date-time {
           type string;
           description "IDP peak packets(or Kbits) per second";
         }
         leaf maximum-tcp-flow-count-time {
           type string;
         }
       }
       container idp-spu-udp-flow-count {
         leaf current-udp-flow-count {
           type uint32;
         }
         leaf maximum-udp-flow-count {
           type uint32;
         }
         leaf date-time {
           type string;
           description "IDP peak packets(or Kbits) per second";
         }
         leaf maximum-udp-flow-count-time {
           type string;
         }
       }
       container idp-spu-other-flow-count {
         leaf current-other-flow-count {
           type uint32;
         }
         leaf maximum-other-flow-count {
           type uint32;
         }
         leaf date-time {
           type string;
           description "IDP peak packets(or Kbits) per second";
         }
         leaf maximum-other-flow-count-time {
           type string;
         }
       }
       container idp-spu-session-count {
         leaf icmp-session-count {
           type uint32;
         }
         leaf tcp-session-count {
           type uint32;
         }
         leaf udp-session-count {
           type uint32;
         }
         leaf other-session-count {
           type uint32;
         }
       }
       container idp-spu-ssl-session-information {
         leaf ssl-session-count {
           type uint32;
         }
       }
     }
   }
   grouping idp-predefined-attack-groups-block {
     list idp-attack-groups {
       leaf name {
         type string;
         description "Name of this component";
       }
     }
   }
   grouping idp-predefined-attacks-block {
     list idp-attacks-list {
       leaf name {
         type string;
         description "Name of this component";
       }
     }
   }
   grouping idp-counter-information-block {
     container idp-counter-system-name {
       leaf idp-logical-system {
         type string;
       }
       leaf idp-tenant {
         type string;
       }
     }
     list idp-counter-statistics {
       leaf name {
         type string;
         description "Name of this component";
       }
       leaf value {
         type uint32;
         description "Value of this entity";
       }
     }
   }
   grouping idp-attack-context-information-block {
     list idp-attack-context-statistics {
       leaf attack-context-name {
         type string;
         description "Attack Context Name";
       }
       leaf attack-context-hits {
         type string;
         description "Attack Context Hits";
       }
       leaf attack-context-value {
         type string;
         description "Attack Context Data";
       }
     }
   }
   grouping idp-attack-deprecated-list-information-block {
     leaf idp-attack-deprecated-list {
       type string;
     }
   }
   grouping idp-policy-deprecated-attack-information-block {
     leaf idp-policy-deprecated-attack {
       type string;
     }
   }
   grouping idp-all-policy-deprecated-attack-information-block {
     list idp-all-policy-deprecated-attack {
       leaf idp-policy-name {
         type string;
         description "IDP active policy name";
       }
       container idp-attack-name {
         leaf attack-name {
           type string;
           description "IDP Attack name";
         }
       }
     }
   }
   grouping idp-attack-description-information-block {
     leaf idp-attack-description {
       type string;
       description "Description of attack";
     }
   }
   grouping idp-attack-detail-information-block {
     leaf idp-attack-detail-name {
       type string;
       description "Display name of attack";
     }
     leaf idp-attack-detail-severity {
       type string;
       description "Severity of attack";
     }
     leaf idp-attack-detail-category {
       type string;
       description "Category of attack";
     }
     leaf idp-attack-detail-recommended {
       type string;
       description "Recommended field of attack";
     }
     leaf idp-attack-detail-recoact {
       type string;
       description "Recommended action for attack";
     }
     leaf idp-attack-detail-type {
       type string;
       description "Type of attack";
     }
     leaf idp-attack-detail-direction {
       type string;
       description "Direction of attack";
     }
     leaf idp-attack-detail-falsepos {
       type string;
       description "False Positives for the attack";
     }
     leaf idp-attack-detail-service {
       type string;
       description "Service of the attack";
     }
     leaf idp-attack-detail-transaction {
       type string;
       description "Transaction of the attack";
     }
     leaf idp-attack-detail-expression {
       type string;
       description "Expression of the attack";
     }
     leaf idp-attack-detail-expression-pcre {
       type string;
       description "PCRE Expression of the attack";
     }
     leaf idp-attack-detail-order {
       type string;
       description "Order of the attack";
     }
     leaf idp-attack-detail-reset {
       type string;
       description "Reset of the attack";
     }
     leaf idp-attack-detail-shellcode {
       type string;
       description "Shellcode of the attack";
     }
     leaf idp-attack-detail-flow {
       type string;
       description "Flow of the attack";
     }
     leaf idp-attack-detail-context {
       type string;
       description "Context of the attack";
     }
     leaf idp-attack-detail-negate {
       type string;
       description "Negate of the attack";
     }
     leaf idp-attack-detail-pattern {
       type string;
       description "Pattern of the attack";
     }
     leaf idp-attack-detail-pattern-pcre {
       type string;
       description "PCRE pattern of the attack";
     }
     leaf idp-attack-detail-regex {
       type string;
       description "Regex of the attack";
     }
     leaf idp-attack-detail-scope {
       type string;
       description "Scope of the attack";
     }
     leaf idp-attack-detail-count {
       type string;
       description "Count of the attack";
     }
     leaf idp-attack-detail-test {
       type string;
       description "Test of the attack";
     }
     leaf idp-attack-detail-value {
       type string;
       description "Value of the attack";
     }
     leaf idp-attack-detail-hidden {
       type string;
       description "Hidden flag of the attack";
     }
     leaf idp-attack-detail-expression-hs {
       type string;
       description "Hyperscan expression of the attack";
     }
     leaf idp-attack-detail-pattern-hs {
       type string;
       description "Hyperscan pattern of the attack";
     }
     leaf idp-attack-detail-regex-hs {
       type string;
       description "Hyperscan regex of the attack";
     }
     container idp-attack-detail-timebinding {
       description "TimeBinding of the attack";
       leaf idp-attack-detail-timebinding-scope {
         type string;
         description "Display attack detail timebinding scope";
       }
       leaf idp-attack-detail-timebinding-count {
         type string;
         description "Display attack detail timebinding count";
       }
     }
     list idp-chain-attack-members-detail-information {
       leaf idp-chain-attack-members-name {
         type string;
         description "Display chain attack member name of attack";
       }
       leaf idp-chain-attack-members-type {
         type string;
         description "Display chain attack member type of attack";
       }
       leaf idp-chain-attack-members-direction {
         type string;
         description "Display chain attack member direction of attack";
       }
       leaf idp-chain-attack-members-flow {
         type string;
         description "Display chain attack member flow of attack";
       }
       leaf idp-chain-attack-members-shellcode {
         type string;
         description "Display chain attack member shellcode of attack";
       }
       leaf idp-chain-attack-members-context {
         type string;
         description "Display chain attack member context of attack";
       }
       leaf idp-chain-attack-members-negate {
         type string;
         description "Display chain attack member negate of attack";
       }
       leaf idp-chain-attack-members-hidden {
         type string;
         description "Hidden flag of the attack members";
       }
       leaf idp-chain-attack-members-pattern {
         type string;
         description "Display chain attack member pattern of attack";
       }
       leaf idp-chain-attack-members-pattern-pcre {
         type string;
         description "Display chain attack member pcre pattern of attack";
       }
       leaf idp-chain-attack-members-regex {
         type string;
         description "Display chain attack member regex of attack";
       }
       leaf idp-chain-attack-members-test {
         type string;
         description "Test of the attack members";
       }
       leaf idp-chain-attack-members-value {
         type string;
         description "Value of the attack members";
       }
     }
   }
   grouping idp-attack-group-entry-detail-information-block {
     leaf idp-attack-group-entry-detail-total {
       type string;
     }
     container idp-attack-group-entry-detail-title {
       description "Entry title";
       leaf idp-attack-group-entry-detail-title-value {
         type int32;
         description "Entry title value";
       }
       leaf idp-attack-group-entry-detail-name {
         type string;
       }
       leaf idp-attack-group-entry-detail-category {
         type string;
       }
       leaf idp-attack-group-entry-detail-severity {
         type string;
       }
       leaf idp-attack-group-entry-detail-false-positive {
         type string;
       }
       leaf idp-attack-group-entry-detail-service {
         type string;
       }
       leaf idp-attack-group-entry-detail-cvss-score {
         type string;
       }
       leaf idp-attack-group-entry-detail-age {
         type int32;
       }
       leaf idp-attack-group-entry-detail-file-type {
         type string;
       }
       leaf idp-attack-group-entry-detail-vulnerability-type {
         type string;
       }
       leaf idp-attack-group-entry-detail-attack-type {
         type string;
       }
       leaf idp-attack-group-entry-detail-direction {
         type string;
       }
       leaf idp-attack-group-entry-detail-performance {
         type string;
       }
       leaf idp-attack-group-entry-detail-type-attack {
         type string;
       }
       leaf idp-attack-group-entry-detail-recommended {
         type string;
       }
       leaf idp-attack-group-entry-detail-group-type {
         type string;
       }
       leaf idp-attack-group-entry-detail-attack-id {
         type int32;
       }
       leaf idp-attack-group-entry-detail-recommended-action {
         type string;
       }
       leaf idp-attack-group-entry-detail-cve-id {
         type string;
       }
       leaf idp-attack-group-entry-detail-certificate {
         type string;
       }
       leaf idp-attack-group-entry-detail-bug-id {
         type string;
       }
     }
   }
   grouping idp-attack-group-entry-filters-information-block {
     leaf idp-attack-group-entry-filters-total {
       type string;
     }
     container idp-attack-group-entry-filters-title {
       description "Entry title";
       leaf idp-attack-group-entry-filters-title-value {
         type int32;
         description "Entry title value";
       }
       leaf idp-attack-group-entry-filters-name {
         type string;
       }
       leaf idp-attack-group-entry-filters-category {
         type string;
       }
       leaf idp-attack-group-entry-filters-severity {
         type string;
       }
       leaf idp-attack-group-entry-filters-false-positive {
         type string;
       }
       leaf idp-attack-group-entry-filters-service {
         type string;
       }
       leaf idp-attack-group-entry-filters-cvss-score {
         type string;
       }
       leaf idp-attack-group-entry-filters-age {
         type int32;
       }
       leaf idp-attack-group-entry-filters-file-type {
         type string;
       }
       leaf idp-attack-group-entry-filters-vulnerability-type {
         type string;
       }
       leaf idp-attack-group-entry-filters-attack-type {
         type string;
       }
       leaf idp-attack-group-entry-filters-direction {
         type string;
       }
       leaf idp-attack-group-entry-filters-performance {
         type string;
       }
       leaf idp-attack-group-entry-filters-type-attack {
         type string;
       }
       leaf idp-attack-group-entry-filters-recommended {
         type string;
       }
       leaf idp-attack-group-entry-filters-group-type {
         type string;
       }
       leaf idp-attack-group-entry-filters-attack-id {
         type int32;
       }
       leaf idp-attack-group-entry-filters-recommended-action {
         type string;
       }
       leaf idp-attack-group-entry-filters-cve-id {
         type string;
       }
       leaf idp-attack-group-entry-filters-certificate {
         type string;
       }
       leaf idp-attack-group-entry-filters-bug-id {
         type string;
       }
     }
   }
   grouping idp-group-attacklist-information-block {
     leaf idp-group-attack-list-entry-title {
       type string;
     }
     leaf idp-group-attack-list-entry {
       type string;
     }
     leaf idp-group-attack-list-rulebaseips-entry {
       type string;
     }
     leaf idp-group-attack-list-rulebaseexempt-entry {
       type string;
     }
   }
   grouping idp-group-forattack-information-block {
     leaf idp-group-for-attack-entry {
       type string;
     }
   }
   grouping idp-attack-type-anomaly-test-service-block {
     container idp-attack-type-anomaly-service-test-title {
       description "Anomaly Error Titles";
       leaf idp-attack-type-anomaly-service-test-title-value {
         type string;
       }
       leaf idp-attack-type-anomaly-service-name {
         type string;
       }
     }
     container idp-attack-type-anomaly-details {
       description "Anomaly Deatils";
       leaf idp-attack-type-anomaly-service-test {
         type string;
       }
       leaf idp-attack-type-anomaly-service-description {
         type string;
       }
     }
   }
   grouping get-idp-ssl-session-cache-information-block {
     leaf idp-ssl-session-cache-count {
       type uint32;
       description "Number of SSL session cache entries";
     }
     list idp-ssl-session-cache-entry {
       description "Information about SSL session cache entry";
       leaf ssl-session-identifier {
         type string;
         description "SSL Session Identifier";
       }
     }
   }
   grouping idp-ssl-key-information-block {
     leaf idp-ssl-key-count {
       type uint32;
       description "Number of SSL keys";
     }
     list idp-ssl-per-key-information {
       leaf key-name {
         type string;
         description "SSL server private key name";
       }
       leaf destination-address {
         type jt:ipaddr;
         description "Destination address";
       }
     }
     list idp-ssl-port-per-key-information {
       leaf key-name {
         type string;
         description "SSL server private key name";
       }
       leaf destination-address {
         type jt:ipaddr;
         description "Destination address";
       }
       leaf destination-port {
         type int32;
         description "Destination port";
       }
     }
   }
   grouping idp-lsys-policy-association-block {
     list idp-lsys-policy-association-entry {
       leaf logical-system-name {
         type string;
         description "Logical system name";
       }
       leaf idp-policy-name {
         type string;
         description "IDP active policy name";
       }
     }
   }
   grouping eedebug-all-action-profile-block {
     leaf filter-name {
       type string;
     }
     leaf eedebug-action-profile-name {
       type string;
     }
     leaf eedebug-action-profile {
       type string;
     }
     leaf filter-index {
       type uint32;
     }
   }
   grouping eedebug-all-events-block {
     leaf eedebug-event {
       type string;
     }
     leaf chassis-id {
       type uint32;
     }
     leaf fpc-id {
       type uint32;
     }
     leaf pic-id {
       type uint32;
     }
     container eedebug-pfe {
       leaf chassis-id {
         type uint32;
       }
       leaf fpc-id {
         type uint32;
       }
       leaf pic-id {
         type uint32;
       }
     }
   }
   grouping eedebug-all-counters-block {
     leaf filter-name {
       type string;
     }
     leaf eedebug-counter-name {
       type string;
     }
     leaf eedebug-cid {
       type uint32;
     }
     leaf eedebug-fpc {
       type uint32;
     }
     leaf eedebug-pic {
       type uint32;
     }
     leaf eedebug-counter-value {
       type uint32;
     }
     leaf filter-index {
       type uint32;
     }
   }
   grouping eedebug-capture-output-block {
     leaf eedebug-capture-output-blob {
       type string;
     }
   }
   grouping alg-status-block {
     leaf alg-dns-status {
       type string;
       description "DNS ALG status";
     }
     leaf alg-ftp-status {
       type string;
       description "FTP ALG status";
     }
     leaf alg-h323-status {
       type string;
       description "H.323 ALG status";
     }
     leaf alg-mgcp-status {
       type string;
       description "MGCP ALG status";
     }
     leaf alg-msrpc-status {
       type string;
       description "MS RPC ALG status";
     }
     leaf alg-pptp-status {
       type string;
       description "PPTP ALG status";
     }
     leaf alg-rsh-status {
       type string;
       description "RSH ALG status";
     }
     leaf alg-rtsp-status {
       type string;
       description "RTSP ALG status";
     }
     leaf alg-sccp-status {
       type string;
       description "SCCP ALG status";
     }
     leaf alg-sip-status {
       type string;
       description "SIP ALG status";
     }
     leaf alg-sql-status {
       type string;
       description "SQL ALG status";
     }
     leaf alg-sunrpc-status {
       type string;
       description "SUN RPC ALG status";
     }
     leaf alg-talk-status {
       type string;
       description "Talk ALG status";
     }
     leaf alg-tftp-status {
       type string;
       description "TFTP ALG status";
     }
     leaf alg-ike-esp-nat-status {
       type string;
       description "IKE-ESP-NAT ALG status";
     }
     leaf alg-twamp-status {
       type string;
       description "TWAMP ALG status";
     }
   }
   grouping alg-h323-counters-block {
     leaf alg-h323-counters-pkt-rcvd {
       type uint32;
       description "Counter for packets received";
     }
     leaf alg-h323-counters-pkt-drpd {
       type uint32;
       description "Counter for packets dropped";
     }
     leaf alg-h323-counters-ras-msg-rcvd {
       type uint32;
       description "Counter for RAS message received";
     }
     leaf alg-h323-counters-q931-msg-rcvd {
       type uint32;
       description "Counter for Q.931 message received";
     }
     leaf alg-h323-counters-h245-msg-rcvd {
       type uint32;
       description "Counter for H.24 message received";
     }
     leaf alg-h323-counters-num-calls {
       type uint32;
       description "Counter for number of calls";
     }
     leaf alg-h323-counters-num-active-calls {
       type uint32;
       description "Counter for number of active calls";
     }
     leaf alg-h323-counters-num-dscp-marked {
       type uint32;
       description "Counter for number of dscp marked data session";
     }
     leaf alg-h323-counters-err-decode {
       type uint32;
       description "Error counter for decoding errors";
     }
     leaf alg-h323-counters-err-msg-flood-drpd {
       type uint32;
       description "Error counter for message flood dropped";
     }
     leaf alg-h323-counters-err-nat {
       type uint32;
       description "Error counter for NAT errors";
     }
     leaf alg-h323-counters-err-rm {
       type uint32;
       description "Error counter for Resource Manager";
     }
     leaf alg-h323-counters-err-dscp {
       type uint32;
       description "Error counter for dscp marked";
     }
     leaf alg-h323-counters-msg-rrq {
       type uint32;
       description "Message counter for RRQ";
     }
     leaf alg-h323-counters-msg-rcf {
       type uint32;
       description "Message counter for RCF";
     }
     leaf alg-h323-counters-msg-arq {
       type uint32;
       description "Message counter for ARQ";
     }
     leaf alg-h323-counters-msg-acf {
       type uint32;
       description "Message counter for ACF";
     }
     leaf alg-h323-counters-msg-urq {
       type uint32;
       description "Message counter for URQ";
     }
     leaf alg-h323-counters-msg-ucf {
       type uint32;
       description "Message counter for UCF";
     }
     leaf alg-h323-counters-msg-drq {
       type uint32;
       description "Message counter for DRQ";
     }
     leaf alg-h323-counters-msg-dcf {
       type uint32;
       description "Message counter for DCF";
     }
     leaf alg-h323-counters-msg-oth-ras {
       type uint32;
       description "Message counter for Oth RAS";
     }
     leaf alg-h323-counters-msg-setup {
       type uint32;
       description "Message counter for Setup";
     }
     leaf alg-h323-counters-msg-alert {
       type uint32;
       description "Message counter for Alert";
     }
     leaf alg-h323-counters-msg-connect {
       type uint32;
       description "Message counter for Connect";
     }
     leaf alg-h323-counters-msg-callprod {
       type uint32;
       description "Message counter for CallProd";
     }
     leaf alg-h323-counters-msg-info {
       type uint32;
       description "Message counter for Info";
     }
     leaf alg-h323-counters-msg-relcmpl {
       type uint32;
       description "Message counter for RelCmpl";
     }
     leaf alg-h323-counters-msg-facility {
       type uint32;
       description "Message counter for Facility";
     }
     leaf alg-h323-counters-msg-empty {
       type uint32;
       description "Message counter for Empty";
     }
     leaf alg-h323-counters-msg-olc {
       type uint32;
       description "Message counter for OLC";
     }
     leaf alg-h323-counters-msg-olc-ack {
       type uint32;
       description "Message counter for OLC-ACK";
     }
     leaf alg-h323-counters-msg-oth-h245 {
       type uint32;
       description "Message counter for Oth H245";
     }
   }
   grouping alg-mgcp-call-information-block {
     list alg-mgcp-call-data {
       leaf alg-mgcp-call-lsys {
         type string;
         description "Logical system for ALG MGCP call";
       }
       leaf alg-mgcp-call-ep {
         type string;
         description "Endpoint for ALG MGCP call";
       }
       leaf alg-mgcp-call-ep-gw {
         type string;
         description "Endpoint gateway for ALG MGCP call";
       }
       leaf alg-mgcp-call-zone {
         type string;
         description "Zone for ALG MGCP call";
       }
       leaf alg-mgcp-call-call-id {
         type string;
         description "ALG MGCP call id";
       }
       leaf alg-mgcp-call-resmgr-group {
         type uint32;
         description "ALG MGCP call resource manager group";
       }
       leaf alg-mgcp-call-call-duration {
         type uint32;
         description "Call duration for ALG MGCP call";
       }
       list alg-mgcp-call-connections-data {
         leaf alg-mgcp-call-connection-id {
           type uint32;
           description "Connection ID for ALG MGCP call";
         }
         leaf alg-mgcp-call-local-sdp-o {
           type jt:ipaddr;
           description "ALG MGCP call local owner IP address as per the Session                      Description Protocol (SDP)";
         }
         leaf alg-mgcp-call-local-sdp-x-o {
           type jt:ipaddr;
           description "ALG MGCP call translated local owner IP address as per                       the Session Description Protocol (SDP)";
         }
         leaf alg-mgcp-call-remote-sdp-o {
           type jt:ipaddr;
           description "ALG MGCP call remote owner IP address as per the Session                       Description Protocol (SDP)";
         }
         leaf alg-mgcp-call-remote-sdp-x-o {
           type jt:ipaddr;
           description "ALG MGCP call translated remote owner IP address as                       per the Session Description Protocol (SDP)";
         }
         list alg-mgcp-call-local-sdp-m-lines {
           leaf alg-mgcp-call-local-sdp-c-ip {
             type jt:ipaddr;
             description "ALG MGCP call local connection IP address as per                           the Session Description Protocol (SDP) ";
           }
           leaf alg-mgcp-call-local-sdp-c-port {
             type uint32;
             description "ALG MGCP call local connection port number as per                           the Session Description Protocol (SDP)";
           }
           leaf alg-mgcp-call-local-sdp-c-x-ip {
             type jt:ipaddr;
             description "ALG MGCP call translated local connection IP address                           as per the Session Description Protocol (SDP)";
           }
           leaf alg-mgcp-call-local-sdp-c-x-port {
             type uint32;
             description "ALG MGCP call translated local connection port                          number as per the Session Description Protocol (SDP)";
           }
         }
         list alg-mgcp-call-remote-sdp-m-lines {
           leaf alg-mgcp-call-remote-sdp-c-ip {
             type jt:ipaddr;
             description "ALG MGCP call remote connection IP address as per                           the Session Description Protocol (SDP) ";
           }
           leaf alg-mgcp-call-remote-sdp-c-port {
             type uint32;
             description "ALG MGCP call remote connection port number as per                           the Session Description Protocol (SDP) ";
           }
           leaf alg-mgcp-call-remote-sdp-c-x-ip {
             type jt:ipaddr;
             description "ALG MGCP call translated remote connection IP                           address as per the Session Description Protocol                           (SDP)";
           }
           leaf alg-mgcp-call-remote-sdp-c-x-port {
             type uint32;
             description "ALG MGCP call translated remote connection port                           number as per the Session Description Protocol (SDP)";
           }
         }
       }
     }
   }
   grouping alg-mgcp-counter-information-block {
     leaf alg-mgcp-counters-packets-received {
       type uint32;
       description "ALG MGCP packets received counter";
     }
     leaf alg-mgcp-counters-packets-dropped {
       type uint32;
       description "ALG MGCP packets dropped counter";
     }
     leaf alg-mgcp-counters-message-received {
       type uint32;
       description "ALG MGCP message received counter";
     }
     leaf alg-mgcp-counters-connections {
       type uint32;
       description "ALG MGCP number of connection counter";
     }
     leaf alg-mgcp-counters-active-connections {
       type uint32;
       description "ALG MGCP active connection counter";
     }
     leaf alg-mgcp-counters-calls {
       type uint32;
       description "ALG MGCP number of call counter";
     }
     leaf alg-mgcp-counters-active-calls {
       type uint32;
       description "ALG MGCP active call counter";
     }
     leaf alg-mgcp-counters-transactions {
       type uint32;
       description "ALG MGCP number of transaction counter";
     }
     leaf alg-mgcp-counters-active-transactions {
       type uint32;
       description "ALG MGCP active transaction counter";
     }
     leaf alg-mgcp-counters-retransmissions {
       type uint32;
       description "Number of ALG MGCP retransmissions";
     }
     leaf alg-mgcp-counters-active-endpoints {
       type uint32;
       description "ALG MGCP active endpoint counter";
     }
     leaf alg-mgcp-counters-dscp-marked {
       type uint32;
       description "ALG MGCP dscp marked counter";
     }
     leaf alg-mgcp-counters-unknown-method {
       type uint32;
       description "ALG MGCP unknown method error counter";
     }
     leaf alg-mgcp-counters-decoding-errors {
       type uint32;
       description "Number of ALG MGCP decoding errors";
     }
     leaf alg-mgcp-counters-transaction-errors {
       type uint32;
       description "Number of ALG MGCP transaction errors";
     }
     leaf alg-mgcp-counters-call-errors {
       type uint32;
       description "Number of ALG MGCP counter errors";
     }
     leaf alg-mgcp-counters-connection-errors {
       type uint32;
       description "Number of ALG MGCP connection errors";
     }
     leaf alg-mgcp-counters-connection-flood-drop {
       type uint32;
       description "ALG MGCP connection flood drop error counter";
     }
     leaf alg-mgcp-counters-message-flood-drop {
       type uint32;
       description "ALG MGCP message flood drop error counter";
     }
     leaf alg-mgcp-counters-ip-resolution-errors {
       type uint32;
       description "Number of ALG MGCP IP-address resolution errors";
     }
     leaf alg-mgcp-counters-nat-errors {
       type uint32;
       description "Number of ALG MGCP network address translation errors";
     }
     leaf alg-mgcp-counters-resource-mgr-errors {
       type uint32;
       description "Number of ALG MGCP resource manager errors";
     }
     leaf alg-mgcp-counters-dscp-errors {
       type uint32;
       description "Number of ALG MGCP dscp errors";
     }
     leaf alg-mgcp-counters-crcx-packets {
       type uint32;
       description "Number of  ALG MGCP CreateConnection (CRCX) packets";
     }
     leaf alg-mgcp-counters-mdcx-packets {
       type uint32;
       description "Number of ALG MGCP ModifyConnection (MDCX) packets";
     }
     leaf alg-mgcp-counters-dlcx-packets {
       type uint32;
       description "Number of ALG MGCP DeleteConnection (DLCX) packets";
     }
     leaf alg-mgcp-counters-auep-packets {
       type uint32;
       description "Number of ALG MGCP AuditEndpoint (AUEP) packets";
     }
     leaf alg-mgcp-counters-aucx-packets {
       type uint32;
       description "Number of ALG MGCP AuditConnection (AUCX) packets";
     }
     leaf alg-mgcp-counters-ntfy-packets {
       type uint32;
       description "Number of ALG MGCP Notify (NTFY) packets";
     }
     leaf alg-mgcp-counters-rsip-packets {
       type uint32;
       description "Number of ALG MGCP RestartInProgress (RSIP) packets";
     }
     leaf alg-mgcp-counters-epcf-packets {
       type uint32;
       description "Number of ALG MGCP EndpointConfiguration (EPCF) packets";
     }
     leaf alg-mgcp-counters-rqnt-packets {
       type uint32;
       description "Number of ALG MGCP NotificationRequest (RQNT) packets";
     }
     leaf alg-mgcp-counters-000-199-packets {
       type uint32;
       description "Number of ALG MGCP packets of a packet type between 0 and 199";
     }
     leaf alg-mgcp-counters-200-299-packets {
       type uint32;
       description "Number of ALG MGCP packets of a packet type between 200 and 299";
     }
     leaf alg-mgcp-counters-300-999-packets {
       type uint32;
       description "Number of ALG MGCP packets of a packet type between 300 and 399";
     }
   }
   grouping alg-mgcp-endpoint-information-block {
     list alg-mgcp-endpoints-data {
       leaf alg-mgcp-endpoints-lsys {
         type string;
         description "ALG MGCP Endpoint logical system";
       }
       leaf alg-mgcp-endpoints-gateway {
         type string;
         description "ALG MGCP Endpoint gateway";
       }
       leaf alg-mgcp-endpoints-zone {
         type string;
         description "Zone for ALG MGCP endpoint";
       }
       leaf alg-mgcp-gw-ip {
         type jt:ipaddr;
         description "IP address of ALG MGCP gateway";
       }
       leaf alg-mgcp-gw-x-ip {
         type jt:ipaddr;
         description "Translated IP address of ALG MGCP gateway";
       }
       leaf alg-mgcp-endpoints-name {
         type string;
         description "ALG MGCP Endpoint name";
       }
       leaf alg-mgcp-endpoints-transaction-num {
         type uint32;
         description "ALG MGCP Endpoint transaction number";
       }
       leaf alg-mgcp-endpoints-call-num {
         type uint32;
         description "ALG MGCP Endpoint call number";
       }
       leaf alg-mgcp-endpoints-ntfy-ip {
         type jt:ipaddr;
         description "IP address of ALG MGCP endpoint-notified entity";
       }
       leaf alg-mgcp-endpoints-ntfy-port {
         type uint32;
         description "Port number of ALG MGCP endpoint-notified entity";
       }
       leaf alg-mgcp-endpoints-ntfy-x-ip {
         type jt:ipaddr;
         description "Translated IP address of ALG MGCP endpoint-notified entity";
       }
       leaf alg-mgcp-endpoints-ntfy-x-port {
         type uint32;
         description "Translated port number of ALG MGCP endpoint-notified entity";
       }
     }
   }
   grouping alg-sccp-counters-block {
     leaf alg-sccp-counters-active-client-sessions {
       type uint32;
       description "Number of active SCCP client sessions";
     }
     leaf alg-sccp-counters-active-calls {
       type uint32;
       description "Number of active SCCP calls";
     }
     leaf alg-sccp-counters-total-calls {
       type uint32;
       description "Total number of SCCP calls since the call counter last reset";
     }
     leaf alg-sccp-counters-packets-received {
       type uint32;
       description "Total number of packets processed by the SCCP ALG";
     }
     leaf alg-sccp-counters-pdus-processed {
       type uint32;
       description "Total number of SCCP protocol data units processed";
     }
     leaf alg-sccp-counters-current-call-rate {
       type uint32;
       description "Current rate of incoming SCCP calls";
     }
     leaf alg-sccp-counters-dscp-marked {
       type uint32;
       description "Number of dscp marked data session";
     }
     leaf alg-sccp-counters-packets-dropped {
       type uint32;
       description "Number of packets dropped by the SCCP ALG";
     }
     leaf alg-sccp-counters-init-errors {
       type uint32;
       description "Number of SCCP ALG initialization errors";
     }
     leaf alg-sccp-counters-decode-errors {
       type uint32;
       description "Number of SCCP ALG decoder errors encountered";
     }
     leaf alg-sccp-counters-protocol-errors {
       type uint32;
       description "Number of SCCP protocol errors encountered";
     }
     leaf alg-sccp-counters-nat-errors {
       type uint32;
       description "Number of network address translation errors encountered by SCCP ALG";
     }
     leaf alg-sccp-counters-policy-not-found {
       type uint32;
       description "Number of packets dropped because of a failed policy lookup";
     }
     leaf alg-sccp-counters-unknown-pdus {
       type uint32;
       description "Number of packets with valid SCCP protocol data units that are unknown to this SCCP ALG implementation";
     }
     leaf alg-sccp-counters-maximum-call-rate-exceeded {
       type uint32;
       description "Number of times the maximum SCCP call rate was exceeded";
     }
     leaf alg-sccp-counters-maximum-calls-exceeded {
       type uint32;
       description "Number of times the maximum SCCP call limit was exceeded";
     }
     leaf alg-sccp-counters-internal-errors {
       type uint32;
       description "Number of times the SCCP ALG detected an internal software error";
     }
     leaf alg-sccp-counters-unspecified-errors {
       type uint32;
       description "Number of nonspecific errors detected by the SCCP ALG";
     }
     leaf alg-sccp-counters-no-active-calls {
       type uint32;
       description "Number of times SCCP ALG failed to delete calls because there were no active calls";
     }
     leaf alg-sccp-counters-no-active-sessions {
       type uint32;
       description "Number of times SCCP ALG failed to delete client sessions because there were no active client sessions";
     }
     leaf alg-sccp-counters-cookie-create-errors {
       type uint32;
       description "Number of times SCCP ALG failed to create a session cookie";
     }
     leaf alg-sccp-counters-bad-nat-cookie {
       type uint32;
       description "Number of times SCCP ALG detected an invalid nat cookie";
     }
     leaf alg-sccp-counters-nat-cookie-not-found {
       type uint32;
       description "Number of times SCCP ALG failed to find a valid nat cookie associated with a session";
     }
     leaf alg-sccp-counters-dscp-marked-errors {
       type uint32;
       description "Number of dscp marked fail";
     }
   }
   grouping alg-sip-call-information-block {
     leaf alg-sip-calls-total-num-calls {
       type uint32;
       description "ALG SIP total number of calls";
     }
     list alg-sip-calls-data {
       leaf alg-sip-calls-call-id {
         type string;
         description "Call Identifier for ALG SIP calls";
       }
       leaf alg-sip-calls-method {
         type string;
         description "Method for ALG SIP calls";
       }
       leaf alg-sip-calls-lsys-name {
         type string;
         description "Logical system name";
       }
       leaf alg-sip-calls-state {
         type string;
         description "State of ALG SIP calls";
       }
       leaf alg-sip-calls-rm-group-id {
         type uint32;
         description "Resource manager group";
       }
     }
   }
   grouping alg-sip-counter-information-block {
     leaf alg-sip-counters-total-packet-in {
       type uint32;
       description "ALG SIP total packet-in counter";
     }
     leaf alg-sip-counters-pkt-drop-on-error {
       type uint32;
       description "ALG SIP total packet dropped on error counter";
     }
     leaf alg-sip-counters-call-error {
       type uint32;
       description "ALG SIP call error counter";
     }
     leaf alg-sip-counters-ip-resolve-error {
       type uint32;
       description "ALG SIP IP resolve error counter";
     }
     leaf alg-sip-counters-nat-error {
       type uint32;
       description "ALG SIP NAT error counter";
     }
     leaf alg-sip-counters-resmgr-error {
       type uint32;
       description "ALG SIP resource manager error counter";
     }
     leaf alg-sip-counters-rr-hdr-exceeded-max {
       type uint32;
       description "ALG SIP RR header exceeded maximum counter";
     }
     leaf alg-sip-counters-contact-hdr-exceeded-max {
       type uint32;
       description "ALG SIP contact header exceeded maximum counter";
     }
     leaf alg-sip-counters-call-drop-to-limit {
       type uint32;
       description "ALG SIP call dropped due to limit counter";
     }
     leaf alg-sip-counters-sip-stack-error {
       type uint32;
       description "ALG SIP stack error counter";
     }
     leaf alg-sip-counters-sip-decode-error {
       type uint32;
       description "ALG SIP decode error counter";
     }
     leaf alg-sip-counters-unknown-method-error {
       type uint32;
       description "ALG SIP unknown method counter";
     }
     leaf alg-sip-counters-dscp-marked {
       type uint32;
       description "ALG SIP dscp marked";
     }
     leaf alg-sip-counters-dscp-marked-error {
       type uint32;
       description "ALG SIP dscp marked error";
     }
     leaf alg-sip-counters-ha-packet-out {
       type uint32;
       description "ALG SIP RTO Packet-out counter";
     }
     leaf alg-sip-counters-ha-packet-in {
       type uint32;
       description "ALG SIP RTO Packet-in counter";
     }
     leaf alg-sip-counters-ha-buffer-alloc-error {
       type uint32;
       description "ALG SIP RTO buffer allocation failure counter";
     }
     leaf alg-sip-counters-ha-transmit-error {
       type uint32;
       description "ALG SIP RTO buffer transmit failure counter";
     }
     leaf alg-sip-counters-ha-send-proc-error {
       type uint32;
       description "ALG SIP RTO send processing error counter";
     }
     leaf alg-sip-counters-ha-receive-proc-error {
       type uint32;
       description "ALG SIP RTO receive processing error counter";
     }
     leaf alg-sip-counters-ha-receive-inv-len-error {
       type uint32;
       description "ALG SIP RTO receive invalid length message counter";
     }
     leaf alg-sip-counters-ha-receive-call-proc-error {
       type uint32;
       description "ALG SIP RTO receive call processing error counter";
     }
     leaf alg-sip-counters-ha-receive-call-alloc-error {
       type uint32;
       description "ALG SIP RTO receive call allocate entry error counter";
     }
     leaf alg-sip-counters-ha-receive-call-reg-error {
       type uint32;
       description "ALG SIP RTO receive call register entry error counter";
     }
     leaf alg-sip-counters-ha-receive-invalid-status-error {
       type uint32;
       description "ALG SIP RTO receive invalid status  error counter";
     }
     list alg-sip-counters-data {
       leaf alg-sip-counters-tbl-method {
         type string;
         description "ALG SIP counter table name";
       }
       leaf alg-sip-counters-tbl-transmit {
         type uint32;
         description "ALG SIP counter table transmit value";
       }
       leaf alg-sip-counters-tbl-transmit-1xx {
         type uint32;
         description "ALG SIP counter table transmit 1xx value";
       }
       leaf alg-sip-counters-tbl-transmit-2xx {
         type uint32;
         description "ALG SIP counter table transmit 2xx value";
       }
       leaf alg-sip-counters-tbl-transmit-3xx {
         type uint32;
         description "ALG SIP counter table transmit 3xx value";
       }
       leaf alg-sip-counters-tbl-transmit-4xx {
         type uint32;
         description "ALG SIP counter table transmit 4xx value";
       }
       leaf alg-sip-counters-tbl-transmit-5xx {
         type uint32;
         description "ALG SIP counter table transmit 5xx value";
       }
       leaf alg-sip-counters-tbl-transmit-6xx {
         type uint32;
         description "ALG SIP counter table transmit 6xx value";
       }
       leaf alg-sip-counters-tbl-retransmit {
         type uint32;
         description "ALG SIP counter table retransmit value";
       }
       leaf alg-sip-counters-tbl-retransmit-1xx {
         type uint32;
         description "ALG SIP counter table retransmit 1xx value";
       }
       leaf alg-sip-counters-tbl-retransmit-2xx {
         type uint32;
         description "ALG SIP counter table retransmit 2xx value";
       }
       leaf alg-sip-counters-tbl-retransmit-3xx {
         type uint32;
         description "ALG SIP counter table retransmit 3xx value";
       }
       leaf alg-sip-counters-tbl-retransmit-4xx {
         type uint32;
         description "ALG SIP counter table retransmit 4xx value";
       }
       leaf alg-sip-counters-tbl-retransmit-5xx {
         type uint32;
         description "ALG SIP counter table retransmit 5xx value";
       }
       leaf alg-sip-counters-tbl-retransmit-6xx {
         type uint32;
         description "ALG SIP counter table retransmit 6xx value";
       }
     }
   }
   grouping alg-ike-esp-show-block {
     list ike-esp-cookies {
       leaf ike-esp-icookie {
         type string;
         description "IKE initiator cookie";
       }
       leaf ike-esp-rcookie {
         type string;
         description "IKE responder cookie";
       }
       leaf ike-esp-session {
         type uint32;
         description "Session identifier";
       }
       leaf ike-esp-state {
         type uint32;
         description "State";
       }
       leaf ike-esp-age {
         type uint32;
         description "Timeout value";
       }
     }
   }
   grouping alg-ike-esp-show-summary-block {
     leaf alg-ike-esp-use-count {
       type uint32;
       description "Number of active IKE alg cookies  ";
     }
     leaf alg-ike-esp-total-count {
       type uint32;
       description "Number of active IKE alg cookies  ";
     }
   }
   grouping application-firewall-block {
     container rule-set-info {
       description "Information of the rule-set";
       list rule-set {
         leaf rule-set-name {
           type string;
           description "Name of the rule-set";
         }
         leaf-list logical-system-name {
           type string;
           description "Name of the logical system";
         }
         leaf-list tenant-name {
           type string;
           description "Name of the tenant";
         }
         leaf profile {
           type string;
           description "Name of profile";
         }
         leaf session-pending-counter {
           type uint32;
           description "Number of sessions with appid pending";
         }
         container rule-list {
           description "Information of all the rules";
           list rule {
             description "Information of the rule";
             leaf rule-name {
               type string;
               description "Name of the rule";
             }
             leaf ssl-encryption-option {
               type string;
               description "SSL encryption setting in this application firewall rule";
             }
             leaf action {
               type string;
               description "Action specified in this application firewall rule";
             }
             leaf session-matched-counter {
               type uint32;
               description "Number of sessions matched";
             }
             leaf session-redirected-counter {
               type uint32;
               description "Number of sessions redirected";
             }
             container dynamic-application-list {
               description "Information of all dynamic applications";
               leaf-list dynamic-application {
                 type string;
                 description "Name of the dynamic application";
               }
             }
             container dynamic-application-group-list {
               description "Information of all dynamic application groups ";
               leaf-list dynamic-application-group {
                 type string;
                 description "Name of the dynamic application group";
               }
             }
           }
           container default-rule {
             description "Information of the default rule";
             leaf action {
               type string;
               description "Action specified in this application firewall rule";
             }
             leaf session-matched-counter {
               type uint32;
               description "Number of sessions matched";
             }
             leaf session-redirected-counter {
               type uint32;
               description "Number of sessions redirected";
             }
           }
         }
       }
     }
   }
   grouping appfw-shadow-rules-block {
     leaf total-dyn-app-num {
       type uint32;
       description "Number of shadowed dynamic application";
     }
     list dynamic-application-entry {
       description "Matching rule and shadow rules for one dynamic application";
       leaf dynamic-application-name {
         type string;
         description "Name of the dynamic application";
       }
       leaf-list logical-system-name {
         type string;
         description "Name of the logical system";
       }
       leaf-list tenant-name {
         type string;
         description "Name of the tenant";
       }
       container non-ssl-encrypted-entry {
         leaf shadowed-rules {
           type string;
         }
         container matching-rule {
           description "Matching rule for the dynamic application";
           leaf rule-name {
             type string;
             description "Name of the rule";
           }
           leaf ssl-encryption-option {
             type string;
             description "SSL encryption setting in this application firewall rule";
           }
           leaf action {
             type string;
             description "Action specified in this application firewall rule";
           }
           container dynamic-application-list {
             description "Information of all dynamic applications";
             leaf-list dynamic-application {
               type string;
               description "Name of the dynamic application";
             }
           }
           container dynamic-application-group-list {
             description "Information of all dynamic application groups ";
             leaf-list dynamic-application-group {
               type string;
               description "Name of the dynamic application group";
             }
           }
         }
         list shadowed-rule-list {
           description "Shadow rules for the dynamic applications";
           leaf rule-name {
             type string;
             description "Name of the rule";
           }
           leaf ssl-encryption-option {
             type string;
             description "SSL encryption setting in this application firewall rule";
           }
           leaf action {
             type string;
             description "Action specified in this application firewall rule";
           }
           container dynamic-application-list {
             description "Information of all dynamic applications";
             leaf-list dynamic-application {
               type string;
               description "Name of the dynamic application";
             }
           }
           container dynamic-application-group-list {
             description "Information of all dynamic application groups ";
             leaf-list dynamic-application-group {
               type string;
               description "Name of the dynamic application group";
             }
           }
         }
       }
       container ssl-encrypted-entry {
         leaf shadowed-rules {
           type string;
         }
         container matching-rule {
           description "Matching rule for the dynamic application";
           leaf rule-name {
             type string;
             description "Name of the rule";
           }
           leaf ssl-encryption-option {
             type string;
             description "SSL encryption setting in this application firewall rule";
           }
           leaf action {
             type string;
             description "Action specified in this application firewall rule";
           }
           container dynamic-application-list {
             description "Information of all dynamic applications";
             leaf-list dynamic-application {
               type string;
               description "Name of the dynamic application";
             }
           }
           container dynamic-application-group-list {
             description "Information of all dynamic application groups ";
             leaf-list dynamic-application-group {
               type string;
               description "Name of the dynamic application group";
             }
           }
         }
         list shadowed-rule-list {
           description "Shadow rules for the dynamic applications";
           leaf rule-name {
             type string;
             description "Name of the rule";
           }
           leaf ssl-encryption-option {
             type string;
             description "SSL encryption setting in this application firewall rule";
           }
           leaf action {
             type string;
             description "Action specified in this application firewall rule";
           }
           container dynamic-application-list {
             description "Information of all dynamic applications";
             leaf-list dynamic-application {
               type string;
               description "Name of the dynamic application";
             }
           }
           container dynamic-application-group-list {
             description "Information of all dynamic application groups ";
             leaf-list dynamic-application-group {
               type string;
               description "Name of the dynamic application group";
             }
           }
         }
       }
     }
   }
   grouping appfw-match-rule-block {
     leaf-list logical-system-name {
       type string;
       description "Name of the logical system";
     }
     leaf-list tenant-name {
       type string;
       description "Name of the tenant";
     }
     container non-ssl-match-rule-entry {
       container matching-rule {
         description "Matching rule for the dynamic application";
         leaf rule-name {
           type string;
           description "Name of the rule";
         }
         leaf ssl-encryption-option {
           type string;
           description "SSL encryption setting in this application firewall rule";
         }
         leaf action {
           type string;
           description "Action specified in this application firewall rule";
         }
         container dynamic-application-list {
           description "Information of all dynamic applications";
           leaf-list dynamic-application {
             type string;
             description "Name of the dynamic application";
           }
         }
         container dynamic-application-group-list {
           description "Information of all dynamic application groups ";
           leaf-list dynamic-application-group {
             type string;
             description "Name of the dynamic application group";
           }
         }
       }
       list shadowed-rule-list {
         description "Shadow rules for the dynamic applications";
         leaf rule-name {
           type string;
           description "Name of the rule";
         }
         leaf ssl-encryption-option {
           type string;
           description "SSL encryption setting in this application firewall rule";
         }
         leaf action {
           type string;
           description "Action specified in this application firewall rule";
         }
         container dynamic-application-list {
           description "Information of all dynamic applications";
           leaf-list dynamic-application {
             type string;
             description "Name of the dynamic application";
           }
         }
         container dynamic-application-group-list {
           description "Information of all dynamic application groups ";
           leaf-list dynamic-application-group {
             type string;
             description "Name of the dynamic application group";
           }
         }
       }
     }
     container ssl-match-rule-entry {
       container matching-rule {
         description "Matching rule for the dynamic application";
         leaf rule-name {
           type string;
           description "Name of the rule";
         }
         leaf ssl-encryption-option {
           type string;
           description "SSL encryption setting in this application firewall rule";
         }
         leaf action {
           type string;
           description "Action specified in this application firewall rule";
         }
         container dynamic-application-list {
           description "Information of all dynamic applications";
           leaf-list dynamic-application {
             type string;
             description "Name of the dynamic application";
           }
         }
         container dynamic-application-group-list {
           description "Information of all dynamic application groups ";
           leaf-list dynamic-application-group {
             type string;
             description "Name of the dynamic application group";
           }
         }
       }
       list shadowed-rule-list {
         description "Shadow rules for the dynamic applications";
         leaf rule-name {
           type string;
           description "Name of the rule";
         }
         leaf ssl-encryption-option {
           type string;
           description "SSL encryption setting in this application firewall rule";
         }
         leaf action {
           type string;
           description "Action specified in this application firewall rule";
         }
         container dynamic-application-list {
           description "Information of all dynamic applications";
           leaf-list dynamic-application {
             type string;
             description "Name of the dynamic application";
           }
         }
         container dynamic-application-group-list {
           description "Information of all dynamic application groups ";
           leaf-list dynamic-application-group {
             type string;
             description "Name of the dynamic application group";
           }
         }
       }
     }
   }
   grouping avt-counters-block {
     list avt-counter-statistics {
       leaf name {
         type string;
         description "Name of this component";
       }
       leaf value {
         type uint32;
         description "Value of this entity";
       }
     }
   }
   grouping utmd-status-block {
     leaf running {
       type empty;
       description "Process is running";
     }
   }
   grouping utmd-session-block {
     container utmd-session-statistics {
       leaf maximum-sessions {
         type uint32;
         description "Maximum sessions";
       }
       leaf total-allocated-sessions {
         type uint32;
         description "Total allocated sessions";
       }
       leaf total-freed-sessions {
         type uint32;
         description "Total freed sessions";
       }
       leaf active-sessions {
         type uint32;
         description "Active sessions";
       }
     }
     container utmd-session-statistics-fpc {
       leaf fpc-slot {
         type uint32;
         description "FPC slot";
       }
       leaf pic-slot {
         type uint32;
         description "PIC slot";
       }
       container utmd-session-statistics {
         leaf maximum-sessions {
           type uint32;
           description "Maximum sessions";
         }
         leaf total-allocated-sessions {
           type uint32;
           description "Total allocated sessions";
         }
         leaf total-freed-sessions {
           type uint32;
           description "Total freed sessions";
         }
         leaf active-sessions {
           type uint32;
           description "Active sessions";
         }
       }
     }
   }
   grouping anti-virus-block {
     container anti-virus-statistics {
       leaf scan-intelligent {
         type uint32;
         description "Scan intelligent";
       }
       leaf skip-mime {
         type uint32;
         description "Number of anti-virus scan requests passed by mime-whitelist";
       }
       leaf url-white {
         type uint32;
         description "Number of anti-virus scan requests passed by url-whitelist";
       }
       leaf forward-to-scan-engine {
         type uint32;
         description "Forward to scan engine";
       }
       leaf session-abort {
         type uint32;
         description "Number of session abort, will cancel scan if have scanned";
       }
       container scan-mode {
         leaf scan-all {
           type uint32;
           description "Scan all";
         }
         leaf scan-extension {
           type uint32;
           description "Scan extension";
         }
       }
       container scan-code {
         leaf clear {
           type uint32;
           description "Clear count";
         }
         leaf infected {
           type uint32;
           description "Infected count";
         }
         leaf password {
           type uint32;
           description "Password count";
         }
         leaf decompress-layer {
           type uint32;
           description "Decompress-layer count";
         }
         leaf corrupted-file {
           type uint32;
           description "Corrupted file count";
         }
         leaf out-of-resource {
           type uint32;
           description "Out of resource count";
         }
         leaf internal-error {
           type uint32;
           description "Internal error count";
         }
       }
       container scan-request {
         leaf scan-request-total {
           type uint32;
         }
         leaf scan-request-clean {
           type uint32;
         }
         leaf scan-request-threat {
           type uint32;
         }
         leaf scan-request-fallback {
           type uint32;
         }
       }
       container fall-back-permit {
         leaf engine-not-ready-log-and-permit {
           type uint32;
           description "Engine not ready and log permit count";
         }
         leaf engine-not-ready-block {
           type uint32;
           description "Engine not ready and block count";
         }
         leaf engine-not-ready-permit {
           type uint32;
           description "Engine not ready permit count";
         }
         leaf out-of-resource-log-and-permit {
           type uint32;
           description "Out of resource log and permit count";
         }
         leaf out-of-resource-block {
           type uint32;
           description "Out of resource block count";
         }
         leaf out-of-resource-permit {
           type uint32;
           description "Out of resource permit count";
         }
         leaf timeout-log-and-permit {
           type uint32;
           description "Timeout log and permit count";
         }
         leaf timeout-block {
           type uint32;
           description "Timeout block count";
         }
         leaf timeout-permit {
           type uint32;
           description "Timeout permit count";
         }
         leaf maximum-content-size-log-and-permit {
           type uint32;
           description "Maximum content size log and permit count";
         }
         leaf maximum-content-size-block {
           type uint32;
           description "Maximum content size block count";
         }
         leaf maximum-content-size-permit {
           type uint32;
           description "Maximum content size permit count";
         }
         leaf too-many-requests-log-and-permit {
           type uint32;
           description "Too many requests log and permit count";
         }
         leaf too-many-requests-block {
           type uint32;
           description "Too many requests block count";
         }
         leaf too-many-requests-permit {
           type uint32;
           description "Too many requests permit count";
         }
         leaf decompress-err-log-and-permit {
           type uint32;
           description "Decompress error log and permit count";
         }
         leaf decompress-err-block {
           type uint32;
           description "Decompress error block count";
         }
         leaf decompress-err-permit {
           type uint32;
           description "Decompress error permit count";
         }
         leaf server-conn-err-log-and-permit {
           type uint32;
           description "Server connection  error log and permit count";
         }
         leaf server-conn-err-block {
           type uint32;
           description "Server connection error block count";
         }
         leaf server-conn-err-permit {
           type uint32;
           description "Server connection error permit count";
         }
         leaf others-log-and-permit {
           type uint32;
           description "Others log and permit count";
         }
         leaf others-block {
           type uint32;
           description "Others block count";
         }
         leaf others-permit {
           type uint32;
           description "Others permit count";
         }
         leaf password-log-and-permit {
           type uint32;
           description "Password log and permit count";
         }
         leaf password-permit {
           type uint32;
           description "Password permit count";
         }
         leaf password-block {
           type uint32;
           description "Password block count";
         }
         leaf decompress-layer-log-and-permit {
           type uint32;
           description "Decompress layer log and permit count";
         }
         leaf decompress-layer-permit {
           type uint32;
           description "Decompress layer permit count";
         }
         leaf decompress-layer-block {
           type uint32;
           description "Decompress layer block count";
         }
         leaf corrupted-file-log-and-permit {
           type uint32;
           description "Corrupted file log and permit count";
         }
         leaf corrupted-file-permit {
           type uint32;
           description "Corrupted file permit count";
         }
         leaf corrupted-file-block {
           type uint32;
           description "Corrupted file block count";
         }
       }
     }
     list anti-virus-statistics-fpc {
       container anti-virus-statistics {
         container fall-back-permit {
           leaf password-log-and-permit {
             type uint32;
             description "Password log and permit count";
           }
           leaf password-permit {
             type uint32;
             description "Password permit count";
           }
           leaf password-block {
             type uint32;
             description "Password block count";
           }
           leaf decompress-layer-log-and-permit {
             type uint32;
             description "Decompress layer log and permit count";
           }
           leaf decompress-layer-permit {
             type uint32;
             description "Decompress layer permit count";
           }
           leaf decompress-layer-block {
             type uint32;
             description "Decompress layer block count";
           }
           leaf corrupted-file-log-and-permit {
             type uint32;
             description "Corrupted file log and permit count";
           }
           leaf corrupted-file-permit {
             type uint32;
             description "Corrupted file permit count";
           }
           leaf corrupted-file-block {
             type uint32;
             description "Corrupted file block count";
           }
           leaf engine-not-ready-log-and-permit {
             type uint32;
             description "Engine not ready and log permit count";
           }
           leaf engine-not-ready-block {
             type uint32;
             description "Engine not ready and block count";
           }
           leaf engine-not-ready-permit {
             type uint32;
             description "Engine not ready permit count";
           }
           leaf out-of-resource-log-and-permit {
             type uint32;
             description "Out of resource log and permit count";
           }
           leaf out-of-resource-block {
             type uint32;
             description "Out of resource block count";
           }
           leaf out-of-resource-permit {
             type uint32;
             description "Out of resource permit count";
           }
           leaf timeout-log-and-permit {
             type uint32;
             description "Timeout log and permit count";
           }
           leaf timeout-block {
             type uint32;
             description "Timeout block count";
           }
           leaf timeout-permit {
             type uint32;
             description "Timeout permit count";
           }
           leaf maximum-content-size-log-and-permit {
             type uint32;
             description "Maximum content size log and permit count";
           }
           leaf maximum-content-size-block {
             type uint32;
             description "Maximum content size block count";
           }
           leaf maximum-content-size-permit {
             type uint32;
             description "Maximum content size permit count";
           }
           leaf too-many-requests-log-and-permit {
             type uint32;
             description "Too many requests log and permit count";
           }
           leaf too-many-requests-block {
             type uint32;
             description "Too many requests block count";
           }
           leaf too-many-requests-permit {
             type uint32;
             description "Too many requests permit count";
           }
           leaf decompress-err-log-and-permit {
             type uint32;
             description "Decompress error log and permit count";
           }
           leaf decompress-err-block {
             type uint32;
             description "Decompress error block count";
           }
           leaf decompress-err-permit {
             type uint32;
             description "Decompress error permit count";
           }
           leaf server-conn-err-log-and-permit {
             type uint32;
             description "Server connection  error log and permit count";
           }
           leaf server-conn-err-block {
             type uint32;
             description "Server connection error block count";
           }
           leaf server-conn-err-permit {
             type uint32;
             description "Server connection error permit count";
           }
           leaf others-log-and-permit {
             type uint32;
             description "Others log and permit count";
           }
           leaf others-block {
             type uint32;
             description "Others block count";
           }
           leaf others-permit {
             type uint32;
             description "Others permit count";
           }
         }
         leaf scan-intelligent {
           type uint32;
           description "Scan intelligent";
         }
         leaf skip-mime {
           type uint32;
           description "Number of anti-virus scan requests passed by mime-whitelist";
         }
         leaf url-white {
           type uint32;
           description "Number of anti-virus scan requests passed by url-whitelist";
         }
         leaf forward-to-scan-engine {
           type uint32;
           description "Forward to scan engine";
         }
         leaf session-abort {
           type uint32;
           description "Number of session abort, will cancel scan if have scanned";
         }
         container scan-mode {
           leaf scan-all {
             type uint32;
             description "Scan all";
           }
           leaf scan-extension {
             type uint32;
             description "Scan extension";
           }
         }
         container scan-code {
           leaf clear {
             type uint32;
             description "Clear count";
           }
           leaf infected {
             type uint32;
             description "Infected count";
           }
           leaf password {
             type uint32;
             description "Password count";
           }
           leaf decompress-layer {
             type uint32;
             description "Decompress-layer count";
           }
           leaf corrupted-file {
             type uint32;
             description "Corrupted file count";
           }
           leaf out-of-resource {
             type uint32;
             description "Out of resource count";
           }
           leaf internal-error {
             type uint32;
             description "Internal error count";
           }
         }
         container scan-request {
           leaf scan-request-total {
             type uint32;
           }
           leaf scan-request-clean {
             type uint32;
           }
           leaf scan-request-threat {
             type uint32;
           }
           leaf scan-request-fallback {
             type uint32;
           }
         }
       }
       leaf fpc-slot {
         type uint32;
         description "FPC slot";
       }
       leaf pic-slot {
         type uint32;
         description "PIC slot";
       }
     }
     list anti-virus-status-fpc {
       leaf fpc-slot {
         type uint32;
         description "FPC slot";
       }
       leaf pic-slot {
         type uint32;
         description "PIC slot";
       }
       container anti-virus-status {
         leaf anti-virus-key-expire-date {
           type string;
           description "Anti-virus key expire date";
         }
         leaf anti-virus-update-url {
           type string;
           description "Anti-virus update URL";
         }
         leaf anti-virus-update-interval {
           type uint32;
           description "Anti-virus update interval count";
         }
         leaf anti-virus-update-status {
           type string;
           description "Anti-virus update status";
         }
         leaf anti-virus-proxy-server {
           type string;
           description "Anti-virus update via proxy server";
         }
         leaf anti-virus-update-result {
           type string;
           description "Anti-virus update results";
         }
         leaf anti-virus-fwd-mode {
           type string;
           description "Anti-virus forwarding-mode";
         }
         leaf anti-virus-signature-version {
           type string;
           description "Anti-virus signature version";
         }
         leaf anti-virus-compiler-version {
           type string;
           description "Anti-virus database compiler info";
         }
         leaf anti-virus-scan-engine-type {
           type string;
           description "Anti-virus engine type";
         }
         leaf anti-virus-scan-engine-information {
           type string;
           description "Anti-virus scan engine information";
         }
         leaf anti-virus-onbox-av-load-flavor-running {
           type string;
           description "Anti-virus onbox av load flavor running";
         }
         leaf anti-virus-onbox-av-load-flavor-config {
           type string;
           description "Anti-virus onbox av load flavor config";
         }
         leaf anti-virus-status-detail {
           type string;
           description "Anti-virus status detail";
         }
       }
     }
     container sophos-anti-virus-status {
       leaf anti-virus-key-expire-date {
         type string;
         description "Anti-virus key expire date";
       }
       leaf anti-virus-update-url {
         type string;
         description "Anti-virus update URL";
       }
       leaf anti-virus-update-interval {
         type uint32;
         description "Anti-virus update interval count";
       }
       leaf anti-virus-update-status {
         type string;
         description "Anti-virus update status";
       }
       leaf anti-virus-update-result {
         type string;
         description "Anti-virus update results";
       }
       leaf anti-virus-signature-version {
         type string;
         description "Anti-virus signature version";
       }
       leaf anti-virus-compiler-version {
         type string;
         description "Anti-virus database compiler info";
       }
       leaf anti-virus-scan-engine-type {
         type string;
         description "Anti-virus engine type";
       }
       leaf anti-virus-scan-engine-information {
         type string;
         description "Anti-virus scan engine information";
       }
       leaf anti-virus-status-detail {
         type string;
         description "Anti-virus status detail";
       }
     }
     container anti-virus-statistics-details {
       container anti-virus-statistics-details-http {
         container http-fallback-request-no-permit {
           leaf http-fallback-engine-not-ready-log-permit {
             type uint32;
           }
           leaf http-fallback-engine-not-ready-block {
             type uint32;
           }
           leaf http-fallback-engine-not-ready-permit {
             type uint32;
           }
           leaf http-fallback-out-resource-log-permit {
             type uint32;
           }
           leaf http-fallback-out-resource-block {
             type uint32;
           }
           leaf http-fallback-out-resource-permit {
             type uint32;
           }
           leaf http-fallback-timeout-log-permit {
             type uint32;
           }
           leaf http-fallback-timeout-block {
             type uint32;
           }
           leaf http-fallback-timeout-permit {
             type uint32;
           }
           leaf http-fallback-maximum-content-size-log-permit {
             type uint32;
           }
           leaf http-fallback-maximum-content-size-block {
             type uint32;
           }
           leaf http-fallback-maximum-content-size-permit {
             type uint32;
           }
           leaf http-fallback-too-many-requests-log-permit {
             type uint32;
           }
           leaf http-fallback-too-many-requests-block {
             type uint32;
           }
           leaf http-fallback-too-many-requests-permit {
             type uint32;
           }
           leaf http-fallback-decompress-err-log-permit {
             type uint32;
           }
           leaf http-fallback-decompress-err-block {
             type uint32;
           }
           leaf http-fallback-decompress-err-permit {
             type uint32;
           }
           leaf http-fallback-server-conn-err-log-permit {
             type uint32;
           }
           leaf http-fallback-server-conn-err-block {
             type uint32;
           }
           leaf http-fallback-server-conn-err-permit {
             type uint32;
           }
           leaf http-fallback-others-log-permit {
             type uint32;
           }
           leaf http-fallback-others-block {
             type uint32;
           }
           leaf http-fallback-others-permit {
             type uint32;
           }
         }
         leaf http-mime-whitelist-passed {
           type uint32;
         }
         leaf http-url-whitelist-passed {
           type uint32;
         }
         container http-scan-request {
           leaf http-scan-request-total {
             type uint32;
           }
           leaf http-scan-request-clean {
             type uint32;
           }
           leaf http-scan-request-threat {
             type uint32;
           }
         }
         container http-fallback-request {
           leaf http-fallback-engine-not-ready-log-permit {
             type uint32;
           }
           leaf http-fallback-engine-not-ready-block {
             type uint32;
           }
           leaf http-fallback-engine-not-ready-permit {
             type uint32;
           }
           leaf http-fallback-out-resource-log-permit {
             type uint32;
           }
           leaf http-fallback-out-resource-block {
             type uint32;
           }
           leaf http-fallback-out-resource-permit {
             type uint32;
           }
           leaf http-fallback-timeout-log-permit {
             type uint32;
           }
           leaf http-fallback-timeout-block {
             type uint32;
           }
           leaf http-fallback-timeout-permit {
             type uint32;
           }
           leaf http-fallback-maximum-content-size-log-permit {
             type uint32;
           }
           leaf http-fallback-maximum-content-size-block {
             type uint32;
           }
           leaf http-fallback-maximum-content-size-permit {
             type uint32;
           }
           leaf http-fallback-too-many-requests-log-permit {
             type uint32;
           }
           leaf http-fallback-too-many-requests-block {
             type uint32;
           }
           leaf http-fallback-too-many-requests-permit {
             type uint32;
           }
           leaf http-fallback-decompress-err-log-permit {
             type uint32;
           }
           leaf http-fallback-decompress-err-block {
             type uint32;
           }
           leaf http-fallback-decompress-err-permit {
             type uint32;
           }
           leaf http-fallback-server-conn-err-log-permit {
             type uint32;
           }
           leaf http-fallback-server-conn-err-block {
             type uint32;
           }
           leaf http-fallback-server-conn-err-permit {
             type uint32;
           }
           leaf http-fallback-others-log-permit {
             type uint32;
           }
           leaf http-fallback-others-block {
             type uint32;
           }
           leaf http-fallback-others-permit {
             type uint32;
           }
         }
       }
       container anti-virus-statistics-details-ftp {
         container ftp-fallback-request-no-permit {
           leaf ftp-fallback-engine-not-ready-log-permit {
             type uint32;
           }
           leaf ftp-fallback-engine-not-ready-block {
             type uint32;
           }
           leaf ftp-fallback-engine-not-ready-permit {
             type uint32;
           }
           leaf ftp-fallback-out-resource-log-permit {
             type uint32;
           }
           leaf ftp-fallback-out-resource-block {
             type uint32;
           }
           leaf ftp-fallback-out-resource-permit {
             type uint32;
           }
           leaf ftp-fallback-timeout-log-permit {
             type uint32;
           }
           leaf ftp-fallback-timeout-block {
             type uint32;
           }
           leaf ftp-fallback-timeout-permit {
             type uint32;
           }
           leaf ftp-fallback-maximum-content-size-log-permit {
             type uint32;
           }
           leaf ftp-fallback-maximum-content-size-block {
             type uint32;
           }
           leaf ftp-fallback-maximum-content-size-permit {
             type uint32;
           }
           leaf ftp-fallback-too-many-requests-log-permit {
             type uint32;
           }
           leaf ftp-fallback-too-many-requests-block {
             type uint32;
           }
           leaf ftp-fallback-too-many-requests-permit {
             type uint32;
           }
           leaf ftp-fallback-decompress-err-log-permit {
             type uint32;
           }
           leaf ftp-fallback-decompress-err-block {
             type uint32;
           }
           leaf ftp-fallback-decompress-err-permit {
             type uint32;
           }
           leaf ftp-fallback-server-conn-err-log-permit {
             type uint32;
           }
           leaf ftp-fallback-server-conn-err-block {
             type uint32;
           }
           leaf ftp-fallback-server-conn-err-permit {
             type uint32;
           }
           leaf ftp-fallback-others-log-permit {
             type uint32;
           }
           leaf ftp-fallback-others-block {
             type uint32;
           }
           leaf ftp-fallback-others-permit {
             type uint32;
           }
         }
         container ftp-scan-request {
           leaf ftp-scan-request-total {
             type uint32;
           }
           leaf ftp-scan-request-clean {
             type uint32;
           }
           leaf ftp-scan-request-threat {
             type uint32;
           }
         }
         container ftp-fallback-request {
           leaf ftp-fallback-engine-not-ready-log-permit {
             type uint32;
           }
           leaf ftp-fallback-engine-not-ready-block {
             type uint32;
           }
           leaf ftp-fallback-engine-not-ready-permit {
             type uint32;
           }
           leaf ftp-fallback-out-resource-log-permit {
             type uint32;
           }
           leaf ftp-fallback-out-resource-block {
             type uint32;
           }
           leaf ftp-fallback-out-resource-permit {
             type uint32;
           }
           leaf ftp-fallback-timeout-log-permit {
             type uint32;
           }
           leaf ftp-fallback-timeout-block {
             type uint32;
           }
           leaf ftp-fallback-timeout-permit {
             type uint32;
           }
           leaf ftp-fallback-maximum-content-size-log-permit {
             type uint32;
           }
           leaf ftp-fallback-maximum-content-size-block {
             type uint32;
           }
           leaf ftp-fallback-maximum-content-size-permit {
             type uint32;
           }
           leaf ftp-fallback-too-many-requests-log-permit {
             type uint32;
           }
           leaf ftp-fallback-too-many-requests-block {
             type uint32;
           }
           leaf ftp-fallback-too-many-requests-permit {
             type uint32;
           }
           leaf ftp-fallback-decompress-err-log-permit {
             type uint32;
           }
           leaf ftp-fallback-decompress-err-block {
             type uint32;
           }
           leaf ftp-fallback-decompress-err-permit {
             type uint32;
           }
           leaf ftp-fallback-server-conn-err-log-permit {
             type uint32;
           }
           leaf ftp-fallback-server-conn-err-block {
             type uint32;
           }
           leaf ftp-fallback-server-conn-err-permit {
             type uint32;
           }
           leaf ftp-fallback-others-log-permit {
             type uint32;
           }
           leaf ftp-fallback-others-block {
             type uint32;
           }
           leaf ftp-fallback-others-permit {
             type uint32;
           }
         }
       }
       container anti-virus-statistics-details-smtp {
         container smtp-fallback-request-no-permit {
           leaf smtp-fallback-engine-not-ready-log-permit {
             type uint32;
           }
           leaf smtp-fallback-engine-not-ready-block {
             type uint32;
           }
           leaf smtp-fallback-engine-not-ready-permit {
             type uint32;
           }
           leaf smtp-fallback-out-resource-log-permit {
             type uint32;
           }
           leaf smtp-fallback-out-resource-block {
             type uint32;
           }
           leaf smtp-fallback-out-resource-permit {
             type uint32;
           }
           leaf smtp-fallback-timeout-log-permit {
             type uint32;
           }
           leaf smtp-fallback-timeout-block {
             type uint32;
           }
           leaf smtp-fallback-timeout-permit {
             type uint32;
           }
           leaf smtp-fallback-maximum-content-size-log-permit {
             type uint32;
           }
           leaf smtp-fallback-maximum-content-size-block {
             type uint32;
           }
           leaf smtp-fallback-maximum-content-size-permit {
             type uint32;
           }
           leaf smtp-fallback-too-many-requests-log-permit {
             type uint32;
           }
           leaf smtp-fallback-too-many-requests-block {
             type uint32;
           }
           leaf smtp-fallback-too-many-requests-permit {
             type uint32;
           }
           leaf smtp-fallback-decompress-err-log-permit {
             type uint32;
           }
           leaf smtp-fallback-decompress-err-block {
             type uint32;
           }
           leaf smtp-fallback-decompress-err-permit {
             type uint32;
           }
           leaf smtp-fallback-server-conn-err-log-permit {
             type uint32;
           }
           leaf smtp-fallback-server-conn-err-block {
             type uint32;
           }
           leaf smtp-fallback-server-conn-err-permit {
             type uint32;
           }
           leaf smtp-fallback-others-log-permit {
             type uint32;
           }
           leaf smtp-fallback-others-block {
             type uint32;
           }
           leaf smtp-fallback-others-permit {
             type uint32;
           }
         }
         container smtp-scan-request {
           leaf smtp-scan-request-total {
             type uint32;
           }
           leaf smtp-scan-request-clean {
             type uint32;
           }
           leaf smtp-scan-request-threat {
             type uint32;
           }
         }
         container smtp-fallback-request {
           leaf smtp-fallback-engine-not-ready-log-permit {
             type uint32;
           }
           leaf smtp-fallback-engine-not-ready-block {
             type uint32;
           }
           leaf smtp-fallback-engine-not-ready-permit {
             type uint32;
           }
           leaf smtp-fallback-out-resource-log-permit {
             type uint32;
           }
           leaf smtp-fallback-out-resource-block {
             type uint32;
           }
           leaf smtp-fallback-out-resource-permit {
             type uint32;
           }
           leaf smtp-fallback-timeout-log-permit {
             type uint32;
           }
           leaf smtp-fallback-timeout-block {
             type uint32;
           }
           leaf smtp-fallback-timeout-permit {
             type uint32;
           }
           leaf smtp-fallback-maximum-content-size-log-permit {
             type uint32;
           }
           leaf smtp-fallback-maximum-content-size-block {
             type uint32;
           }
           leaf smtp-fallback-maximum-content-size-permit {
             type uint32;
           }
           leaf smtp-fallback-too-many-requests-log-permit {
             type uint32;
           }
           leaf smtp-fallback-too-many-requests-block {
             type uint32;
           }
           leaf smtp-fallback-too-many-requests-permit {
             type uint32;
           }
           leaf smtp-fallback-decompress-err-log-permit {
             type uint32;
           }
           leaf smtp-fallback-decompress-err-block {
             type uint32;
           }
           leaf smtp-fallback-decompress-err-permit {
             type uint32;
           }
           leaf smtp-fallback-server-conn-err-log-permit {
             type uint32;
           }
           leaf smtp-fallback-server-conn-err-block {
             type uint32;
           }
           leaf smtp-fallback-server-conn-err-permit {
             type uint32;
           }
           leaf smtp-fallback-others-log-permit {
             type uint32;
           }
           leaf smtp-fallback-others-block {
             type uint32;
           }
           leaf smtp-fallback-others-permit {
             type uint32;
           }
         }
       }
       container anti-virus-statistics-details-pop3 {
         container pop3-fallback-request-no-permit {
           leaf pop3-fallback-engine-not-ready-log-permit {
             type uint32;
           }
           leaf pop3-fallback-engine-not-ready-block {
             type uint32;
           }
           leaf pop3-fallback-engine-not-ready-permit {
             type uint32;
           }
           leaf pop3-fallback-out-resource-log-permit {
             type uint32;
           }
           leaf pop3-fallback-out-resource-block {
             type uint32;
           }
           leaf pop3-fallback-out-resource-permit {
             type uint32;
           }
           leaf pop3-fallback-timeout-log-permit {
             type uint32;
           }
           leaf pop3-fallback-timeout-block {
             type uint32;
           }
           leaf pop3-fallback-timeout-permit {
             type uint32;
           }
           leaf pop3-fallback-maximum-content-size-log-permit {
             type uint32;
           }
           leaf pop3-fallback-maximum-content-size-block {
             type uint32;
           }
           leaf pop3-fallback-maximum-content-size-permit {
             type uint32;
           }
           leaf pop3-fallback-too-many-requests-log-permit {
             type uint32;
           }
           leaf pop3-fallback-too-many-requests-block {
             type uint32;
           }
           leaf pop3-fallback-too-many-requests-permit {
             type uint32;
           }
           leaf pop3-fallback-decompress-err-log-permit {
             type uint32;
           }
           leaf pop3-fallback-decompress-err-block {
             type uint32;
           }
           leaf pop3-fallback-decompress-err-permit {
             type uint32;
           }
           leaf pop3-fallback-server-conn-err-log-permit {
             type uint32;
           }
           leaf pop3-fallback-server-conn-err-block {
             type uint32;
           }
           leaf pop3-fallback-server-conn-err-permit {
             type uint32;
           }
           leaf pop3-fallback-others-log-permit {
             type uint32;
           }
           leaf pop3-fallback-others-block {
             type uint32;
           }
           leaf pop3-fallback-others-permit {
             type uint32;
           }
         }
         container pop3-scan-request {
           leaf pop3-scan-request-total {
             type uint32;
           }
           leaf pop3-scan-request-clean {
             type uint32;
           }
           leaf pop3-scan-request-threat {
             type uint32;
           }
         }
         container pop3-fallback-request {
           leaf pop3-fallback-engine-not-ready-log-permit {
             type uint32;
           }
           leaf pop3-fallback-engine-not-ready-block {
             type uint32;
           }
           leaf pop3-fallback-engine-not-ready-permit {
             type uint32;
           }
           leaf pop3-fallback-out-resource-log-permit {
             type uint32;
           }
           leaf pop3-fallback-out-resource-block {
             type uint32;
           }
           leaf pop3-fallback-out-resource-permit {
             type uint32;
           }
           leaf pop3-fallback-timeout-log-permit {
             type uint32;
           }
           leaf pop3-fallback-timeout-block {
             type uint32;
           }
           leaf pop3-fallback-timeout-permit {
             type uint32;
           }
           leaf pop3-fallback-maximum-content-size-log-permit {
             type uint32;
           }
           leaf pop3-fallback-maximum-content-size-block {
             type uint32;
           }
           leaf pop3-fallback-maximum-content-size-permit {
             type uint32;
           }
           leaf pop3-fallback-too-many-requests-log-permit {
             type uint32;
           }
           leaf pop3-fallback-too-many-requests-block {
             type uint32;
           }
           leaf pop3-fallback-too-many-requests-permit {
             type uint32;
           }
           leaf pop3-fallback-decompress-err-log-permit {
             type uint32;
           }
           leaf pop3-fallback-decompress-err-block {
             type uint32;
           }
           leaf pop3-fallback-decompress-err-permit {
             type uint32;
           }
           leaf pop3-fallback-server-conn-err-log-permit {
             type uint32;
           }
           leaf pop3-fallback-server-conn-err-block {
             type uint32;
           }
           leaf pop3-fallback-server-conn-err-permit {
             type uint32;
           }
           leaf pop3-fallback-others-log-permit {
             type uint32;
           }
           leaf pop3-fallback-others-block {
             type uint32;
           }
           leaf pop3-fallback-others-permit {
             type uint32;
           }
         }
       }
       container anti-virus-statistics-details-imap {
         container imap-fallback-request-no-permit {
           leaf imap-fallback-engine-not-ready-log-permit {
             type uint32;
           }
           leaf imap-fallback-engine-not-ready-block {
             type uint32;
           }
           leaf imap-fallback-engine-not-ready-permit {
             type uint32;
           }
           leaf imap-fallback-out-resource-log-permit {
             type uint32;
           }
           leaf imap-fallback-out-resource-block {
             type uint32;
           }
           leaf imap-fallback-out-resource-permit {
             type uint32;
           }
           leaf imap-fallback-timeout-log-permit {
             type uint32;
           }
           leaf imap-fallback-timeout-block {
             type uint32;
           }
           leaf imap-fallback-timeout-permit {
             type uint32;
           }
           leaf imap-fallback-maximum-content-size-log-permit {
             type uint32;
           }
           leaf imap-fallback-maximum-content-size-block {
             type uint32;
           }
           leaf imap-fallback-maximum-content-size-permit {
             type uint32;
           }
           leaf imap-fallback-too-many-requests-log-permit {
             type uint32;
           }
           leaf imap-fallback-too-many-requests-block {
             type uint32;
           }
           leaf imap-fallback-too-many-requests-permit {
             type uint32;
           }
           leaf imap-fallback-decompress-err-log-permit {
             type uint32;
           }
           leaf imap-fallback-decompress-err-block {
             type uint32;
           }
           leaf imap-fallback-decompress-err-permit {
             type uint32;
           }
           leaf imap-fallback-server-conn-err-log-permit {
             type uint32;
           }
           leaf imap-fallback-server-conn-err-block {
             type uint32;
           }
           leaf imap-fallback-server-conn-err-permit {
             type uint32;
           }
           leaf imap-fallback-others-log-permit {
             type uint32;
           }
           leaf imap-fallback-others-block {
             type uint32;
           }
           leaf imap-fallback-others-permit {
             type uint32;
           }
         }
         container imap-scan-request {
           leaf imap-scan-request-total {
             type uint32;
           }
           leaf imap-scan-request-clean {
             type uint32;
           }
           leaf imap-scan-request-threat {
             type uint32;
           }
         }
         container imap-fallback-request {
           leaf imap-fallback-engine-not-ready-log-permit {
             type uint32;
           }
           leaf imap-fallback-engine-not-ready-block {
             type uint32;
           }
           leaf imap-fallback-engine-not-ready-permit {
             type uint32;
           }
           leaf imap-fallback-out-resource-log-permit {
             type uint32;
           }
           leaf imap-fallback-out-resource-block {
             type uint32;
           }
           leaf imap-fallback-out-resource-permit {
             type uint32;
           }
           leaf imap-fallback-timeout-log-permit {
             type uint32;
           }
           leaf imap-fallback-timeout-block {
             type uint32;
           }
           leaf imap-fallback-timeout-permit {
             type uint32;
           }
           leaf imap-fallback-maximum-content-size-log-permit {
             type uint32;
           }
           leaf imap-fallback-maximum-content-size-block {
             type uint32;
           }
           leaf imap-fallback-maximum-content-size-permit {
             type uint32;
           }
           leaf imap-fallback-too-many-requests-log-permit {
             type uint32;
           }
           leaf imap-fallback-too-many-requests-block {
             type uint32;
           }
           leaf imap-fallback-too-many-requests-permit {
             type uint32;
           }
           leaf imap-fallback-decompress-err-log-permit {
             type uint32;
           }
           leaf imap-fallback-decompress-err-block {
             type uint32;
           }
           leaf imap-fallback-decompress-err-permit {
             type uint32;
           }
           leaf imap-fallback-server-conn-err-log-permit {
             type uint32;
           }
           leaf imap-fallback-server-conn-err-block {
             type uint32;
           }
           leaf imap-fallback-server-conn-err-permit {
             type uint32;
           }
           leaf imap-fallback-others-log-permit {
             type uint32;
           }
           leaf imap-fallback-others-block {
             type uint32;
           }
           leaf imap-fallback-others-permit {
             type uint32;
           }
         }
       }
     }
     container anti-virus-status {
       leaf anti-virus-key-expire-date {
         type string;
         description "Anti-virus key expire date";
       }
       leaf anti-virus-update-url {
         type string;
         description "Anti-virus update URL";
       }
       leaf anti-virus-update-interval {
         type uint32;
         description "Anti-virus update interval count";
       }
       leaf anti-virus-update-status {
         type string;
         description "Anti-virus update status";
       }
       leaf anti-virus-proxy-server {
         type string;
         description "Anti-virus update via proxy server";
       }
       leaf anti-virus-update-result {
         type string;
         description "Anti-virus update results";
       }
       leaf anti-virus-fwd-mode {
         type string;
         description "Anti-virus forwarding-mode";
       }
       leaf anti-virus-signature-version {
         type string;
         description "Anti-virus signature version";
       }
       leaf anti-virus-compiler-version {
         type string;
         description "Anti-virus database compiler info";
       }
       leaf anti-virus-scan-engine-type {
         type string;
         description "Anti-virus engine type";
       }
       leaf anti-virus-scan-engine-information {
         type string;
         description "Anti-virus scan engine information";
       }
       leaf anti-virus-onbox-av-load-flavor-running {
         type string;
         description "Anti-virus onbox av load flavor running";
       }
       leaf anti-virus-onbox-av-load-flavor-config {
         type string;
         description "Anti-virus onbox av load flavor config";
       }
       leaf anti-virus-status-detail {
         type string;
         description "Anti-virus status detail";
       }
     }
     list anti-virus-performance {
       leaf fpc-slot {
         type uint32;
         description "FPC slot";
       }
       leaf pic-slot {
         type uint32;
         description "PIC slot";
       }
       leaf anti-virus-onbox-av-cpu-usage {
         type uint32;
         description "Anti-virus onbox av cpu usage";
       }
     }
   }
   grouping url-feed-block {
     container url-feed-status {
       leaf url-feed-name {
         type string;
         description "Feed name";
       }
       leaf url-feed-url {
         type string;
         description "Feed download URL";
       }
       leaf url-feed-rt-instance {
         type string;
         description "Feed routing-instance";
       }
       leaf url-feed-proxy-settings {
         type string;
         description "Feed proxy settings";
       }
       leaf url-feed-auto-update {
         type string;
         description "Feed auto update";
       }
       leaf url-feed-interval {
         type uint32;
         description "Feed interval time";
       }
       leaf url-feed-url-pattern {
         type string;
         description "Feed corresponding url-pattern";
       }
       leaf url-feed-last-update-time {
         type string;
         description "Feed last update time";
       }
       leaf url-feed-current-status {
         type string;
         description "Feed current status";
       }
       leaf url-feed-error {
         type string;
         description "Feed error";
       }
       leaf url-feed-invalid-urls-count {
         type uint32;
         description "Invalid URLs count";
       }
       leaf url-feed-ignored-urls-count {
         type uint32;
         description "Ignored URLs count";
       }
     }
     container url-feed-status-option-invalid-urls {
       leaf url-feed-url {
         type string;
         description "Feed download URL";
       }
     }
     container url-feed-status-option-ignored-urls {
       leaf url-feed-url {
         type string;
         description "Feed download URL";
       }
     }
   }
   grouping utmd-web-filtering-block {
     container utmd-web-filtering-statistics {
       leaf total-requests {
         type uint64;
         description "Total requests count";
       }
       leaf white-list-hit {
         type uint64;
         description "White list hits count";
       }
       leaf black-list-hit {
         type uint64;
         description "Black list hits count";
       }
       leaf default-action-hit {
         type uint64;
         description "Default action hits count";
       }
       leaf no-license-permit {
         type uint64;
         description "No license permit count";
       }
       leaf queries-to-server {
         type uint64;
         description "Queries to server count";
       }
       leaf server-reply-permit {
         type uint64;
         description "Server replies permit count";
       }
       leaf server-reply-block {
         type uint64;
         description "Server replies block count";
       }
       leaf server-reply-quarantine {
         type uint64;
         description "Quarantine count for Server reply";
       }
       leaf server-reply-quarantine-block {
         type uint64;
         description "Quarantine count for Server reply block";
       }
       leaf server-reply-quarantine-permit {
         type uint64;
         description "Quarantine count for Server reply permit";
       }
       leaf custom-category-permit {
         type uint64;
         description "Custom category permit count";
       }
       leaf custom-category-block {
         type uint64;
         description "Custom category block count";
       }
       leaf custom-category-quarantine {
         type uint64;
         description "Quarantine count for Custom Category";
       }
       leaf custom-category-quarantine-block {
         type uint64;
         description "Quarantine count for Custom Category block";
       }
       leaf custom-category-quarantine-permit {
         type uint64;
         description "Quarantine count for Custom Category permit";
       }
       leaf site-reputation-permit {
         type uint64;
         description "Site reputation permit count";
       }
       leaf site-reputation-block {
         type uint64;
         description "Site reputation block count";
       }
       leaf site-reputation-quarantine {
         type uint64;
         description "Quarantine count for site reputation";
       }
       leaf site-reputation-quarantine-block {
         type uint64;
         description "Quarantine count for site reputation block";
       }
       leaf site-reputation-quarantine-permit {
         type uint64;
         description "Quarantine count for site reputation permit";
       }
       leaf site-reputation-category {
         type uint64;
         description "Site reputation action due to category configuration";
       }
       leaf site-reputation-global {
         type uint64;
         description "Site reputation action due to global configuration";
       }
       leaf cache-hit-permit {
         type uint64;
         description "Cache hit permit count";
       }
       leaf cache-hit-block {
         type uint64;
         description "Cache hit block count";
       }
       leaf cache-hit-quarantine {
         type uint64;
         description "Quarantine Cache hit count";
       }
       leaf cache-hit-quarantine-block {
         type uint64;
         description "Quarantine Cache hit block count";
       }
       leaf cache-hit-quarantine-permit {
         type uint64;
         description "Quarantie Cache hit permit count";
       }
       leaf safe-search-redirect {
         type uint64;
         description "Safe-search redirect count";
       }
       leaf safe-search-rewrite {
         type uint64;
         description "Safe-search rewrite count";
       }
       leaf sni-queries-to-server {
         type uint64;
         description "SNI pre-check queries to server";
       }
       leaf sni-server-responses {
         type uint64;
         description "SNI pre-check server responses";
       }
       leaf web-filtering-session-total {
         type uint64;
         description "Web-filtering session total count";
       }
       leaf web-filtering-session-inuse {
         type uint64;
         description "Web-filtering session in use count";
       }
       leaf web-filtering-session-dynamic-policy {
         type uint64;
         description "Web-filtering session matched with dynamic policy";
       }
       leaf web-filtering-session-default-policy {
         type uint64;
         description "Web-filtering session matched with default policy";
       }
       leaf web-filtering-session-final-policy {
         type uint64;
         description "Web-filtering session matched with final policy";
       }
       container web-filtering-fallback {
         leaf fallback-permit-default {
           type uint64;
           description "Fallback default permit count";
         }
         leaf fallback-block-default {
           type uint64;
           description "Fallback default block count";
         }
         leaf fallback-permit-timeout {
           type uint64;
           description "Fallback timeout permit count";
         }
         leaf fallback-block-timeout {
           type uint64;
           description "Fallback timeout block count";
         }
         leaf fallback-permit-connectivity {
           type uint64;
           description "Fallback connectivity permit count";
         }
         leaf fallback-block-connectivity {
           type uint64;
           description "Fallback connectivity block count";
         }
         leaf fallback-permit-too-many-requests {
           type uint64;
           description "Fallback too many requests permit count";
         }
         leaf fallback-block-too-many-requests {
           type uint64;
           description "Fallback too many requests permit count";
         }
       }
     }
     list utmd-web-filtering-statistics-fpc {
       container utmd-web-filtering-statistics {
         leaf total-requests {
           type uint64;
           description "Total requests count";
         }
         leaf white-list-hit {
           type uint64;
           description "White list hits count";
         }
         leaf black-list-hit {
           type uint64;
           description "Black list hits count";
         }
         leaf default-action-hit {
           type uint64;
           description "Default action hits count";
         }
         leaf no-license-permit {
           type uint64;
           description "No license permit count";
         }
         leaf queries-to-server {
           type uint64;
           description "Queries to server count";
         }
         leaf server-reply-permit {
           type uint64;
           description "Server replies permit count";
         }
         leaf server-reply-block {
           type uint64;
           description "Server replies block count";
         }
         leaf server-reply-quarantine {
           type uint64;
           description "Quarantine count for Server reply";
         }
         leaf server-reply-quarantine-block {
           type uint64;
           description "Quarantine count for Server reply block";
         }
         leaf server-reply-quarantine-permit {
           type uint64;
           description "Quarantine count for Server reply permit";
         }
         leaf custom-category-permit {
           type uint64;
           description "Custom category permit count";
         }
         leaf custom-category-block {
           type uint64;
           description "Custom category block count";
         }
         leaf custom-category-quarantine {
           type uint64;
           description "Quarantine count for Custom Category";
         }
         leaf custom-category-quarantine-block {
           type uint64;
           description "Quarantine count for Custom Category block";
         }
         leaf custom-category-quarantine-permit {
           type uint64;
           description "Quarantine count for Custom Category permit";
         }
         leaf site-reputation-permit {
           type uint64;
           description "Site reputation permit count";
         }
         leaf site-reputation-block {
           type uint64;
           description "Site reputation block count";
         }
         leaf site-reputation-quarantine {
           type uint64;
           description "Quarantine count for site reputation";
         }
         leaf site-reputation-quarantine-block {
           type uint64;
           description "Quarantine count for site reputation block";
         }
         leaf site-reputation-quarantine-permit {
           type uint64;
           description "Quarantine count for site reputation permit";
         }
         leaf site-reputation-category {
           type uint64;
           description "Site reputation action due to category configuration";
         }
         leaf site-reputation-global {
           type uint64;
           description "Site reputation action due to global configuration";
         }
         leaf cache-hit-permit {
           type uint64;
           description "Cache hit permit count";
         }
         leaf cache-hit-block {
           type uint64;
           description "Cache hit block count";
         }
         leaf cache-hit-quarantine {
           type uint64;
           description "Quarantine Cache hit count";
         }
         leaf cache-hit-quarantine-block {
           type uint64;
           description "Quarantine Cache hit block count";
         }
         leaf cache-hit-quarantine-permit {
           type uint64;
           description "Quarantie Cache hit permit count";
         }
         leaf safe-search-redirect {
           type uint64;
           description "Safe-search redirect count";
         }
         leaf safe-search-rewrite {
           type uint64;
           description "Safe-search rewrite count";
         }
         leaf sni-queries-to-server {
           type uint64;
           description "SNI pre-check queries to server";
         }
         leaf sni-server-responses {
           type uint64;
           description "SNI pre-check server responses";
         }
         leaf web-filtering-session-total {
           type uint64;
           description "Web-filtering session total count";
         }
         leaf web-filtering-session-inuse {
           type uint64;
           description "Web-filtering session in use count";
         }
         leaf web-filtering-session-dynamic-policy {
           type uint64;
           description "Web-filtering session matched with dynamic policy";
         }
         leaf web-filtering-session-default-policy {
           type uint64;
           description "Web-filtering session matched with default policy";
         }
         leaf web-filtering-session-final-policy {
           type uint64;
           description "Web-filtering session matched with final policy";
         }
         container web-filtering-fallback {
           leaf fallback-permit-default {
             type uint64;
             description "Fallback default permit count";
           }
           leaf fallback-block-default {
             type uint64;
             description "Fallback default block count";
           }
           leaf fallback-permit-timeout {
             type uint64;
             description "Fallback timeout permit count";
           }
           leaf fallback-block-timeout {
             type uint64;
             description "Fallback timeout block count";
           }
           leaf fallback-permit-connectivity {
             type uint64;
             description "Fallback connectivity permit count";
           }
           leaf fallback-block-connectivity {
             type uint64;
             description "Fallback connectivity block count";
           }
           leaf fallback-permit-too-many-requests {
             type uint64;
             description "Fallback too many requests permit count";
           }
           leaf fallback-block-too-many-requests {
             type uint64;
             description "Fallback too many requests permit count";
           }
         }
       }
       leaf fpc-slot {
         type uint32;
         description "FPC slot";
       }
       leaf pic-slot {
         type uint32;
         description "PIC slot";
       }
     }
     container utmd-web-filtering-status {
       leaf web-filtering-type {
         type string;
         description "Web-filtering type";
       }
       leaf web-filtering-server-status {
         type string;
         description "Web-filtering server status";
       }
       leaf web-filtering-status-reason {
         type string;
         description "Web-filtering server status reason";
       }
       leaf web-filtering-parser-status {
         type string;
         description "Web-filtering JDPI status";
       }
       leaf web-filtering-dynapp-status {
         type string;
         description "Web-filtering dynapp selection status";
       }
     }
     list utmd-web-filtering-status-fpc {
       leaf fpc-slot {
         type uint32;
         description "FPC slot";
       }
       leaf pic-slot {
         type uint32;
         description "PIC slot";
       }
       leaf web-filtering-server-status {
         type string;
         description "Web-filtering server status";
       }
       leaf web-filtering-status-reason {
         type string;
         description "Web-filtering server status reason";
       }
     }
   }
   grouping ewf-cache-block {
     container ewf-cache-abs-tree {
       list ewf-cache-abs-tree-host {
         leaf ewf-cache-abs-tree-host-name {
           type string;
           description "Host name";
         }
       }
     }
   }
   grouping ewf-cache-preload-block {
     container ewf-cache-preload-status {
       container ewf-cache-preload-dld-status {
         leaf prld-dld-feed-type {
           type string;
           description "Type of the URL Feed";
         }
         leaf prld-dld-pkg-url {
           type string;
           description "URL of the package";
         }
         leaf prld-dld-pkg-version {
           type string;
           description "Version of the package";
         }
         leaf prld-dld-status-msg {
           type string;
           description "Status of the download";
         }
         leaf prld-dld-time-stamp {
           type string;
           description "Time of the download";
         }
       }
       container ewf-cache-preload-ins-status {
         leaf prld-ins-feed-type {
           type string;
           description "Type of the URL Feed";
         }
         leaf prld-ins-pkg-url {
           type string;
           description "URL of the package";
         }
         leaf prld-ins-pkg-version {
           type string;
           description "Version of the package";
         }
         leaf prld-ins-status-msg {
           type string;
           description "Status of install";
         }
         leaf prld-ins-time-stamp {
           type string;
           description "Time of install";
         }
       }
       container ewf-cache-preload-act-status {
         leaf prld-act-feed-type {
           type string;
           description "Type of the URL Feed";
         }
         leaf prld-act-feed-db {
           type string;
           description "Location of the feed";
         }
         leaf prld-act-feed-version {
           type string;
           description "Version of the feed";
         }
         leaf prld-act-status-msg {
           type string;
           description "Status of load active";
         }
         leaf prld-act-time-stamp {
           type string;
           description "Time of load active";
         }
       }
       container ewf-cache-local-feed-db-info {
         leaf prld-ins-abs-urls-db {
           type string;
           description "Absolute URL feed DB file";
         }
         leaf prld-ins-abs-urls-db-version {
           type string;
           description "Absolute URL feed DB version";
         }
         leaf prld-ins-srv-names-db {
           type string;
           description "Server Names feed DB file";
         }
         leaf prld-ins-srv-names-db-version {
           type string;
           description "Server Names feed DB version";
         }
       }
       container ewf-cache-preload-cfg-status {
         leaf prld-cfg-pkg-url {
           type string;
           description "URL of the package";
         }
         leaf prld-cfg-ri-name {
           type string;
           description "Routing instance used for download";
         }
         leaf prld-cfg-auto-preload {
           type string;
           description "Automatic preload status";
         }
         leaf prld-cfg-feed-type {
           type string;
           description "Type of the URL Feed";
         }
         leaf prld-cfg-auto-interval {
           type int32;
           description "Automatic download and preload interval";
         }
         leaf prld-cfg-retry-interval {
           type int32;
           description "Retry interval if download fails";
         }
         leaf prld-cfg-prld-next-due {
           type string;
           description "Time remaining to trigger auto preload";
         }
       }
     }
     leaf ewf-cache-preload-result {
       type string;
       description "Cache preload result of the request";
     }
   }
   grouping category-block {
     container category-status {
       leaf category-install-version {
         type uint32;
       }
       leaf category-download-version {
         type uint32;
       }
       leaf category-update-status {
         type string;
       }
     }
     container category-base-filter {
       leaf base-filter-name {
         type string;
       }
       container base-filter-category-action {
         leaf category-name {
           type string;
         }
         leaf category-action {
           type string;
         }
       }
     }
     container category-category {
       leaf category-name {
         type string;
       }
     }
   }
   grouping enhanced-to-ng-migrate-status-block {
     container category-migrate-to-ng-juniper-status {
       leaf category-no-migration {
         type string;
       }
       leaf category-migrate-status {
         type string;
       }
     }
   }
   grouping content-filtering-block {
     container content-filtering-statistics {
       container passed-blocked {
         leaf content-filtering-command-blocked {
           type uint32;
           description "Content-filtering command blocked count";
         }
         leaf content-filtering-mime-blocked {
           type uint32;
           description "Content-filtering mime blocked count";
         }
         leaf content-filtering-extension-blocked {
           type uint32;
           description "Content-filtering extension blocked count";
         }
         leaf content-filtering-activex-blocked {
           type uint32;
           description "Content-filtering activex blocked count";
         }
         leaf content-filtering-java-applet-blocked {
           type uint32;
           description "Content-filtering java applet blocked count";
         }
         leaf content-filtering-exe-blocked {
           type uint32;
           description "Content-filtering exe blocked count";
         }
         leaf content-filtering-zip-blocked {
           type uint32;
           description "Content-filtering zip blocked count";
         }
         leaf content-filtering-cookie-blocked {
           type uint32;
           description "Content-filtering cookie blocked count";
         }
         leaf content-filtering-command-passed {
           type uint32;
           description "Content-filtering command passed count";
         }
         leaf content-filtering-mime-passed {
           type uint32;
           description "Content-filtering mime passed count";
         }
         leaf content-filtering-extension-passed {
           type uint32;
           description "Content-filtering extension passed count";
         }
         leaf content-filtering-activex-passed {
           type uint32;
           description "Content-filtering activex passed count";
         }
         leaf content-filtering-java-applet-passed {
           type uint32;
           description "Content-filtering java applet passed count";
         }
         leaf content-filtering-exe-passed {
           type uint32;
           description "Content-filtering exe passed count";
         }
         leaf content-filtering-zip-passed {
           type uint32;
           description "Content-filtering zip passed count";
         }
         leaf content-filtering-cookie-passed {
           type uint32;
           description "Content-filtering cookie passed count";
         }
       }
       container cf-global-stats {
         leaf content-filtering-rule-sets-count {
           type uint32;
           description "Content-filtering rule sets count";
         }
         leaf content-filtering-rule-set-add-fail {
           type uint32;
           description "Content-filtering rule set add failure count";
         }
         leaf content-filtering-rule-set-del-fail {
           type uint32;
           description "Content-filtering rule set delete failure count";
         }
         leaf content-filtering-rules-count {
           type uint32;
           description "Content-filtering rules count";
         }
         leaf content-filtering-rule-add-fail {
           type uint32;
           description "Content-filtering rule add failure count";
         }
         leaf content-filtering-rule-del-fail {
           type uint32;
           description "Content-filtering rule delete failure count";
         }
         leaf content-filtering-rule-mod-ok {
           type uint32;
           description "Content-filtering rule modify succeeded count";
         }
         leaf content-filtering-rule-mod-fail {
           type uint32;
           description "Content-filtering rule modify failure count";
         }
         leaf content-filtering-fatal-errors {
           type uint32;
           description "Content-filtering fatal error count";
         }
         leaf content-filtering-malloc-fail {
           type uint32;
           description "Content-filtering malloc failure count";
         }
         leaf content-filtering-sanity-fail {
           type uint32;
           description "Content-filtering sanity errors count";
         }
         leaf content-filtering-memory-inuse {
           type uint32;
           description "Content-filtering malloc blocks in use";
         }
       }
       container cf-policy-stats {
         leaf content-filtering-rules-app-any {
           type uint32;
           description "Content-filtering rules count with application any";
         }
         leaf content-filtering-rules-app-http {
           type uint32;
           description "Content-filtering rules count with application http";
         }
         leaf content-filtering-rules-app-ftp {
           type uint32;
           description "Content-filtering rules count with application ftp";
         }
         leaf content-filtering-rules-app-smtp {
           type uint32;
           description "Content-filtering rules count with application smtp";
         }
         leaf content-filtering-rules-app-imap {
           type uint32;
           description "Content-filtering rules count with application imap";
         }
         leaf content-filtering-rules-app-pop3 {
           type uint32;
           description "Content-filtering rules count with application pop3";
         }
         leaf content-filtering-blocked-dir-download {
           type uint32;
           description "Number of times content blocked in download direction";
         }
         leaf content-filtering-blocked-dir-upload {
           type uint32;
           description "Number of times content blocked in upload direction";
         }
         leaf content-filtering-blocked-app-http {
           type uint32;
           description "Number of times content blocked in http application";
         }
         leaf content-filtering-blocked-app-ftp {
           type uint32;
           description "Number of times content blocked in ftp application";
         }
         leaf content-filtering-blocked-app-smtp {
           type uint32;
           description "Number of times content blocked in smtp application";
         }
         leaf content-filtering-blocked-app-imap {
           type uint32;
           description "Number of times content blocked in imap application";
         }
         leaf content-filtering-blocked-app-pop3 {
           type uint32;
           description "Number of times content blocked in pop3 application";
         }
         leaf content-filtering-matched-act-no-action {
           type uint32;
           description "Number of times a rule with action no-action is matched";
         }
         leaf content-filtering-matched-act-block {
           type uint32;
           description "Number of times a rule with action block is matched";
         }
         leaf content-filtering-matched-act-client-reset {
           type uint32;
           description "Number of times a rule with action client reset is matched";
         }
         leaf content-filtering-matched-act-server-reset {
           type uint32;
           description "Number of times a rule with action server reset is matched";
         }
         leaf content-filtering-matched-act-client-server-reset {
           type uint32;
           description "Number of times a rule with action client server reset is matched";
         }
         leaf content-filtering-blocked-ftype-unknown {
           type uint32;
           description "Number of times unknown file-type is blocked";
         }
         leaf content-filtering-blocked-ftype-7z {
           type uint32;
           description "Number of times 7z file is blocked";
         }
         leaf content-filtering-blocked-ftype-ace {
           type uint32;
           description "Number of times ace file is blocked";
         }
         leaf content-filtering-blocked-ftype-applesingle {
           type uint32;
           description "Number of times applesingle file is blocked";
         }
         leaf content-filtering-blocked-ftype-arj {
           type uint32;
           description "Number of times arj file is blocked";
         }
         leaf content-filtering-blocked-ftype-bzip {
           type uint32;
           description "Number of times bzip file is blocked";
         }
         leaf content-filtering-blocked-ftype-diskdupe {
           type uint32;
           description "Number of times diskdupe file is blocked";
         }
         leaf content-filtering-blocked-ftype-dos {
           type uint32;
           description "Number of times dos file is blocked";
         }
         leaf content-filtering-blocked-ftype-eicar {
           type uint32;
           description "Number of times eicar file is blocked";
         }
         leaf content-filtering-blocked-ftype-elf {
           type uint32;
           description "Number of times elf file is blocked";
         }
         leaf content-filtering-blocked-ftype-emf {
           type uint32;
           description "Number of times emf file is blocked";
         }
         leaf content-filtering-blocked-ftype-eml {
           type uint32;
           description "Number of times eml file is blocked";
         }
         leaf content-filtering-blocked-ftype-flash {
           type uint32;
           description "Number of times flash file is blocked";
         }
         leaf content-filtering-blocked-ftype-gea {
           type uint32;
           description "Number of times gea file is blocked";
         }
         leaf content-filtering-blocked-ftype-gzip {
           type uint32;
           description "Number of times gzip file is blocked";
         }
         leaf content-filtering-blocked-ftype-ha {
           type uint32;
           description "Number of times ha file is blocked";
         }
         leaf content-filtering-blocked-ftype-hlp {
           type uint32;
           description "Number of times hlp file is blocked";
         }
         leaf content-filtering-blocked-ftype-hybris {
           type uint32;
           description "Number of times hybris file is blocked";
         }
         leaf content-filtering-blocked-ftype-itsf {
           type uint32;
           description "Number of times itsf file is blocked";
         }
         leaf content-filtering-blocked-ftype-java {
           type uint32;
           description "Number of times java file java blocked";
         }
         leaf content-filtering-blocked-ftype-jmp {
           type uint32;
           description "Number of times jmp file is blocked";
         }
         leaf content-filtering-blocked-ftype-jpeg {
           type uint32;
           description "Number of times jpeg file is blocked";
         }
         leaf content-filtering-blocked-ftype-lha {
           type uint32;
           description "Number of times lha file is blocked";
         }
         leaf content-filtering-blocked-ftype-lnk {
           type uint32;
           description "Number of times lnk file is blocked";
         }
         leaf content-filtering-blocked-ftype-map {
           type uint32;
           description "Number of times map file is blocked";
         }
         leaf content-filtering-blocked-ftype-mime {
           type uint32;
           description "Number of times mime file is blocked";
         }
         leaf content-filtering-blocked-ftype-msasf {
           type uint32;
           description "Number of times ms asf file is blocked";
         }
         leaf content-filtering-blocked-ftype-mscf {
           type uint32;
           description "Number of times mscf file is blocked";
         }
         leaf content-filtering-blocked-ftype-msi {
           type uint32;
           description "Number of times msi file is blocked";
         }
         leaf content-filtering-blocked-ftype-mso {
           type uint32;
           description "Number of times mso file is blocked";
         }
         leaf content-filtering-blocked-ftype-ntdetect {
           type uint32;
           description "Number of times ntdetect file is blocked";
         }
         leaf content-filtering-blocked-ftype-ole {
           type uint32;
           description "Number of times ole file is blocked";
         }
         leaf content-filtering-blocked-ftype-paquet {
           type uint32;
           description "Number of times paquet file is blocked";
         }
         leaf content-filtering-blocked-ftype-pdf {
           type uint32;
           description "Number of times pdf file is blocked";
         }
         leaf content-filtering-blocked-ftype-pe {
           type uint32;
           description "Number of times pe file is blocked";
         }
         leaf content-filtering-blocked-ftype-perl {
           type uint32;
           description "Number of times perl file is blocked";
         }
         leaf content-filtering-blocked-ftype-pif {
           type uint32;
           description "Number of times pif file is blocked";
         }
         leaf content-filtering-blocked-ftype-png {
           type uint32;
           description "Number of times png file is blocked";
         }
         leaf content-filtering-blocked-ftype-rar {
           type uint32;
           description "Number of times rar file is blocked";
         }
         leaf content-filtering-blocked-ftype-reg {
           type uint32;
           description "Number of times reg file is blocked";
         }
         leaf content-filtering-blocked-ftype-rtf {
           type uint32;
           description "Number of times rtf file is blocked";
         }
         leaf content-filtering-blocked-ftype-script {
           type uint32;
           description "Number of times script file is blocked";
         }
         leaf content-filtering-blocked-ftype-sh {
           type uint32;
           description "Number of times sh file is blocked";
         }
         leaf content-filtering-blocked-ftype-sis {
           type uint32;
           description "Number of times sis file is blocked";
         }
         leaf content-filtering-blocked-ftype-spis {
           type uint32;
           description "Number of times spis file is blocked";
         }
         leaf content-filtering-blocked-ftype-sys {
           type uint32;
           description "Number of times sys file is blocked";
         }
         leaf content-filtering-blocked-ftype-tar {
           type uint32;
           description "Number of times tar file is blocked";
         }
         leaf content-filtering-blocked-ftype-vba {
           type uint32;
           description "Number of times vba file is blocked";
         }
         leaf content-filtering-blocked-ftype-wmf {
           type uint32;
           description "Number of times wmf file is blocked";
         }
         leaf content-filtering-blocked-ftype-wsf {
           type uint32;
           description "Number of times wsf file is blocked";
         }
         leaf content-filtering-blocked-ftype-xml {
           type uint32;
           description "Number of times xml file is blocked";
         }
         leaf content-filtering-blocked-ftype-xz {
           type uint32;
           description "Number of times xz file is blocked";
         }
         leaf content-filtering-blocked-ftype-zip {
           type uint32;
           description "Number of times zip file is blocked";
         }
       }
     }
     list content-filtering-statistics-fpc {
       container content-filtering-statistics {
         container passed-blocked {
           leaf content-filtering-command-passed {
             type uint32;
             description "Content-filtering command passed count";
           }
           leaf content-filtering-mime-passed {
             type uint32;
             description "Content-filtering mime passed count";
           }
           leaf content-filtering-extension-passed {
             type uint32;
             description "Content-filtering extension passed count";
           }
           leaf content-filtering-activex-passed {
             type uint32;
             description "Content-filtering activex passed count";
           }
           leaf content-filtering-java-applet-passed {
             type uint32;
             description "Content-filtering java applet passed count";
           }
           leaf content-filtering-exe-passed {
             type uint32;
             description "Content-filtering exe passed count";
           }
           leaf content-filtering-zip-passed {
             type uint32;
             description "Content-filtering zip passed count";
           }
           leaf content-filtering-cookie-passed {
             type uint32;
             description "Content-filtering cookie passed count";
           }
           leaf content-filtering-command-blocked {
             type uint32;
             description "Content-filtering command blocked count";
           }
           leaf content-filtering-mime-blocked {
             type uint32;
             description "Content-filtering mime blocked count";
           }
           leaf content-filtering-extension-blocked {
             type uint32;
             description "Content-filtering extension blocked count";
           }
           leaf content-filtering-activex-blocked {
             type uint32;
             description "Content-filtering activex blocked count";
           }
           leaf content-filtering-java-applet-blocked {
             type uint32;
             description "Content-filtering java applet blocked count";
           }
           leaf content-filtering-exe-blocked {
             type uint32;
             description "Content-filtering exe blocked count";
           }
           leaf content-filtering-zip-blocked {
             type uint32;
             description "Content-filtering zip blocked count";
           }
           leaf content-filtering-cookie-blocked {
             type uint32;
             description "Content-filtering cookie blocked count";
           }
         }
       }
       leaf fpc-slot {
         type uint32;
         description "FPC slot";
       }
       leaf pic-slot {
         type uint32;
         description "PIC slot";
       }
     }
     container content-filtering-status {
       leaf content-filtering-status-value {
         type string;
         description "Content-filtering status";
       }
       leaf content-filtering-profile-name {
         type string;
         description "Content-filtering profile name";
       }
     }
     container content-filtering-dpi-status {
       leaf content-filtering-dpi-status-value {
         type string;
         description "Content-filtering JDPI parser status";
       }
       leaf content-filtering-dynapp-status {
         type string;
         description "Content-filtering dynapp selection status";
       }
     }
   }
   grouping anti-spam-block {
     container anti-spam-statistics {
       leaf total-connections {
         type uint32;
         description "Total connections";
       }
       leaf denied-connections {
         type uint32;
         description "Denied connections";
       }
       leaf total-greetings {
         type uint32;
         description "Total number of connection greetings";
       }
       leaf denied-greetings {
         type uint32;
         description "Number of connection greetings that were denied";
       }
       leaf total-emails-scanned {
         type uint32;
         description "Total e-mail scanned";
       }
       leaf as-white-list-hit {
         type uint32;
         description "Antispam White list hit";
       }
       leaf as-black-list-hit {
         type uint32;
         description "Antispam Black list hit";
       }
       leaf spam-total {
         type uint32;
         description "Spam total";
       }
       leaf spam-tagged {
         type uint32;
         description "Spam tagged";
       }
       leaf spam-dropped {
         type uint32;
         description "Spam emails";
       }
       leaf dns-errors {
         type uint32;
         description "Number of DNS errors";
       }
       leaf timeout-errors {
         type uint32;
         description "Number of timeout errors";
       }
       leaf return-errors {
         type uint32;
         description "Number of return errors";
       }
       leaf invalid-parameter-errors {
         type uint32;
         description "Number of invalid parameter errors";
       }
       leaf statistics-start-time {
         type string;
         description "Anti-Spam engine start time";
       }
       container statistics-last-10-days {
         leaf day1-permitted-emails {
           type uint32;
           description "Day1 permitted emails";
         }
         leaf day1-spam-emails {
           type uint32;
           description "Day1 spam emails";
         }
         leaf day2-permitted-emails {
           type uint32;
           description "Day2 permitted emails";
         }
         leaf day2-spam-emails {
           type uint32;
           description "Day2 spam emails";
         }
         leaf day3-permitted-emails {
           type uint32;
           description "Day3 permitted emails";
         }
         leaf day3-spam-emails {
           type uint32;
           description "Day3 spam emails";
         }
         leaf day4-permitted-emails {
           type uint32;
           description "Day4 permitted emails";
         }
         leaf day4-spam-emails {
           type uint32;
           description "Day4 spam emails";
         }
         leaf day5-permitted-emails {
           type uint32;
           description "Day5 permitted emails";
         }
         leaf day5-spam-emails {
           type uint32;
           description "Day5 spam emails";
         }
         leaf day6-permitted-emails {
           type uint32;
           description "Day6 permitted emails";
         }
         leaf day6-spam-emails {
           type uint32;
           description "Day6 spam emails";
         }
         leaf day7-permitted-emails {
           type uint32;
           description "Day7 permitted emails";
         }
         leaf day7-spam-emails {
           type uint32;
           description "Day7 spam emails";
         }
         leaf day8-permitted-emails {
           type uint32;
           description "Day8 permitted emails";
         }
         leaf day8-spam-emails {
           type uint32;
           description "Day8 spam emails";
         }
         leaf day9-permitted-emails {
           type uint32;
           description "Day9 permitted emails";
         }
         leaf day9-spam-emails {
           type uint32;
           description "Day9 spam emails";
         }
         leaf day10-permitted-emails {
           type uint32;
           description "Day10 permitted emails";
         }
         leaf day10-spam-emails {
           type uint32;
           description "Day10 spam emails";
         }
       }
     }
     list anti-spam-statistics-fpc {
       container anti-spam-statistics {
         leaf total-connections {
           type uint32;
           description "Total connections";
         }
         leaf denied-connections {
           type uint32;
           description "Denied connections";
         }
         leaf total-greetings {
           type uint32;
           description "Total number of connection greetings";
         }
         leaf denied-greetings {
           type uint32;
           description "Number of connection greetings that were denied";
         }
         leaf total-emails-scanned {
           type uint32;
           description "Total e-mail scanned";
         }
         leaf as-white-list-hit {
           type uint32;
           description "Antispam White list hit";
         }
         leaf as-black-list-hit {
           type uint32;
           description "Antispam Black list hit";
         }
         leaf spam-total {
           type uint32;
           description "Spam total";
         }
         leaf spam-tagged {
           type uint32;
           description "Spam tagged";
         }
         leaf spam-dropped {
           type uint32;
           description "Spam emails";
         }
         leaf dns-errors {
           type uint32;
           description "Number of DNS errors";
         }
         leaf timeout-errors {
           type uint32;
           description "Number of timeout errors";
         }
         leaf return-errors {
           type uint32;
           description "Number of return errors";
         }
         leaf invalid-parameter-errors {
           type uint32;
           description "Number of invalid parameter errors";
         }
         leaf statistics-start-time {
           type string;
           description "Anti-Spam engine start time";
         }
         container statistics-last-10-days {
           leaf day1-permitted-emails {
             type uint32;
             description "Day1 permitted emails";
           }
           leaf day1-spam-emails {
             type uint32;
             description "Day1 spam emails";
           }
           leaf day2-permitted-emails {
             type uint32;
             description "Day2 permitted emails";
           }
           leaf day2-spam-emails {
             type uint32;
             description "Day2 spam emails";
           }
           leaf day3-permitted-emails {
             type uint32;
             description "Day3 permitted emails";
           }
           leaf day3-spam-emails {
             type uint32;
             description "Day3 spam emails";
           }
           leaf day4-permitted-emails {
             type uint32;
             description "Day4 permitted emails";
           }
           leaf day4-spam-emails {
             type uint32;
             description "Day4 spam emails";
           }
           leaf day5-permitted-emails {
             type uint32;
             description "Day5 permitted emails";
           }
           leaf day5-spam-emails {
             type uint32;
             description "Day5 spam emails";
           }
           leaf day6-permitted-emails {
             type uint32;
             description "Day6 permitted emails";
           }
           leaf day6-spam-emails {
             type uint32;
             description "Day6 spam emails";
           }
           leaf day7-permitted-emails {
             type uint32;
             description "Day7 permitted emails";
           }
           leaf day7-spam-emails {
             type uint32;
             description "Day7 spam emails";
           }
           leaf day8-permitted-emails {
             type uint32;
             description "Day8 permitted emails";
           }
           leaf day8-spam-emails {
             type uint32;
             description "Day8 spam emails";
           }
           leaf day9-permitted-emails {
             type uint32;
             description "Day9 permitted emails";
           }
           leaf day9-spam-emails {
             type uint32;
             description "Day9 spam emails";
           }
           leaf day10-permitted-emails {
             type uint32;
             description "Day10 permitted emails";
           }
           leaf day10-spam-emails {
             type uint32;
             description "Day10 spam emails";
           }
         }
       }
       leaf fpc-slot {
         type uint32;
         description "FPC slot";
       }
       leaf pic-slot {
         type uint32;
         description "PIC slot";
       }
     }
     container anti-spam-status {
       container dns-server-setting {
         leaf primary {
           type string;
           description "Primary DNS server";
         }
         leaf primary-source-interface {
           type string;
           description "Primary source interface";
         }
         leaf secondary {
           type string;
           description "Secondary DNS server";
         }
         leaf secondary-source-interface {
           type string;
           description "Secondary source interface";
         }
         leaf ternary {
           type string;
           description "Ternary DNS server";
         }
         leaf ternary-source-interface {
           type string;
           description "Ternary source interface";
         }
       }
       container anti-spam-type {
         leaf anti-spam-type-status {
           type string;
           description "Anti-spam type";
         }
       }
     }
   }
   grouping security-dynamic-address-block {
     leaf da-ipc-entry-add {
       type int32;
       description "Num of entry add IPC message object created";
     }
     leaf da-ipc-entry-del {
       type int32;
       description "Num of entry del IPC message object created";
     }
     leaf da-ipc-entry-trace-option {
       type int32;
       description "Num of trace option IPC message object created";
     }
     leaf da-ipc-batch-sent {
       type int32;
       description "Num of IPC message batches have been sent";
     }
     leaf da-malloc-failure {
       type int32;
       description "Counter of malloc failure";
     }
     leaf da-ipc-init {
       type string;
       description "Timestamp for IPC initialization";
     }
     leaf da-pfe-conn-first {
       type string;
       description "Timestamp for first PFE connection";
     }
     leaf da-pfe-conn-last {
       type string;
       description "Timestamp for last PFE connection";
     }
     leaf da-pfe-conn-failure {
       type string;
       description "Timestamp for last PFE connection failure";
     }
     leaf da-instance-name {
       type string;
       description "Name of dynamic address instance";
     }
     leaf da-ip-entry-idx {
       type int32;
       description "Position in found IP entries";
     }
     leaf da-ip-start {
       type string;
       description "Numerically minimal IP address within the range";
     }
     leaf da-ip-end {
       type string;
       description "Numerically maximal IP address within the range";
     }
     leaf da-name {
       type string;
       description "Dynamic address name";
     }
     leaf da-country-code {
       type string;
       description "Country code";
     }
     leaf da-lsys-name {
       type string;
       description "Logical system name";
     }
     leaf da-lsysinfo {
       type string;
       description "Dynamic address logical-system tenant name";
     }
     leaf feed-ref-da-name {
       type string;
       description "Dynamic address name";
     }
     leaf da-id {
       type int32;
       description "Dynamic address ID";
     }
     leaf da-sscan-status {
       type string;
       description "Dynamic address session scan module status";
     }
     leaf da-sscan-hold-interval {
       type string;
       description "Dynamic address session scan hold interval";
     }
     leaf da-sscan-entry-status {
       type string;
       description "Dynamic address session scan entry status";
     }
     leaf da-feed-server-name {
       type string;
       description "Feed server name";
     }
     leaf da-feed-server-lsysinfo {
       type string;
       description "Feed server logical-system tenant name";
     }
     leaf da-feed-name {
       type string;
       description "Feed source name";
     }
     leaf da-feed-lsysinfo {
       type string;
       description "Feed logical-system tenant name";
     }
     leaf da-category-name {
       type string;
       description "Category name";
     }
     leaf da-category-feed {
       type string;
       description "Category feed";
     }
     leaf da-property-name {
       type string;
       description "Property name";
     }
     leaf da-property-value {
       type string;
       description "Property value";
     }
     leaf da-property-value-start {
       type string;
       description "Property start value inclusive";
     }
     leaf da-property-value-end {
       type string;
       description "Property nd value inclusive";
     }
     leaf da-inst-name {
       type string;
       description "Dynamic address instance name";
     }
     leaf da-total-count {
       type int32;
       description "Number of entries";
     }
     leaf da-entry-cnt-v4 {
       type int32;
       description "IPv4 entry count";
     }
     leaf da-entry-cnt-v6 {
       type int32;
       description "IPv6 entry count";
     }
     leaf da-entry-cnt-mapping-feed {
       type int32;
       description "Mapping feed count";
     }
     leaf da-config-flags {
       type string;
       description "Configuration flags";
     }
     leaf da-feed-server-cnt {
       type int32;
       description "Number of feed server";
     }
     leaf da-feed-cnt {
       type int32;
       description "Number of feed";
     }
     leaf da-cnt {
       type int32;
       description "Number of dynamic address entry";
     }
     leaf da-cnt-total-v4 {
       type int32;
       description "IPv4 entry count";
     }
     leaf da-cnt-total-feed-v4 {
       type int32;
       description "IPv4 entry count from feed";
     }
     leaf da-cnt-total-v6 {
       type int32;
       description "IPv6 entry count";
     }
     leaf da-cnt-total-feed-v6 {
       type int32;
       description "IPv6 entry count from feed";
     }
     leaf da-feed-server-ca-profile-name {
       type string;
       description "Certificate profile name";
     }
     leaf da-feed-server-tls-profile-name {
       type string;
       description "TLS profile name";
     }
     leaf da-feed-server-user-name {
       type string;
       description "User name";
     }
     leaf da-feed-server-url {
       type string;
       description "Common url for feeds under same server";
     }
     leaf da-feed-server-routing-table {
       type string;
       description "Preferred routing table";
     }
     leaf da-feed-server-update-interval {
       type int32;
       description "The interval between end of last retrieval and start of next retrieval when feed does not configure it";
     }
     leaf da-feed-server-hold-interval {
       type int32;
       description "The time to hold data when feed update failed";
     }
     leaf da-feed-update-interval {
       type int32;
       description "The interval between end of last retrieval and start of next retrieval when feed does not configure it";
     }
     leaf da-feed-hold-interval {
       type int32;
       description "The time to hold data when feed update failed";
     }
     leaf da-feed-url {
       type int32;
       description "The URL to retreive dynamic address feed";
     }
     leaf da-feed-routing-table {
       type string;
       description "Preferred routing table";
     }
     leaf da-feed-ca-profile-name {
       type string;
       description "Certificate profile name";
     }
     leaf da-feed-stat-hist-total-update {
       type int32;
       description "Total number of updates on this feed";
     }
     leaf da-feed-stat-db-total-v4 {
       type int32;
       description "Total number of IPv4 entries in db from this feed";
     }
     leaf da-feed-stat-db-total-v6 {
       type int32;
       description "Total number of IPv6 entries in db from this feed";
     }
     leaf da-feed-stat-hist-total-err-download {
       type int32;
       description "Total number of download error on this feed";
     }
     leaf da-feed-stat-hist-total-err-db {
       type int32;
       description "Total number of db error on this feed";
     }
     leaf da-feed-stat-hist-total-err-other {
       type int32;
       description "Total number of other error on this feed";
     }
     leaf da-feed-stat-hist-total-ageout {
       type int32;
       description "Total number of ageout this feed";
     }
     leaf da-feed-stat-last-update-file-size {
       type int32;
       description "File size of last update";
     }
     leaf da-feed-stat-last-update-ipv4 {
       type int32;
       description "Total number of IPv4 entries contained in last update";
     }
     leaf da-feed-stat-last-update-ipv6 {
       type int32;
       description "Total number of IPv6 entries contained in last update";
     }
     leaf da-feed-stat-last-update-time-cost {
       type string;
       description "Seconds it took for last update parsing";
     }
     leaf da-feed-stat-last-download-time-cost {
       type string;
       description "Seconds it took for last downloading";
     }
     leaf da-feed-stat-last-update-begin-timestamp {
       type string;
       description "The time when last update began";
     }
     leaf da-feed-stat-last-update-end-timestamp {
       type string;
       description "The time when last update finished";
     }
     leaf da-feed-stat-last-update-status {
       type string;
       description "Last update status";
     }
     leaf da-feed-stat-last-download-begin-timestamp {
       type string;
       description "The time when last download began";
     }
     leaf da-feed-stat-last-download-end-timestamp {
       type string;
       description "The time when last download finished";
     }
     leaf da-feed-stat-last-err-download-timestamp {
       type string;
       description "The time when last download error happened";
     }
     leaf da-feed-stat-last-err-db-timestamp {
       type string;
       description "The time when last db error happened";
     }
     leaf da-feed-stat-last-err-other-timestamp {
       type string;
       description "The time when last other error happened";
     }
     leaf da-feed-stat-last-ageout-timestamp {
       type string;
       description "The time when last ageout happened";
     }
     leaf da-feed-stat-wakeup-update-time {
       type string;
       description "The time when next update happened";
     }
     leaf da-feed-stat-wakeup-expire-time {
       type string;
       description "The time when next expire happened";
     }
     leaf da-feed-stat-flag {
       type int32;
       description "Flags for feed";
     }
     container da-ip-entry {
       leaf da-ip-entry-idx {
         type int32;
         description "Position in found IP entries";
       }
       leaf da-ip-start {
         type string;
         description "Numerically minimal IP address within the range";
       }
       leaf da-ip-end {
         type string;
         description "Numerically maximal IP address within the range";
       }
       leaf da-feed-name {
         type string;
         description "Feed source name";
       }
       leaf da-name {
         type string;
         description "Dynamic address name";
       }
       leaf da-country-code {
         type string;
         description "Country code";
       }
     }
     container da-ip-entry-lsys {
       leaf da-ip-entry-idx {
         type int32;
         description "Position in found IP entries";
       }
       leaf da-ip-start {
         type string;
         description "Numerically minimal IP address within the range";
       }
       leaf da-ip-end {
         type string;
         description "Numerically maximal IP address within the range";
       }
       leaf da-feed-name {
         type string;
         description "Feed source name";
       }
       leaf da-name {
         type string;
         description "Dynamic address name";
       }
       leaf da-country-code {
         type string;
         description "Country code";
       }
       leaf da-lsys-name {
         type string;
         description "Logical system name";
       }
     }
     container da-ip-entry-foot {
       leaf da-inst-name {
         type string;
         description "Dynamic address instance name";
       }
       leaf da-total-count {
         type int32;
         description "Number of entries";
       }
     }
     container da-summary-brief {
       leaf da-feed-server-cnt {
         type int32;
         description "Number of feed server";
       }
       leaf da-feed-cnt {
         type int32;
         description "Number of feed";
       }
       leaf da-cnt {
         type int32;
         description "Number of dynamic address entry";
       }
     }
     container da-summary-server {
       leaf da-feed-server-name {
         type string;
         description "Feed server name";
       }
       leaf da-feed-server-lsysinfo {
         type string;
         description "Feed server logical-system tenant name";
       }
       leaf da-feed-server-ca-profile-name {
         type string;
         description "Certificate profile name";
       }
       leaf da-feed-server-tls-profile-name {
         type string;
         description "TLS profile name";
       }
       leaf da-feed-server-user-name {
         type string;
         description "User name";
       }
       leaf da-feed-server-url {
         type string;
         description "Common url for feeds under same server";
       }
       leaf da-feed-server-routing-table {
         type string;
         description "Preferred routing table";
       }
       leaf da-feed-server-update-interval {
         type int32;
         description "The interval between end of last retrieval and start of next retrieval when feed does not configure it";
       }
       leaf da-feed-server-hold-interval {
         type int32;
         description "The time to hold data when feed update failed";
       }
       container da-summary-feed {
         leaf da-feed-name {
           type string;
           description "Feed source name";
         }
         leaf da-feed-lsysinfo {
           type string;
           description "Feed logical-system tenant name";
         }
         leaf feed-ref-da-name {
           type string;
           description "Dynamic address name";
         }
         leaf da-feed-ca-profile-name {
           type string;
           description "Certificate profile name";
         }
         leaf da-feed-url {
           type int32;
           description "The URL to retreive dynamic address feed";
         }
         leaf da-feed-routing-table {
           type string;
           description "Preferred routing table";
         }
         leaf da-feed-update-interval {
           type int32;
           description "The interval between end of last retrieval and start of next retrieval when feed does not configure it";
         }
         leaf da-feed-hold-interval {
           type int32;
           description "The time to hold data when feed update failed";
         }
         leaf da-feed-stat-hist-total-update {
           type int32;
           description "Total number of updates on this feed";
         }
         leaf da-feed-stat-db-total-v4 {
           type int32;
           description "Total number of IPv4 entries in db from this feed";
         }
         leaf da-feed-stat-db-total-v6 {
           type int32;
           description "Total number of IPv6 entries in db from this feed";
         }
         leaf da-feed-stat-hist-total-err-download {
           type int32;
           description "Total number of download error on this feed";
         }
         leaf da-feed-stat-last-err-download-timestamp {
           type string;
           description "The time when last download error happened";
         }
         leaf da-feed-stat-hist-total-err-db {
           type int32;
           description "Total number of db error on this feed";
         }
         leaf da-feed-stat-last-err-db-timestamp {
           type string;
           description "The time when last db error happened";
         }
         leaf da-feed-stat-hist-total-err-other {
           type int32;
           description "Total number of other error on this feed";
         }
         leaf da-feed-stat-last-err-other-timestamp {
           type string;
           description "The time when last other error happened";
         }
         leaf da-feed-stat-hist-total-ageout {
           type int32;
           description "Total number of ageout this feed";
         }
         leaf da-feed-stat-last-ageout-timestamp {
           type string;
           description "The time when last ageout happened";
         }
         leaf da-feed-stat-wakeup-update-time {
           type string;
           description "The time when next update happened";
         }
         leaf da-feed-stat-wakeup-expire-time {
           type string;
           description "The time when next expire happened";
         }
         leaf da-feed-stat-flag {
           type int32;
           description "Flags for feed";
         }
         leaf da-feed-stat-last-update-file-size {
           type int32;
           description "File size of last update";
         }
         leaf da-feed-stat-last-update-ipv4 {
           type int32;
           description "Total number of IPv4 entries contained in last update";
         }
         leaf da-feed-stat-last-update-ipv6 {
           type int32;
           description "Total number of IPv6 entries contained in last update";
         }
         leaf da-feed-stat-last-update-begin-timestamp {
           type string;
           description "The time when last update began";
         }
         leaf da-feed-stat-last-update-end-timestamp {
           type string;
           description "The time when last update finished";
         }
         leaf da-feed-stat-last-update-time-cost {
           type string;
           description "Seconds it took for last update parsing";
         }
         leaf da-feed-stat-last-update-status {
           type string;
           description "Last update status";
         }
         leaf da-feed-stat-last-download-begin-timestamp {
           type string;
           description "The time when last download began";
         }
         leaf da-feed-stat-last-download-end-timestamp {
           type string;
           description "The time when last download finished";
         }
         leaf da-feed-stat-last-download-time-cost {
           type string;
           description "Seconds it took for last downloading";
         }
       }
     }
   }
   grouping identity-information-block {
     leaf name {
       type string;
       description "Name of a SSH identity key pair";
     }
     leaf time {
       type string;
       description "Create time";
     }
     leaf encrypted {
       type string;
       description "Encrypted or not";
     }
     list identity {
       description "Identity information";
       leaf name {
         type string;
         description "Name of a SSH identity key pair";
       }
       leaf time {
         type string;
         description "Create time";
       }
       leaf encrypted {
         type string;
         description "Encrypted or not";
       }
     }
   }
   grouping identity-public-information-block {
     leaf identity-public {
       type string;
       description "SSH identity public key information";
     }
   }
   grouping mape-confidentiality-status-block {
     container mape-confidentiality {
       description "Confidentiality Status";
       leaf domain {
         type string;
         description "Mape domain";
       }
       leaf status {
         type string;
         description "Domain confidentiality status";
       }
     }
   }
   grouping security-dynamic-policies-block {
     list security-context {
       list context-information {
         leaf source-zone-name {
           type string;
           description "Name of the source zone";
         }
         leaf destination-zone-name {
           type string;
           description "Name of the destination zone";
         }
       }
       container policies {
         list policy-information {
           leaf policy-name {
             type string;
             description "Name of the policy";
           }
           leaf policy-state {
             type string;
             description "State of the policy";
           }
           leaf policy-identifier {
             type uint32;
             description "Unique identifier for the policy";
           }
           leaf scope-policy-identifier {
             type uint32;
             description "Scope policy identifier for the policy";
           }
           leaf policy-sequence-number {
             type int32;
             description "Sequence number for the policy in a given zone context";
           }
           leaf log-profile-id {
             type uint32;
             description "Unique id for the log profile";
           }
           leaf service-set-name {
             type string;
             description "Name of the service set";
           }
           leaf interface-name {
             type string;
             description "Name of the services interface";
           }
           leaf sfw-rule-name {
             type string;
             description "Name of the stateful-firewall-rule";
           }
           leaf sfw-rule-set-name {
             type string;
             description "Name of the stateful-firewall-rule-set";
           }
           leaf match-direction {
             type string;
             description "Match Direction of the policy";
           }
           leaf policy-description {
             type string;
             description "Description of the policy";
           }
           leaf explicit-proxy-policy-sequence-number {
             type int32;
             description "Sequence number for the policy in a given zone context";
           }
           leaf explicit-proxy-policy-description {
             type string;
             description "Description of the policy";
           }
           container policy-action {
             leaf action-type {
               type string;
             }
             leaf tunnel {
               type empty;
               description "Tunnel packets that match this policy";
             }
             leaf nat-source {
               type empty;
               description "Apply source NAT to packets that match this policy";
             }
             leaf nat-destination {
               type string;
               description "Apply destination NAT to packets that match this policy";
             }
             leaf firewall-authentication {
               type empty;
               description "Authenticate the client that sent the packets that match this        policy";
             }
             leaf services-offload {
               type empty;
               description "Services-offload options of the policy";
             }
             leaf no-services-offload {
               type empty;
               description "No-services-offload options of the policy";
             }
             leaf advanced-connection-tracking {
               type empty;
               description "Advanced-connection-tracking option of the policy";
             }
             leaf application-services {
               type empty;
               description "Application services";
             }
             leaf feed {
               type empty;
               description "Feed";
             }
             leaf uac-enabled {
               type empty;
               description "Enable unified access control enforcement of policy";
             }
             leaf log {
               type empty;
               description "Log the session of packets that match this policy";
             }
             leaf count {
               type empty;
               description "Count packets that match this policy";
             }
             leaf scheduled {
               type empty;
               description "Schedule the policy based on a scheduler";
             }
           }
           list context-information {
             leaf global-context {
               type empty;
               description "Global policy conext";
             }
             leaf source-zone-name {
               type string;
               description "Name of the source zone";
             }
             leaf destination-zone-name {
               type string;
               description "Name of the destination zone";
             }
           }
           container policy-type-information {
             leaf policy-type-string {
               type string;
               description "Type of policy";
             }
             leaf policy-type-dynamic-policy-count {
               type int32;
               description "Number of dynamic policies under this scope";
             }
           }
           container multiple-source-zones {
             container source-zone {
               leaf source-zone-name {
                 type string;
                 description "Name of the source zone";
               }
             }
           }
           container multiple-destination-zones {
             container destination-zone {
               leaf destination-zone-name {
                 type string;
                 description "Name of the destination zone";
               }
             }
           }
           container source-addresses {
             container source-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container destination-addresses {
             container destination-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container source-end-user-profile {
             leaf source-end-user-profile-name {
               type string;
               description "Name of the source-end-user-profile";
             }
           }
           container destination-identity-context-profile {
             leaf destination-identity-context-profile-name {
               type string;
               description "Name of the destination-identity-context-profile-name";
             }
           }
           list applications {
             list application {
               leaf application-name {
                 type string;
                 description "Name of the application";
               }
               list application-term {
                 list source-port-range {
                   leaf low {
                     type int32;
                     description "The lower limit in the range of ports";
                   }
                   leaf high {
                     type int32;
                     description "The higher limit in the range of the ports";
                   }
                 }
                 list destination-port-range {
                   leaf ports_array {
                     type string;
                     description "The ports array string";
                   }
                   leaf single {
                     type int32;
                     description "The single port";
                   }
                   leaf low {
                     type int32;
                     description "The lower limit in the range of ports";
                   }
                   leaf high {
                     type int32;
                     description "The higher limit in the range of the ports";
                   }
                 }
                 container icmp-info {
                   leaf icmp-type {
                     type string;
                     description "The icmp application type";
                   }
                   leaf icmp-code {
                     type string;
                     description "The icmp application code";
                   }
                 }
                 container rpc-information {
                   leaf rpc-uuid {
                     type string;
                     description "The rpc application uuid";
                   }
                   container program-number-range {
                     leaf low {
                       type int32;
                       description "The lower limit in the range of ports";
                     }
                     leaf high {
                       type int32;
                       description "The higher limit in the range of the ports";
                     }
                   }
                 }
                 leaf protocol {
                   type string;
                   description "IP protocol";
                 }
                 leaf alg-name {
                   type string;
                   description "Name of the application layer gateway";
                 }
                 leaf inactivity-timeout {
                   type int32;
                   description "Idle timeout for any session that match this application";
                 }
                 leaf gate-timeout {
                   type int32;
                   description "Gate timeout for ALG child session to get established";
                 }
                 leaf child-inactivity-timeout {
                   type int32;
                   description "Idle timeout for ALG child session that is created after gate hit";
                 }
               }
             }
           }
           container policy-dynamic-applications {
             list policy-dynamic-application-name {
               leaf dynamic-application-name {
                 type string;
                 description "Dynamic application name in the policy";
               }
               leaf dynamic-application-id {
                 type uint32;
                 description "Dynamic application identifier in the policy";
               }
             }
             list policy-dynamic-application {
               leaf dynamic-application-name {
                 type string;
                 description "Dynamic application name in the policy";
               }
               leaf dynamic-application-id {
                 type uint32;
                 description "Dynamic application identifier in the policy";
               }
             }
             list policy-dynamic-application-group {
               leaf dynamic-application-group-name {
                 type string;
                 description "Dynamic application group name in the policy";
               }
               leaf dynamic-application-group-id {
                 type uint32;
                 description "Dynamic application group identifier in the policy";
               }
             }
           }
           container policy-url-categories {
             list policy-url-category-name {
               leaf url-category-name {
                 type string;
                 description "Url category name in the policy";
               }
               leaf url-category-id {
                 type uint32;
                 description "Url category identifier in the policy";
               }
             }
             list policy-url-category {
               leaf url-category-name {
                 type string;
                 description "Url category name in the policy";
               }
               leaf url-category-id {
                 type uint32;
                 description "Url category identifier in the policy";
               }
             }
           }
           container source-identities {
             container source-identity {
               leaf role-name {
                 type string;
                 description "Name of the role";
               }
             }
           }
           container destination-identity-context {
             container destination-context {
               leaf role-name {
                 type string;
                 description "Name of the role";
               }
             }
           }
           container source-identities-feeds {
             container source-identity-feed {
               leaf feed-name {
                 type string;
                 description "Name of the feed";
               }
             }
           }
           container destination-identities-feeds {
             container destination-identity-feed {
               leaf feed-name {
                 type string;
                 description "Name of the feed";
               }
             }
           }
           container aamw-policy-info {
             leaf aamw-info {
               type string;
             }
           }
           container dynapp-redir-profile {
             leaf dynapp-redir-profile-name {
               type string;
               description "Name of the redirect profile";
             }
           }
           container unknown-source-identities {
             leaf role-name {
               type string;
               description "Name of the role";
             }
           }
           container unknown-destination-identities {
             leaf role-name {
               type string;
               description "Name of the role";
             }
           }
           container policy-tcp-options {
             leaf policy-tcp-options-syn-check {
               type string;
               description "Per policy SYN check required flag";
             }
             leaf policy-tcp-options-sequence-check {
               type string;
               description "Per policy Sequence check required flag";
             }
             leaf policy-tcp-options-window-scale {
               type string;
               description "Per policy window scale enabled flag";
             }
             leaf policy-tcp-options-initial-tcp-mss {
               type uint32;
               description "Initial direction TCP MSS for the policy";
             }
             leaf policy-tcp-options-reverse-tcp-mss {
               type uint32;
               description "Reverse direction TCP MSS for the policy";
             }
           }
           container policy-tunnel {
             leaf tunnel-name {
               type string;
               description "Name of the tunnel";
             }
             leaf tunnel-type {
               type string;
               description "Type of tunnel";
             }
             leaf tunnel-identifier {
               type int32;
               description "Unique identifier for the tunnel";
             }
             leaf pair-policy-name {
               type string;
               description "Name of the pair policy";
             }
           }
           container policy-tunnel-inspection {
             leaf policy-tunnel-inspection-profile {
               type string;
               description "Policy tunnel inspection profile";
             }
           }
           container policy-firewall-authentication {
             leaf authentication-type {
               type string;
               description "Type of authentication";
             }
             leaf access-profile-name {
               type string;
               description "Name of the access profile";
             }
             leaf web-redirect {
               type string;
               description "Web-redirect flag for http";
             }
             leaf web-redirect-to-https {
               type string;
               description "Web-redirect-to-https flag";
             }
             leaf auth-only-browser {
               type string;
               description "Auth-only-browser flag";
             }
             leaf push-to-identity-management {
               type string;
               description "Push-to-identity-management flag";
             }
             leaf ssl-termination-profile {
               type string;
               description "Name of the ssl termination profile for HTTPS";
             }
             leaf domain {
               type string;
               description "Domain name";
             }
             leaf client-match-name {
               type string;
               description "Name to match, as given by client";
             }
             leaf auth-user-agent {
               type string;
               description "Responde to only HTTP request with given user agent";
             }
           }
           container policy-application-services {
             leaf gprs-gtp-profile {
               type string;
               description "Status of GPRS Tunneling Protocol Profile";
             }
             leaf gprs-sctp-profile {
               type string;
               description "Status of GPRS Stream Control Protocol profile";
             }
             leaf idp {
               type string;
             }
             leaf uac-policy {
               type string;
             }
             leaf utm {
               type string;
               description "Status of Unified Threat Management";
             }
             leaf advanced-anti-malware {
               type string;
               description "Advanced-anti-malware service";
             }
             leaf icap-redirect-profile {
               type string;
               description "ICAP Redirect service";
             }
             leaf security-intelligence {
               type string;
               description "Security intelligence service";
             }
             leaf wan-acceleration {
               type string;
             }
             leaf security-metadata-streaming-policy {
               type string;
               description "Security metadata streaming policy";
             }
             leaf anti-virus-policy {
               type string;
               description "Anti-virus policy";
             }
             leaf captive-portal {
               type string;
               description "Secure web gateway captive portal";
             }
             container application-firewall {
               container rule-set-info {
                 container rule-set {
                   leaf name {
                     type string;
                     description "Name information";
                   }
                   container rule-list {
                     list rule {
                       leaf name {
                         type string;
                         description "Name information";
                       }
                       leaf action {
                         type string;
                         description "Action specified for one rule";
                       }
                       container dynamic-application-list {
                         leaf-list dynamic-application {
                           type string;
                           description "Name of the dynamic application";
                         }
                       }
                       container dynamic-application-group-list {
                         leaf-list dynamic-application-group {
                           type string;
                           description "Name of the dynamic application group";
                         }
                       }
                     }
                     container default-rule {
                       leaf action {
                         type string;
                         description "Action specified for one rule";
                       }
                     }
                   }
                 }
               }
             }
             container application-acceleration {
               leaf application-acceleration-profile-name {
                 type string;
                 description "Application acceleration profile name";
               }
               leaf application-acceleration-service-options {
                 type string;
                 description "Application acceleration service options";
               }
             }
             container ssl-initiation {
               leaf ssl-initiation-profile-name {
                 type string;
                 description "SSL initiation profile name";
               }
             }
             container ssl-termination {
               leaf ssl-termination-profile-name {
                 type string;
                 description "SSL termination profile name";
               }
             }
             container ssl-proxy {
               leaf ssl-proxy-profile-name {
                 type string;
                 description "SSL proxy profile name";
               }
             }
             container web-proxy {
               leaf web-proxy-profile-name {
                 type string;
                 description "Web proxy profile name";
               }
             }
             container application-traffic-control {
               leaf rule-set-name {
                 type string;
                 description "Application traffic control rule-set name";
               }
             }
             container wx-optimizer {
               leaf wx-optimizer-profile-name {
                 type string;
                 description "Wan Optimizer Profile Name";
               }
               leaf wx-optimizer-service-options {
                 type string;
                 description "Wan Optimizer Service Options";
               }
             }
           }
           container policy-count-alarms {
             container alarm {
               leaf alarm-count {
                 type int32;
                 description "Number of the times alarm was raised";
               }
               leaf alarm-type {
                 type string;
                 description "Type of the alarm";
               }
             }
           }
           container policy-log {
             leaf log-session-creation {
               type empty;
               description "Log when a new session gets created for the policy";
             }
             leaf log-session-close {
               type empty;
               description "Log when a new session gets closed for the policy";
             }
           }
           container policy-feed {
             leaf policy-feed-type {
               type string;
               description "Add session element to security intellgence feed";
             }
           }
           container policy-scheduler {
             leaf attached-scheduler-name {
               type string;
               description "Information about the scheduler name";
             }
           }
           container policy-statistics-information {
             leaf pfe-identifier {
               type string;
               description "An identifier for a PFE";
             }
             leaf input-bytes {
               type int32;
               description "Number of incoming bytes";
             }
             leaf input-byte-rate {
               type int32;
               description "Number of incoming bytes per second";
             }
             leaf input-bytes-init {
               type int32;
               description "Number of incoming bytes in initial direction";
             }
             leaf input-byte-rate-init {
               type int32;
               description "Number of incoming bytes per second in initial direction";
             }
             leaf input-bytes-reply {
               type int32;
               description "Number of incoming bytes in reply direction";
             }
             leaf input-byte-rate-reply {
               type int32;
               description "Number of incoming bytes per second in reply direction";
             }
             leaf output-bytes {
               type int32;
               description "Number of outgoing bytes";
             }
             leaf output-byte-rate {
               type int32;
               description "Number of outgoing bytes per second";
             }
             leaf output-bytes-init {
               type int32;
               description "Number of outgoing bytes in initial direction";
             }
             leaf output-byte-rate-init {
               type int32;
               description "Number of outgoing bytes per second in initial direction";
             }
             leaf output-bytes-reply {
               type int32;
               description "Number of outgoing bytes in reply direction";
             }
             leaf output-byte-rate-reply {
               type int32;
               description "Number of outgoing bytes per second in reply direction";
             }
             leaf input-packets {
               type int32;
               description "Number of incoming packets";
             }
             leaf input-packet-rate {
               type int32;
               description "Number of incoming packets per second";
             }
             leaf input-packets-init {
               type int32;
               description "Number of incoming packets in initial direction";
             }
             leaf input-packet-rate-init {
               type int32;
               description "Number of incoming packets per second in initial direction";
             }
             leaf input-packets-reply {
               type int32;
               description "Number of incoming packets in reply direction";
             }
             leaf input-packet-rate-reply {
               type int32;
               description "Number of incoming packets per second in reply direction";
             }
             leaf output-packets {
               type int32;
               description "Number of outgoing packets";
             }
             leaf output-packet-rate {
               type int32;
               description "Number of outgoing packets per second";
             }
             leaf output-packets-init {
               type int32;
               description "Number of outgoing packets in initial direction";
             }
             leaf output-packet-rate-init {
               type int32;
               description "Number of outgoing packets per second in initial direction";
             }
             leaf output-packets-reply {
               type int32;
               description "Number of outgoing packets in reply direction";
             }
             leaf output-packet-rate-reply {
               type int32;
               description "Number of outgoing packets per second in reply direction";
             }
             leaf session-creations {
               type int32;
               description "Number of sessions created";
             }
             leaf session-creation-rate {
               type int32;
               description "Number of sessions created per second";
             }
             leaf active-sessions {
               type int32;
               description "Number of active sessions";
             }
             leaf session-deletions {
               type int32;
               description "Number of sessions deleted";
             }
             leaf policy-lookups {
               type int32;
               description "Number of policy lookups";
             }
           }
           container source-vrfs {
             container source-vrf {
               leaf source-vrf-name {
                 type string;
                 description "Name of the source vrf group";
               }
             }
           }
           container destination-vrfs {
             container destination-vrf {
               leaf destination-vrf-name {
                 type string;
                 description "Name of the destination vrf";
               }
             }
           }
         }
       }
     }
   }
   grouping flow-swrss-io-block {
     leaf io_id {
       type uint32;
       description "Swrss io id";
     }
     leaf current_usage {
       type uint32;
       description "Current usage";
     }
     leaf last_usage {
       type uint32;
       description "Last usage";
     }
     leaf sched_counter {
       type uint32;
       description "Sched counter";
     }
   }
   grouping flow-pmi-statistics-block {
     leaf pmi-spu-id {
       type string;
       description "PMI SPU ID";
     }
     leaf pmi-rx {
       type uint64;
       description "PMI inbounds";
     }
     leaf pmi-tx {
       type uint64;
       description "PMI outbounds";
     }
     leaf pmi-rfp {
       type uint64;
       description "PMI return flow path";
     }
     leaf pmi-drop {
       type uint64;
       description "PMI drop";
     }
     leaf pmi-encap-bytes {
       type uint64;
       description "PMI encapsulation bytes";
     }
     leaf pmi-decap-bytes {
       type uint64;
       description "PMI decapsulation bytes";
     }
     leaf pmi-encap-pkts {
       type uint64;
       description "PMI encapsulation packets";
     }
     leaf pmi-decap-pkts {
       type uint64;
       description "PMI decapsulation packets";
     }
   }
   grouping flow-tunnel-inspection-statistics-block {
     leaf ti-spu-id {
       type string;
       description "Tunnel-inspection SPU ID";
     }
     list flow-ti-statistics-data {
       leaf ti-type {
         type string;
         description "Tunnel-inspection TYPE";
       }
       leaf ti-overlay-active {
         type uint64;
         description "Overlay active sessions";
       }
       leaf ti-overlay-create {
         type uint64;
         description "Overlay create sessions";
       }
       leaf ti-overlay-close {
         type uint64;
         description "Overlay close sessions";
       }
       leaf ti-underlay-active {
         type uint64;
         description "Underlay active sessions";
       }
       leaf ti-underlay-create {
         type uint64;
         description "Underlay create sessions";
       }
       leaf ti-underlay-close {
         type uint64;
         description "Underlay close sessions";
       }
       leaf ti-input-packets {
         type uint64;
         description "Input packets";
       }
       leaf ti-input-bytes {
         type uint64;
         description "Input bytes";
       }
       leaf ti-output-packets {
         type uint64;
         description "Output packets";
       }
       leaf ti-output-bytes {
         type uint64;
         description "Output bytes";
       }
       leaf ti-bypass-packets {
         type uint64;
         description "Bypass packets";
       }
       leaf ti-bypass-bytes {
         type uint64;
         description "Bypass bytes";
       }
     }
   }
   grouping flow-statistics-all-block {
     leaf flow-spu-id {
       type string;
       description "SPU id";
     }
     leaf flow-session-count-valid {
       type uint32;
       description "Number of current valid sessions";
     }
     leaf flow-session-allocated-total {
       type uint32;
       description "Number of total allocated sessions";
     }
     leaf flow-session-failed-total {
       type uint32;
       description "Number of total failed-to-allocate sessions";
     }
     leaf flow-session-valid-system {
       type uint32;
       description "Number of system valid sessions";
     }
     leaf flow-pkt-count-rx {
       type string;
       description "Number of received packets";
     }
     leaf flow-pkt-count-tx {
       type string;
       description "Number of transmitted packets";
     }
     leaf flow-pkt-count-copy {
       type string;
       description "Number of copied packets";
     }
     leaf flow-pkt-count-drop {
       type string;
       description "Number of dropped packets";
     }
     leaf flow-pkt-count-fwd {
       type string;
       description "Number of forwarded/queued packets";
     }
     leaf flow-llf-pkt-count-prd {
       type string;
       description "Number of services-offload packets";
     }
     leaf flow-frag-count-fwd {
       type string;
       description "Number of fragments packets";
     }
     leaf tunnel-frag-gen-pre {
       type string;
       description "Number of pre fragments generated";
     }
     leaf tunnel-frag-gen-post {
       type uint64;
       description "Number of post fragments generated";
     }
   }
   grouping flow-status-all-block {
     container flow-forwarding-mode {
       description "Forwarding mode";
       leaf flow-forwarding-mode-inet {
         type string;
         description "Inet forwarding mode";
       }
       leaf flow-forwarding-mode-inet-reboot-status {
         type string;
         description "Inet forwarding mode reboot status";
       }
       leaf flow-forwarding-mode-inet6 {
         type string;
         description "Inet6 forwarding mode";
       }
       leaf flow-forwarding-mode-inet6-reboot-status {
         type string;
         description "Inet6 forwarding mode reboot status";
       }
       leaf flow-forwarding-mode-mpls {
         type string;
         description "MPLS forwarding mode";
       }
       leaf flow-forwarding-mode-mpls-reboot-status {
         type string;
         description "MPLS forwarding mode reboot status";
       }
       leaf flow-forwarding-mode-iso {
         type string;
         description "ISO forwarding mode";
       }
       leaf flow-forwarding-mode-iso-reboot-status {
         type string;
         description "ISO forwarding mode reboot status";
       }
       leaf flow-tap-mode {
         type string;
         description "Tap mode";
       }
       leaf flow-reduce-dp-memory-mode {
         type string;
         description "Advanced services data-plane memory mode";
       }
       leaf flow-reduce-dp-memory-reboot-status {
         type string;
         description "Advanced services data-plane memory reboot status";
       }
       leaf flow-enhanced-routing-mode {
         type string;
         description "Enhanced route scaling mode";
       }
       leaf flow-enhanced-routing-mode-reboot-status {
         type string;
         description "Enhanced route scaling mode reboot status";
       }
       leaf flow-enhanced-services-mode {
         type string;
         description "Enhanced services mode";
       }
       leaf flow-enhanced-services-mode-reboot-status {
         type string;
         description "Enhanced services mode reboot status";
       }
     }
     container flow-l3l4-scaling-mode {
       description "Flow scaled L3L4 mode";
       leaf l3l4-mode-status {
         type string;
         description "Scaled L3L4 mode status";
       }
       leaf l3l4-scaling-mode-reboot-status {
         type string;
         description "Scaled L3L4 mode reboot status";
       }
     }
     container flow-tcp-options {
       leaf flow-tcp-sequence-check {
         type string;
         description "TCP sequence check";
       }
       leaf flow-tcp-mss {
         type uint32;
         description "TCP maximum segment size";
       }
     }
     container flow-trace-option {
       leaf flow-trace-status {
         type string;
         description "Flow debugging status";
       }
       leaf flow-trace-options {
         type string;
         description "Enabled trace options";
       }
       leaf flow-trace-level {
         type string;
         description "Enabled trace level";
       }
       leaf flow-trace-root-override-status {
         type string;
         description "Status of root override enabled or not";
       }
       leaf flow-counter-filtering {
         type string;
         description "Flow counter filtering status";
       }
     }
     container flow-session-distribution {
       description "Session distribution";
       leaf mode {
         type string;
         description "Session distribution mode";
       }
       leaf reboot-status {
         type string;
         description "Session distribution reboot status";
       }
       leaf gtpu-distr-status {
         type string;
         description "GTP-U distribution status";
       }
       leaf sctp-distr-status {
         type string;
         description "SCTP distribution status";
       }
     }
     container flow-ipsec-performance-acceleration {
       description "Ipsec performance acceleration";
       leaf ipa-status {
         type string;
         description "Ipsec performance acceleration status";
       }
     }
     container flow-gre-performance-acceleration {
       description "GRE performance acceleration";
       leaf grea-status {
         type string;
         description "GRE performance acceleration status";
       }
     }
     container flow-packet-ordering {
       description "Packet ordering";
       leaf ordering-mode {
         type string;
         description "Packet ordering mode";
       }
       leaf ordering-reboot-status {
         type string;
         description "Packet ordering reboot status";
       }
     }
     container flow-power-mode {
       description "Power mode";
       leaf power-mode-status {
         type string;
         description "Power mode express path status";
       }
     }
     container flow-power-mode-ipsec {
       description "Power mode IPsec";
       leaf pmi-status {
         type string;
         description "Power mode IPsec status";
       }
     }
     container flow-power-mode-ipsec-qat {
       description "Power mode IPsec QAT";
       leaf pmi-qat-status {
         type string;
         description "Power mode IPsec QAT status";
       }
       leaf pmi-qat-reboot-status {
         type string;
         description "Power mode IPsec QAT reboot status";
       }
     }
     container flow-fat-core-group {
       description "Fat core group size";
       leaf fcg-status {
         type string;
         description "Fat core group status";
       }
     }
     container utm-onbox-av-load-flavor {
       description "UTM onbox AV load flavor";
       leaf utm-onbox-av-status {
         type string;
         description "UTM onbox AV status";
       }
     }
     container flow-inline-fpga-crypto {
       description "Inline FPGA Crypto";
       leaf ifc-status {
         type string;
         description "Inline FPGA Crypto status";
       }
     }
     container flow-multicast-strict-order {
       description "Multicast Strict-Order";
       leaf multicast-strict-order-status {
         type string;
         description "Multicast Strict-Order status";
       }
     }
     container flow-drop-flow {
       description "Drop-flow";
       leaf drop-flow-max-sess {
         type uint32;
         description "Drop-flow maximum sessions";
       }
       leaf drop-flow-timeout {
         type uint32;
         description "Drop-flow timeout";
       }
       leaf drop-flow-status {
         type string;
         description "Drop-flow status";
       }
     }
   }
   grouping flow-gate-information-block {
     leaf flow-gate-fpc-pic-id {
       type string;
       description "FPC PIC id";
     }
     leaf displayed-gate-valid {
       type uint32;
       description "Valid gates displayed";
     }
     leaf displayed-gate-pending {
       type uint32;
       description "Pending gates displayed";
     }
     leaf displayed-gate-invalidated {
       type uint32;
       description "Invalidated gates displayed";
     }
     leaf displayed-gate-other {
       type uint32;
       description "Free and allocated gates displayed";
     }
     leaf displayed-gate-count {
       type uint32;
       description "Total gates displayed";
     }
     leaf displayed-gate-max {
       type uint32;
       description "Maximum gates";
     }
     list gate {
       leaf protocol {
         type string;
         description "IP protocol";
       }
       leaf application-name {
         type string;
         description "Application name";
       }
       leaf application-value {
         type uint32;
         description "Application value";
       }
       leaf age {
         type uint32;
         description "Timeout value";
       }
       leaf flags {
         type string;
         description "Flags";
       }
       leaf vrf {
         type string;
         description "VRF";
       }
       leaf zone {
         type string;
         description "Zone name";
       }
       leaf logical-system {
         type string;
         description "Logical system name";
       }
       leaf parent-id {
         type uint32;
         description "ID of the parent session";
       }
       leaf reference-count {
         type uint32;
         description "Reference count";
       }
       leaf resource {
         type string;
         description "Resource";
       }
       leaf nat-source-pool-name {
         type string;
         description "Name of the source NAT pool";
       }
       container hole {
         leaf source-address-start {
           type jt:ipaddr;
           description "Start of the range of source addresses";
         }
         leaf source-address-end {
           type jt:ipaddr;
           description "End of the range of source addresses";
         }
         leaf source-port-start {
           type uint32;
           description "Start of the range of source ports";
         }
         leaf source-port-end {
           type uint32;
           description "End of the range of source ports";
         }
         leaf destination-address-start {
           type jt:ipaddr;
           description "Start of the range of destination addresses";
         }
         leaf destination-address-end {
           type jt:ipaddr;
           description "End of the range of destination addresses";
         }
         leaf destination-port-start {
           type uint32;
           description "Start of the range of destination ports";
         }
         leaf destination-port-end {
           type uint32;
           description "End of the range of destination ports";
         }
       }
       container translated-hole {
         leaf source-address {
           type jt:ipaddr;
           description "Source address";
         }
         leaf source-port {
           type uint32;
           description "Source port";
         }
         leaf destination-address {
           type jt:ipaddr;
           description "Destination address";
         }
         leaf destination-port {
           type uint32;
           description "Destination port";
         }
       }
     }
   }
   grouping advanced-connection-tracking-table-block {
     list advanced-connection-tracking-entry {
       description "Information about advanced-connection-tracking entry";
       leaf advanced-connection-tracking-fpc-pic-name {
         type string;
         description "FPC PIC name";
       }
       leaf advanced-connection-tracking-flag {
         type uint32;
         description "Flag of advanced-connection-tracking entry";
       }
       leaf source-address {
         type jt:ipaddr;
         description "Source address";
       }
       leaf destination-address {
         type jt:ipaddr;
         description "Destination address";
       }
       leaf advanced-connection-tracking-destination-port {
         type string;
         description "Destination port";
       }
       leaf protocol {
         type string;
         description "IP protocol";
       }
       leaf advanced-connection-tracking-hash {
         type uint32;
         description "Hash of advanced-connection-tracking entry";
       }
       leaf advanced-connection-tracking-ttl {
         type uint32;
         description "Time to live of advanced-connection-tracking entry";
       }
       leaf advanced-connection-tracking-hitcnt {
         type uint32;
         description "Hit count of advanced-connection-tracking entry";
       }
       leaf advanced-connection-tracking-zone {
         type string;
         description "Name of zone";
       }
     }
   }
   grouping flow-session-information-block {
     leaf flow-fpc-pic-id {
       type string;
       description "FPC PIC id";
     }
     leaf dcp-flow-fpc-pic-id {
       type string;
       description "DCP Flow FPC PIC id";
     }
     leaf displayed-session-valid {
       type uint32;
       description "Valid sessions displayed";
     }
     leaf displayed-session-pending {
       type uint32;
       description "Pending sessions displayed";
     }
     leaf displayed-session-invalidated {
       type uint32;
       description "Invalidated sessions displayed";
     }
     leaf displayed-session-other {
       type uint32;
       description "Free and allocated sessions displayed";
     }
     leaf displayed-session-count {
       type uint32;
       description "Total sessions displayed";
     }
     leaf max-session-count {
       type uint32;
       description "Maximum sessions";
     }
     leaf max-inet6-session-count {
       type uint32;
       description "Maximum inet6 sessions";
     }
     list flow-session {
       description "Information about one or more session wings";
       leaf session-identifier {
         type uint64;
         description "Session identifier";
       }
       leaf session-svc-set {
         type string;
         description "Service set to which this session belongs";
       }
       leaf session-state {
         type string;
         description "High availability session state";
       }
       leaf session-spu-id {
         type uint32;
         description "Session SPU ID";
       }
       leaf sess-state {
         type string;
         description "Session state";
       }
       leaf logical-system {
         type string;
         description "Logical system name";
       }
       leaf session-mams-name {
         type string;
         description "AMS member interface to which this session belongs";
       }
       leaf tenant {
         type string;
         description "Tenant name";
       }
       leaf session-mask {
         type uint32;
         description "Session mask";
       }
       leaf module-name {
         type string;
         description "Module name";
       }
       leaf internal-module-identifier {
         type string;
         description "Internal information about the module";
       }
       leaf session-authentication {
         type string;
         description "Authentication of the session";
       }
       container resource-manager-information {
         leaf client-name {
           type string;
           description "Client name";
         }
         leaf group-identifier {
           type uint32;
           description "Group identifier for resource manager";
         }
         leaf resource-identifier {
           type uint32;
           description "Resource identifier for resource manager";
         }
       }
       list flow-information {
         leaf direction {
           type string;
           description "Flow direction";
         }
         leaf source-address {
           type jt:ipaddr;
           description "Source address";
         }
         leaf source-port {
           type uint32;
           description "Source port";
         }
         leaf destination-address {
           type jt:ipaddr;
           description "Destination address";
         }
         leaf destination-port {
           type uint32;
           description "Destination port";
         }
         leaf protocol {
           type string;
           description "IP protocol";
         }
         leaf conn-tag {
           type uint32;
           description "Connection Tag";
         }
         leaf l3vpn-vrf-group {
           type string;
           description "L3VPN VRF Group";
         }
         leaf interface-name {
           type string;
           description "Interface name";
         }
         leaf pkt-cnt {
           type uint64;
           description "Packet count";
         }
         leaf byte-cnt {
           type uint64;
           description "Byte count";
         }
         leaf wing-state {
           type string;
           description "High availability wing state";
         }
         leaf dcp-session-id {
           type uint32;
           description "DCP session ID when system in CPLITE";
         }
         leaf conn-type {
           type string;
           description "Tunnel connection type when inspection";
         }
         leaf vxlan-vni {
           type uint32;
           description "VXLAN VNI when inspection";
         }
         leaf tunnel-session-id {
           type uint32;
           description "Tunnel session id when inspection";
         }
         leaf vector-routing-info {
           type string;
           description "Vector routing information";
         }
         leaf tunnel-information {
           type uint32;
           description "Information about a tunnel";
         }
         leaf seq-ack-diff {
           type uint32;
           description "Seq/Ack diff";
         }
         leaf dcp-session-spu-id {
           type uint32;
           description "DCP session SPU ID when system in CPLITE";
         }
         container sw-flow-information {
           leaf sw-flow-type {
             type string;
             description "Type of softwire flow";
           }
           leaf sw-flow-src-ip {
             type string;
             description "Source IP address";
           }
           leaf sw-flow-src-port {
             type string;
             description "Source port";
           }
           leaf sw-flow-dst-ip {
             type string;
             description "Destination IP address";
           }
           leaf sw-flow-dst-port {
             type string;
             description "Destination port";
           }
         }
         leaf attachment-id {
           type uint64;
           description "Attachment Id";
         }
         leaf gw-endpoint-id {
           type uint64;
           description "GW Endpoint Id";
         }
         leaf flow-cookie {
           type uint32;
           description "Flow Cookie";
         }
         leaf path-mtu {
           type uint32;
           description "Maximum transmission unit for path";
         }
         leaf session-token {
           type uint32;
           description "Session token";
         }
         leaf flag {
           type uint32;
           description "Flag";
         }
         leaf unidirectional-session-refreshing {
           type string;
           description "Unidirectional-session-refreshing";
         }
         leaf route {
           type uint32;
           description "Route";
         }
         leaf gateway {
           type jt:ipaddr;
           description "Gateway address";
         }
         leaf tunnel-id {
           type uint32;
           description "Tunnel ID";
         }
         leaf tunnel-type {
           type string;
           description "Tunnel type";
         }
         leaf tunnel-info {
           type uint32;
           description "Tunnel info";
         }
         leaf port-sequence {
           type uint32;
           description "Port sequence";
         }
         leaf fin-sequence {
           type uint32;
           description "FIN sequence";
         }
         leaf fin-state {
           type uint32;
           description "FIN state";
         }
         leaf cookie {
           type uint32;
           description "Cookie";
         }
         leaf power-mode-express-path {
           type string;
           description "Power-mode-express-path";
         }
         leaf self-tunnel-id {
           type uint32;
           description "Self tunnel ID";
         }
         leaf self-tunnel-type {
           type string;
           description "Self tunnel type";
         }
         leaf self-tunnel-info {
           type uint32;
           description "Self tunnel info";
         }
         leaf recv-ipv4-post-frags-counter {
           type uint64;
           description "Information about counter";
         }
         leaf gen-ipv4-post-frags-counter {
           type uint64;
           description "Information about counter";
         }
         leaf recv-ipv4-pre-frags-counter {
           type uint64;
           description "Information about counter";
         }
         leaf ipv4-tx-to-tunnel-frags {
           type uint64;
           description "Information about counter";
         }
         leaf gen-ipv4-pre-frags-counter {
           type uint64;
           description "Information about counter";
         }
         leaf recv-ipv6-pre-frags-counter {
           type uint64;
           description "Information about counter";
         }
         leaf ipv6-tx-to-tunnel-frags {
           type uint64;
           description "Information about counter";
         }
         leaf gen-ipv6-pre-frags-counter {
           type uint64;
           description "Information about counter";
         }
         leaf pretty-direction {
           type string;
           description "Flow direction";
         }
         leaf utm-mode {
           type string;
           description "Utm mode";
         }
         leaf idp-mode {
           type string;
           description "Idp mode";
         }
         leaf aamw-mode {
           type string;
           description "Aamw mode";
         }
         leaf secintel-mode {
           type string;
           description "Secintel mode";
         }
         leaf icapredirect-mode {
           type string;
           description "Icapredirect mode";
         }
         leaf apbr-mode {
           type string;
           description "Apbr mode";
         }
         leaf jdpi-mode {
           type string;
           description "Jdpi mode";
         }
         list plugin-info {
           leaf plugin-name {
             type string;
             description "Plugin name";
           }
           leaf plugin-s2c {
             type string;
             description "S2C interested ";
           }
           leaf plugin-c2s {
             type string;
             description "C2S interested ";
           }
         }
       }
       leaf policy {
         type string;
         description "Policy name";
       }
       leaf timeout {
         type string;
         description "Session timeout";
       }
       leaf status {
         type string;
         description "Status of the session";
       }
       leaf app-name {
         type string;
         description "App name";
       }
       leaf app-status {
         type string;
         description "App status";
       }
       leaf app-action {
         type string;
         description "App action";
       }
       leaf nat-source-pool-name {
         type string;
         description "Name of the source NAT pool";
       }
       leaf nat-dst-pool-name {
         type string;
         description "Name of the destination NAT pool";
       }
       leaf nat-eif-pool-name {
         type string;
         description "Name of the eif matched NAT pool";
       }
       leaf application-name {
         type string;
         description "Application name";
       }
       leaf application-value {
         type uint32;
         description "Application value";
       }
       leaf dynamic-application-name {
         type string;
         description "Dynamic application name";
       }
       leaf dynamic-nested-application-name {
         type string;
         description "Dynamic nested application name";
       }
       leaf encryption-traffic-name {
         type string;
         description "Traffic is encrypted";
       }
       leaf url-category-name {
         type string;
         description "Url Category name";
       }
       leaf application-firewall-rule-set-name {
         type string;
         description "Application firewall rule set name";
       }
       leaf application-firewall-rule-name {
         type string;
         description "Application firewall rule name";
       }
       leaf application-traffic-control-rule-set-name {
         type string;
         description "Application traffic control rule-set name";
       }
       leaf application-traffic-control-rule-name {
         type string;
         description "Application traffic control rule name";
       }
       leaf application-traffic-control-fc {
         type string;
         description "Application traffic control forwarding class name";
       }
       leaf application-traffic-control-fc-queue-num {
         type uint32;
         description "Application traffic control forwarding class queue number";
       }
       leaf application-traffic-control-dscp {
         type string;
         description "Application traffic control dscp";
       }
       leaf application-traffic-control-loss {
         type string;
         description "Application traffic control loss priority";
       }
       leaf application-traffic-control-rl-c2s {
         type string;
         description "Application traffic control rate limiters name";
       }
       leaf application-traffic-control-rl-c2s-bdl {
         type uint32;
         description "Application traffic control bandwidth-limit";
       }
       leaf application-traffic-control-rl-c2s-bsl {
         type uint32;
         description "Application traffic control burst-size-limit";
       }
       leaf application-traffic-control-rl-s2c {
         type string;
         description "Application traffic control rate limiters name";
       }
       leaf application-traffic-control-rl-s2c-bdl {
         type uint32;
         description "Application traffic control bandwidth-limit";
       }
       leaf application-traffic-control-rl-s2c-bsl {
         type uint32;
         description "Application traffic control burst-size-limit";
       }
       leaf configured-timeout {
         type string;
         description "Configured timeout";
       }
       leaf wan-acceleration {
         type string;
         description "WAN acceleration redirection status";
       }
       leaf start-time {
         type uint32;
         description "Start time of the session";
       }
       leaf duration {
         type uint32;
         description "Duration of the session";
       }
       leaf session-flag {
         type string;
         description "Session flag";
       }
       leaf forward-type {
         type string;
         description "Forwarding Type";
       }
       leaf bandwidth {
         type string;
         description "Bandwidth information";
       }
       leaf source-user {
         type string;
         description "Source-user name";
       }
       leaf from-zone {
         type string;
         description "From zone";
       }
       leaf to-zone {
         type string;
         description "Zone name";
       }
       leaf l4-application-name {
         type string;
         description "Layer4-Application name";
       }
       leaf l7-base-application-name {
         type string;
         description "Base-layer7-Application name";
       }
       leaf l7-application-name {
         type string;
         description "Layer7-Application name";
       }
       leaf inspection-mode {
         type string;
         description "Inspection mode";
       }
       leaf hardware-acceleration {
         type string;
         description "Hardware acceleration redirection status";
       }
       leaf ssl-encrypted {
         type string;
         description "Ssl enable";
       }
       leaf decrypted-mirrored {
         type string;
         description "Decrypted mirrored";
       }
       leaf jdpi-classification {
         type string;
         description "JDPI classfication";
       }
       leaf tunnel-session {
         type string;
         description "Tunnel session's existence";
       }
     }
   }
   grouping idp-session-summary-information-block {
     leaf total-sessions {
       type uint32;
       description "Total sessions";
     }
     list idp-session-summary-per-pic-information {
       description "IDP session summary per PIC information";
       leaf pic-name {
         type string;
         description "Pic name";
       }
       leaf maximum-sessions {
         type uint32;
         description "Maximum sessions";
       }
       leaf active-sessions {
         type uint32;
         description "Number of active sessions";
       }
     }
   }
   grouping flow-ipaction-information-block {
     leaf ip-action-count {
       type uint32;
       description "IP Action count";
     }
     list flow-ipaction-entry {
       description "Information about ip-action entry";
       leaf source-address {
         type jt:ipaddr;
         description "Source address";
       }
       leaf source-port {
         type uint32;
         description "Source port";
       }
       leaf destination-address {
         type jt:ipaddr;
         description "Destination address";
       }
       leaf destination-port {
         type uint32;
         description "Destination port";
       }
       leaf protocol {
         type string;
         description "IP protocol";
       }
       leaf ip-action-timeout {
         type string;
         description "Ip-action Timeout";
       }
       leaf from-zone {
         type string;
         description "From zone";
       }
       leaf ip-action {
         type string;
         description "IP Action";
       }
       leaf ip-action-state {
         type string;
         description "IP Action state";
       }
       leaf logical-system {
         type string;
         description "Logical system name";
       }
     }
   }
   grouping secure-wire-information-block {
     leaf secure-wire-lsys-name {
       type string;
       description "Logical-system Name of a secure wire";
     }
     leaf secure-wire-name {
       type string;
       description "Name of a secure wire";
     }
     leaf interface-name {
       type string;
       description "Interface name";
     }
     leaf link-state {
       type string;
       description "Operational link state of the interface";
     }
     leaf interface2-name {
       type string;
       description "Interface name";
     }
     leaf link2-state {
       type string;
       description "Operational link state of the interface";
     }
   }
   grouping flow-resource-manager-settings-block {
     leaf resource-manager-settings-owner {
       type string;
       description "Resource owner";
     }
     leaf resource-manager-settings-type {
       type string;
       description "Resource type";
     }
     leaf resource-manager-settings-current {
       type string;
       description "Current settings";
     }
     leaf resource-manager-settings-next {
       type string;
       description "Next settings";
     }
   }
   grouping resource-manager-status-details-block {
     leaf resource-manager-cpu-io-number {
       type uint32;
       description "CPU number for IO threads";
     }
     leaf resource-manager-cpu-flow-number {
       type uint32;
       description "CPU number for flow threads";
     }
     leaf resource-manager-enhanced-logging {
       type string;
       description "Dedicated resources for logging";
     }
   }
   grouping flow-vsrx-dpts-status-block {
     leaf vsrx-dpts-status {
       type string;
       description "Dataplane sleep status";
     }
   }
   grouping show-mirror-filter-entry-block {
     list mirror-filter-entry {
       description "Information about one or more mirror filter entries";
       leaf mirror-filter-name {
         type string;
         description "X2 mirror filter name";
       }
       leaf mirror-filter-dst-prefix {
         type string;
         description "Mirror destination prefix";
       }
       leaf mirror-filter-destination-port {
         type uint32;
         description "Mirror destination port";
       }
       leaf mirror-filter-src-prefix {
         type string;
         description "Mirror source prefix";
       }
       leaf mirror-filter-source-port {
         type uint32;
         description "Mirror source port";
       }
       leaf mirror-filter-interface-in {
         type string;
         description "Mirror interface in";
       }
       leaf mirror-filter-interface-out {
         type string;
         description "Mirror interface out";
       }
       leaf mirror-filter-protocol {
         type int32;
         description "Mirror filter protocol";
       }
       leaf mirror-filter-counters {
         type int32;
         description "Number of packets match filters";
       }
       leaf mirror-output-counters {
         type int32;
         description "Number of mirror packet sent";
       }
     }
   }
   grouping packet-drop-records-block {
     leaf packet-drop-fpc-pic-name {
       type string;
       description "FPC PIC name";
     }
     leaf displayed-packet-drop-count {
       type uint32;
       description "Total packet-drop records displayed";
     }
     list packet-drop-information {
       description "Information about one or more packet-drops";
       leaf prompt {
         type string;
         description "Starting packet drop";
       }
       leaf drop-time {
         type uint32;
         description "Drop time";
       }
       leaf fpc-pic-name {
         type string;
         description "FPC PIC name";
       }
       leaf logical-system {
         type string;
         description "Logical system name";
       }
       leaf source-address {
         type jt:ipaddr;
         description "Source address";
       }
       leaf source-port {
         type uint32;
         description "Source port";
       }
       leaf destination-address {
         type jt:ipaddr;
         description "Destination address";
       }
       leaf destination-port {
         type uint32;
         description "Destination port";
       }
       leaf protocol {
         type string;
         description "IP protocol";
       }
       leaf ipid {
         type uint32;
         description "Ip identification";
       }
       leaf interface {
         type string;
         description "Interface name";
       }
       leaf drop-messages {
         type string;
         description "Drop message";
       }
       leaf tenant {
         type string;
         description "Tenant name";
       }
     }
   }
   grouping firewall-authentication-table-details-block {
     container fwauth-table-info {
       description "Information about firewall authentication table";
       leaf fwauth-total-users {
         type int32;
       }
     }
     list fwauth-user-logical-system {
       description "Logical system";
       leaf user-logical-name {
         type string;
         description "Logical system name";
       }
     }
     list fwauth-user-tenant-name {
       description "Tenant";
       leaf user-tenant-name {
         type string;
         description "Tenant name";
       }
     }
     container fwauth-users-table {
       list fwauth-entry {
         description "Current firewall user authentication information";
         leaf auth-id {
           type uint32;
           description "Unique id of this authentication session";
         }
         leaf src-ip {
           type string;
           description "Source Ip of user";
         }
         leaf src-zone {
           type string;
           description "Source zone user came in on";
         }
         leaf dst-zone {
           type string;
           description "Destination zone user was going to";
         }
         leaf access-profile {
           type string;
           description "Access profile used to authenticate user";
         }
         leaf age {
           type uint32;
           description "Time elapsed since inactivity";
         }
         leaf status {
           type string;
           description "Authentication state of user";
         }
         leaf user-name {
           type string;
           description "Name of user";
         }
       }
     }
   }
   grouping firewall-authentication-history-details-block {
     container fwauth-history-info {
       description "Historical information about firewall authentication";
       leaf fwauth-total-authentications {
         type int32;
       }
     }
     list fwauth-history-logical-system {
       description "Logical system";
       leaf history-logical-name {
         type string;
         description "Logical system name";
       }
     }
     list fwauth-history-tenant-name {
       description "Tenant";
       leaf history-tenant-name {
         type string;
         description "Tenant name";
       }
     }
     container fwauth-history-table {
       list fwauth-history {
         description "History of firewall user authentication";
         leaf auth-id {
           type uint32;
           description "Unique id of this authentication session";
         }
         leaf src-ip {
           type string;
           description "Source Ip of user";
         }
         leaf start-date {
           type string;
           description "Date user gained access";
         }
         leaf start-time {
           type string;
           description "Time user gained access";
         }
         leaf duration {
           type string;
           description "Duration of user's access";
         }
         leaf status {
           type string;
           description "Authentication state of user";
         }
         leaf user-name {
           type string;
           description "Name of user";
         }
       }
     }
   }
   grouping fwauth-debug-counters-block {
     leaf fwauth-debug-counters-title {
       type string;
       description "Fwauth group debug counters";
     }
     list fwauth-debug-counters-list {
       description "Fwauth group debug counters list";
       leaf fwauth-debug-counter-name {
         type string;
       }
       leaf fwauth-debug-counter-value {
         type uint32;
       }
     }
   }
   grouping show-ids-data-block {
     container ids-data-trap {
       description "Screen snmp trap";
       leaf ids-data-trap-name {
         type string;
         description "Screen snmp trap";
       }
       leaf ids-data-trap-value {
         type uint32;
         description "Configure trap value";
       }
     }
   }
   grouping show-ids-whitelist-block {
     list ids-logical-system {
       description "Logical system";
       leaf name {
         type string;
         description "Logical system name";
       }
     }
     list ids-wlist-status {
       leaf ids-wlist-addr {
         type jt:ipprefix;
         description "IP address";
       }
     }
   }
   grouping show-ids-status-block {
     leaf ids-description {
       type string;
       description "Description of screen";
     }
     list ids-logical-system {
       description "Logical system";
       leaf name {
         type string;
         description "Logical system name";
       }
     }
     container ids-status-header {
       leaf ids-status-header-name {
         type string;
         description "Name of header";
       }
       leaf ids-status-header-value {
         type string;
         description "Name of value";
       }
     }
     list ids-status {
       leaf ids-status-name {
         type string;
         description "Name of IDS configure";
       }
       leaf ids-status-value {
         type uint32;
         description "Configure value";
       }
     }
     list ids-white-list {
       leaf white-list-name {
         type string;
         description "Name of white list";
       }
       leaf ids-address {
         type jt:ipprefix;
         description "IP address";
       }
     }
     list ids-udp-wlist {
       leaf udp-wlist-string-name {
         type string;
         description "Name of white list string";
       }
       leaf udp-wlist-name {
         type string;
         description "Name of white list";
       }
     }
     list ids-ipblockfrag-wlist {
       leaf ipblockfrag-wlist-string-name {
         type string;
         description "Name of white list string";
       }
       leaf ipblockfrag-wlist-name {
         type string;
         description "Name of white list";
       }
     }
   }
   grouping destination-nat-pool-information-block {
     leaf-list logical-system-name {
       type string;
       description "Name of the logical system";
     }
     container total-destination-nat-pool-number {
       description "Total number of destination-nat pools";
       leaf total-pools {
         type uint32;
         description "Total number of destination-nat pool";
       }
     }
     list destination-nat-pool-entry {
       description "Information on the destination-nat pool";
       leaf interface-name {
         type string;
         description "Name of the services interface";
       }
       leaf service-set-name {
         type string;
         description "Name of the service set";
       }
       leaf pool-name {
         type string;
         description "Name of the source NAT pool";
       }
       leaf pool-description {
         type string;
         description "The description of the pool";
       }
       leaf pool-id {
         type uint32;
         description "The numerical pool number";
       }
       leaf routing-instance-name {
         type string;
         description "The name of the routing instance";
       }
       leaf total-pool-address {
         type uint32;
         description "The total number of address pools";
       }
       leaf address-pool-hits {
         type uint32;
         description "The number of translation hits on this pool address";
       }
       list pool-address-range {
         description "Information on address range";
         leaf address-range-low {
           type string;
           description "The low range of the address";
         }
         leaf address-range-high {
           type string;
           description "The high range of the address";
         }
         leaf address-port {
           type uint32;
           description "The port number used";
         }
       }
     }
   }
   grouping destination-nat-rule-application-information-block {
     leaf-list logical-system-name {
       type string;
       description "Name of the logical system";
     }
     list destination-nat-rule-app-entry {
       description "Application configured on the destination NAT rule";
       leaf rule-name {
         type string;
         description "The name of the rule";
       }
       leaf rule-set-name {
         type string;
         description "The name of the rule-set";
       }
       leaf rule-id {
         type uint32;
         description "The rule identifier";
       }
       list applications {
         list application {
           leaf application-name {
             type string;
             description "Name of the application";
           }
           list application-term {
             leaf protocol {
               type string;
               description "IP protocol";
             }
             list source-port-range {
               leaf low {
                 type int32;
                 description "The lower limit in the range of ports";
               }
               leaf high {
                 type int32;
                 description "The higher limit in the range of the ports";
               }
             }
             list destination-port-range {
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
           }
         }
       }
     }
   }
   grouping destination-nat-summary-information-block {
     list destination-nat-entry {
       description "Information about a destination NAT entry";
       leaf destination-nat-pool-name {
         type string;
       }
       leaf destination-address-range {
         type string;
       }
       leaf destination-port-number {
         type int32;
       }
     }
   }
   grouping source-nat-pool-information-block {
     list source-nat-pool-entry {
       leaf pool-name {
         type string;
         description "Name of the source NAT pool";
       }
       leaf address {
         type jt:ipaddr;
         description "IP address";
       }
       leaf pool-status {
         type string;
         description "Pool status";
       }
       leaf single-ports {
         type uint32;
         description "Number of allocated single ports";
       }
       leaf twin-ports {
         type uint32;
         description "Number of allocated twin ports";
       }
       leaf port-address-translation {
         type string;
         description "Support port address translation";
       }
       leaf host-address {
         type jt:ipaddr;
         description "Host IP address";
       }
       leaf references {
         type uint32;
         description "Reference count";
       }
     }
   }
   grouping source-nat-summary-block {
     list source-nat-entry {
       leaf pool-name {
         type string;
         description "Name of the source NAT pool";
       }
       leaf address-low {
         type jt:ipaddr;
         description "Start of the address range";
       }
       leaf address-high {
         type jt:ipaddr;
         description "End of the address range";
       }
       leaf interface {
         type string;
         description "Name of the interface";
       }
       leaf port-address-translation {
         type string;
         description "Support port address translation";
       }
       leaf service-set-name {
         type string;
         description "Name of the service set";
       }
       leaf interface-name {
         type string;
         description "Name of the services interface";
       }
     }
   }
   grouping source-nat-rule-application-information-block {
     leaf-list logical-system-name {
       type string;
       description "Name of the logical system";
     }
     list source-nat-rule-app-entry {
       description "Information on the source NAT rule";
       leaf rule-name {
         type string;
         description "The name of the rule";
       }
       leaf rule-set-name {
         type string;
         description "The name of the rule-set";
       }
       leaf rule-id {
         type uint32;
         description "The rule identifier";
       }
       list applications {
         list application {
           leaf application-name {
             type string;
             description "Name of the application";
           }
           list application-term {
             leaf protocol {
               type string;
               description "IP protocol";
             }
             list source-port-range {
               leaf low {
                 type int32;
                 description "The lower limit in the range of ports";
               }
               leaf high {
                 type int32;
                 description "The higher limit in the range of the ports";
               }
             }
             list destination-port-range {
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
           }
         }
       }
     }
   }
   grouping source-nat-pool-distribution-block {
     leaf state {
       type string;
       description "Source nat pool-distribution state";
     }
   }
   grouping static-nat-rule-information-block {
     leaf-list logical-system-name {
       type string;
       description "Name of the logical system";
     }
     container total-static-nat-rules {
       description "Total number of static-nat rules";
       leaf total-rules {
         type uint32;
         description "Total number of destination-nat rules";
       }
     }
     container total-static-nat-rule-ref-addr-num {
       description "Total referenced IPv4/IPv6 ip-prefixes in static NAT rule";
       leaf total-static-nat-rule-ref-addr-num-v4 {
         type uint32;
         description "Total referenced IPv4 ip-prefixes in static NAT rule";
       }
       leaf total-static-nat-rule-ref-addr-num-v6 {
         type uint32;
         description "Total referenced IPv6 ip-prefixes in static NAT rule";
       }
     }
     list static-nat-rule-entry {
       description "Information on the static-nat rule";
       leaf interface-name {
         type string;
         description "Name of the services interface";
       }
       leaf service-set-name {
         type string;
         description "Name of the service set";
       }
       leaf rule-name {
         type string;
         description "The name of the rule";
       }
       leaf rule-set-name {
         type string;
         description "The name of the rule-set";
       }
       leaf rule-description {
         type string;
         description "The description of the rule";
       }
       leaf rule-id {
         type uint32;
         description "The rule identifier";
       }
       leaf rule-matching-position {
         type uint32;
         description "The matching criteria or position of the rule";
       }
       leaf rule-from-context {
         type string;
         description "The from context based on the rule definition";
       }
       leaf rule-from-context-name {
         type string;
         description "The name of the zone, routing instance, interface, or rouing group";
       }
       leaf rule-destination-address-prefix {
         type string;
         description "The destination address prefix";
       }
       leaf rule-host-address-prefix {
         type string;
         description "The host address prefix";
       }
       leaf rule-address-netmask {
         type string;
         description "The netmask of address";
       }
       leaf rule-host-routing-instance {
         type string;
         description "The host routing-instance of the rule";
       }
       leaf clear-alarm {
         type uint32;
         description "Clear alarm threshold of the rule";
       }
       leaf raise-alarm {
         type uint32;
         description "Raise alarm threshold of the rule";
       }
       leaf rule-translation-hits {
         type uint32;
         description "Number of rule translation hits on the specified object";
       }
       leaf succ-hits {
         type uint32;
         description "Number of succ translation hits on the specified object";
       }
       leaf failed-hits {
         type uint32;
         description "Number of failed translation hits on the specified object";
       }
       leaf concurrent-hits {
         type uint32;
         description "Number of concurrent translation hits on the specified object";
       }
       list static-source-address-range-entry {
         leaf rule-source-address {
           type string;
           description "The source address";
         }
         leaf rule-source-address-low-range {
           type string;
           description "The low range of the source address";
         }
         leaf rule-source-address-high-range {
           type string;
           description "The high range of the source address";
         }
       }
       list static-source-port-entry {
         leaf static-rule-source-port-low {
           type uint32;
           description "The low source port";
         }
         leaf static-rule-source-port-high {
           type uint32;
           description "The high source port";
         }
       }
       leaf rule-destination-port-low {
         type uint32;
         description "The low destination port";
       }
       leaf rule-destination-port-high {
         type uint32;
         description "The high destination port";
       }
       leaf rule-host-port-low {
         type uint32;
         description "The low host port";
       }
       leaf rule-host-port-high {
         type uint32;
         description "The high host port";
       }
       leaf rule-destination-nptv6-address-prefix {
         type string;
         description "The destination NPTv6 address prefix";
       }
       leaf rule-destination-nptv6-netmask {
         type string;
         description "The netmask of destination NPTv6 address";
       }
     }
   }
   grouping interface-nat-ports-information-block {
     list interface-nat-ports-entry {
       leaf pool-index {
         type uint32;
         description "Port pool index";
       }
       leaf total-ports {
         type uint32;
         description "Total number of ports in the pool";
       }
       leaf single-ports-allocated {
         type uint32;
         description "Number of allocated single ports";
       }
       leaf single-ports-available {
         type uint32;
         description "Number of available single ports";
       }
       leaf twin-ports-allocated {
         type uint32;
         description "Number of allocated twin ports";
       }
       leaf twin-ports-available {
         type uint32;
         description "Number of available twin ports";
       }
       leaf-list logical-system-name {
         type string;
         description "Name of the logical system";
       }
     }
   }
   grouping security-policies-block {
     leaf-list logical-system-name {
       type string;
       description "Name of the logical system";
     }
     leaf tenant-name {
       type string;
       description "Tenant name";
     }
     leaf-list default-policy {
       type string;
       description "Default policy for the logical system";
     }
     leaf-list default-policy-log-profile-id {
       type uint32;
       description "Default policy log profile id";
     }
     leaf-list pre-id-default-policy {
       type string;
       description "Pre-id-default-policy for the logical system";
     }
     leaf all-logical-systems {
       type string;
       description "All logical systems";
     }
     list security-context {
       list context-information {
         leaf global-context {
           type empty;
           description "Global policy conext";
         }
         leaf source-zone-name {
           type string;
           description "Name of the source zone";
         }
         leaf destination-zone-name {
           type string;
           description "Name of the destination zone";
         }
       }
       container policies {
         list policy-information {
           leaf policy-name {
             type string;
             description "Name of the policy";
           }
           leaf policy-state {
             type string;
             description "State of the policy";
           }
           leaf policy-identifier {
             type uint32;
             description "Unique identifier for the policy";
           }
           leaf scope-policy-identifier {
             type uint32;
             description "Scope policy identifier for the policy";
           }
           leaf policy-sequence-number {
             type int32;
             description "Sequence number for the policy in a given zone context";
           }
           leaf log-profile-id {
             type uint32;
             description "Unique id for the log profile";
           }
           leaf sfw-rule-name {
             type string;
             description "Name of the stateful-firewall-rule";
           }
           leaf sfw-rule-set-name {
             type string;
             description "Name of the stateful-firewall-rule-set";
           }
           leaf service-set-name {
             type string;
             description "Name of the service set";
           }
           leaf interface-name {
             type string;
             description "Name of the services interface";
           }
           leaf match-direction {
             type string;
             description "Match Direction of the policy";
           }
           leaf policy-description {
             type string;
             description "Description of the policy";
           }
           leaf explicit-proxy-policy-sequence-number {
             type int32;
             description "Sequence number for the policy in a given zone context";
           }
           leaf explicit-proxy-policy-description {
             type string;
             description "Description of the policy";
           }
           container policy-action {
             leaf action-type {
               type string;
             }
             leaf tunnel {
               type empty;
               description "Tunnel packets that match this policy";
             }
             leaf nat-source {
               type empty;
               description "Apply source NAT to packets that match this policy";
             }
             leaf nat-destination {
               type string;
               description "Apply destination NAT to packets that match this policy";
             }
             leaf firewall-authentication {
               type empty;
               description "Authenticate the client that sent the packets that match this        policy";
             }
             leaf services-offload {
               type empty;
               description "Services-offload options of the policy";
             }
             leaf no-services-offload {
               type empty;
               description "No-services-offload options of the policy";
             }
             leaf advanced-connection-tracking {
               type empty;
               description "Advanced-connection-tracking option of the policy";
             }
             leaf application-services {
               type empty;
               description "Application services";
             }
             leaf feed {
               type empty;
               description "Feed";
             }
             leaf uac-enabled {
               type empty;
               description "Enable unified access control enforcement of policy";
             }
             leaf log {
               type empty;
               description "Log the session of packets that match this policy";
             }
             leaf count {
               type empty;
               description "Count packets that match this policy";
             }
             leaf scheduled {
               type empty;
               description "Schedule the policy based on a scheduler";
             }
           }
           list context-information {
             leaf global-context {
               type empty;
               description "Global policy conext";
             }
             leaf source-zone-name {
               type string;
               description "Name of the source zone";
             }
             leaf destination-zone-name {
               type string;
               description "Name of the destination zone";
             }
           }
           container policy-type-information {
             leaf policy-type-string {
               type string;
               description "Type of policy";
             }
             leaf policy-type-dynamic-policy-count {
               type int32;
               description "Number of dynamic policies under this scope";
             }
           }
           container multiple-source-zones {
             container source-zone {
               leaf source-zone-name {
                 type string;
                 description "Name of the source zone";
               }
             }
           }
           container multiple-destination-zones {
             container destination-zone {
               leaf destination-zone-name {
                 type string;
                 description "Name of the destination zone";
               }
             }
           }
           container source-addresses {
             container source-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container destination-addresses {
             container destination-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container source-end-user-profile {
             leaf source-end-user-profile-name {
               type string;
               description "Name of the source-end-user-profile";
             }
           }
           container destination-identity-context-profile {
             leaf destination-identity-context-profile-name {
               type string;
               description "Name of the destination-identity-context-profile-name";
             }
           }
           list applications {
             list application {
               leaf application-name {
                 type string;
                 description "Name of the application";
               }
               list application-term {
                 list source-port-range {
                   leaf low {
                     type int32;
                     description "The lower limit in the range of ports";
                   }
                   leaf high {
                     type int32;
                     description "The higher limit in the range of the ports";
                   }
                 }
                 list destination-port-range {
                   leaf ports_array {
                     type string;
                     description "The ports array string";
                   }
                   leaf single {
                     type int32;
                     description "The single port";
                   }
                   leaf low {
                     type int32;
                     description "The lower limit in the range of ports";
                   }
                   leaf high {
                     type int32;
                     description "The higher limit in the range of the ports";
                   }
                 }
                 container icmp-info {
                   leaf icmp-type {
                     type string;
                     description "The icmp application type";
                   }
                   leaf icmp-code {
                     type string;
                     description "The icmp application code";
                   }
                 }
                 container rpc-information {
                   leaf rpc-uuid {
                     type string;
                     description "The rpc application uuid";
                   }
                   container program-number-range {
                     leaf low {
                       type int32;
                       description "The lower limit in the range of ports";
                     }
                     leaf high {
                       type int32;
                       description "The higher limit in the range of the ports";
                     }
                   }
                 }
                 leaf protocol {
                   type string;
                   description "IP protocol";
                 }
                 leaf alg-name {
                   type string;
                   description "Name of the application layer gateway";
                 }
                 leaf inactivity-timeout {
                   type int32;
                   description "Idle timeout for any session that match this application";
                 }
                 leaf gate-timeout {
                   type int32;
                   description "Gate timeout for ALG child session to get established";
                 }
                 leaf child-inactivity-timeout {
                   type int32;
                   description "Idle timeout for ALG child session that is created after gate hit";
                 }
               }
             }
           }
           container policy-dynamic-applications {
             list policy-dynamic-application-name {
               leaf dynamic-application-name {
                 type string;
                 description "Dynamic application name in the policy";
               }
               leaf dynamic-application-id {
                 type uint32;
                 description "Dynamic application identifier in the policy";
               }
             }
             list policy-dynamic-application {
               leaf dynamic-application-name {
                 type string;
                 description "Dynamic application name in the policy";
               }
               leaf dynamic-application-id {
                 type uint32;
                 description "Dynamic application identifier in the policy";
               }
             }
             list policy-dynamic-application-group {
               leaf dynamic-application-group-name {
                 type string;
                 description "Dynamic application group name in the policy";
               }
               leaf dynamic-application-group-id {
                 type uint32;
                 description "Dynamic application group identifier in the policy";
               }
             }
           }
           container policy-url-categories {
             list policy-url-category-name {
               leaf url-category-name {
                 type string;
                 description "Url category name in the policy";
               }
               leaf url-category-id {
                 type uint32;
                 description "Url category identifier in the policy";
               }
             }
             list policy-url-category {
               leaf url-category-name {
                 type string;
                 description "Url category name in the policy";
               }
               leaf url-category-id {
                 type uint32;
                 description "Url category identifier in the policy";
               }
             }
           }
           container source-identities {
             container source-identity {
               leaf role-name {
                 type string;
                 description "Name of the role";
               }
             }
           }
           container destination-identity-context {
             container destination-context {
               leaf role-name {
                 type string;
                 description "Name of the role";
               }
             }
           }
           container source-identities-feeds {
             container source-identity-feed {
               leaf feed-name {
                 type string;
                 description "Name of the feed";
               }
             }
           }
           container destination-identities-feeds {
             container destination-identity-feed {
               leaf feed-name {
                 type string;
                 description "Name of the feed";
               }
             }
           }
           container aamw-policy-info {
             leaf aamw-info {
               type string;
             }
           }
           container dynapp-redir-profile {
             leaf dynapp-redir-profile-name {
               type string;
               description "Name of the redirect profile";
             }
           }
           container unknown-source-identities {
             leaf role-name {
               type string;
               description "Name of the role";
             }
           }
           container unknown-destination-identities {
             leaf role-name {
               type string;
               description "Name of the role";
             }
           }
           container policy-tcp-options {
             leaf policy-tcp-options-syn-check {
               type string;
               description "Per policy SYN check required flag";
             }
             leaf policy-tcp-options-sequence-check {
               type string;
               description "Per policy Sequence check required flag";
             }
             leaf policy-tcp-options-window-scale {
               type string;
               description "Per policy window scale enabled flag";
             }
             leaf policy-tcp-options-initial-tcp-mss {
               type uint32;
               description "Initial direction TCP MSS for the policy";
             }
             leaf policy-tcp-options-reverse-tcp-mss {
               type uint32;
               description "Reverse direction TCP MSS for the policy";
             }
           }
           container policy-tunnel {
             leaf tunnel-name {
               type string;
               description "Name of the tunnel";
             }
             leaf tunnel-type {
               type string;
               description "Type of tunnel";
             }
             leaf tunnel-identifier {
               type int32;
               description "Unique identifier for the tunnel";
             }
             leaf pair-policy-name {
               type string;
               description "Name of the pair policy";
             }
           }
           container policy-tunnel-inspection {
             leaf policy-tunnel-inspection-profile {
               type string;
               description "Policy tunnel inspection profile";
             }
           }
           container policy-firewall-authentication {
             leaf authentication-type {
               type string;
               description "Type of authentication";
             }
             leaf access-profile-name {
               type string;
               description "Name of the access profile";
             }
             leaf web-redirect {
               type string;
               description "Web-redirect flag for http";
             }
             leaf web-redirect-to-https {
               type string;
               description "Web-redirect-to-https flag";
             }
             leaf auth-only-browser {
               type string;
               description "Auth-only-browser flag";
             }
             leaf push-to-identity-management {
               type string;
               description "Push-to-identity-management flag";
             }
             leaf ssl-termination-profile {
               type string;
               description "Name of the ssl termination profile for HTTPS";
             }
             leaf domain {
               type string;
               description "Domain name";
             }
             leaf client-match-name {
               type string;
               description "Name to match, as given by client";
             }
             leaf auth-user-agent {
               type string;
               description "Responde to only HTTP request with given user agent";
             }
           }
           container policy-application-services {
             leaf gprs-gtp-profile {
               type string;
               description "Status of GPRS Tunneling Protocol Profile";
             }
             leaf gprs-sctp-profile {
               type string;
               description "Status of GPRS Stream Control Protocol profile";
             }
             leaf idp {
               type string;
             }
             leaf uac-policy {
               type string;
             }
             leaf utm {
               type string;
               description "Status of Unified Threat Management";
             }
             leaf advanced-anti-malware {
               type string;
               description "Advanced-anti-malware service";
             }
             leaf icap-redirect-profile {
               type string;
               description "ICAP Redirect service";
             }
             leaf security-intelligence {
               type string;
               description "Security intelligence service";
             }
             leaf wan-acceleration {
               type string;
             }
             leaf security-metadata-streaming-policy {
               type string;
               description "Security metadata streaming policy";
             }
             leaf anti-virus-policy {
               type string;
               description "Anti-virus policy";
             }
             leaf captive-portal {
               type string;
               description "Secure web gateway captive portal";
             }
             container application-firewall {
               container rule-set-info {
                 container rule-set {
                   leaf name {
                     type string;
                     description "Name information";
                   }
                   container rule-list {
                     list rule {
                       leaf name {
                         type string;
                         description "Name information";
                       }
                       leaf action {
                         type string;
                         description "Action specified for one rule";
                       }
                       container dynamic-application-list {
                         leaf-list dynamic-application {
                           type string;
                           description "Name of the dynamic application";
                         }
                       }
                       container dynamic-application-group-list {
                         leaf-list dynamic-application-group {
                           type string;
                           description "Name of the dynamic application group";
                         }
                       }
                     }
                     container default-rule {
                       leaf action {
                         type string;
                         description "Action specified for one rule";
                       }
                     }
                   }
                 }
               }
             }
             container application-acceleration {
               leaf application-acceleration-profile-name {
                 type string;
                 description "Application acceleration profile name";
               }
               leaf application-acceleration-service-options {
                 type string;
                 description "Application acceleration service options";
               }
             }
             container ssl-initiation {
               leaf ssl-initiation-profile-name {
                 type string;
                 description "SSL initiation profile name";
               }
             }
             container ssl-termination {
               leaf ssl-termination-profile-name {
                 type string;
                 description "SSL termination profile name";
               }
             }
             container ssl-proxy {
               leaf ssl-proxy-profile-name {
                 type string;
                 description "SSL proxy profile name";
               }
             }
             container web-proxy {
               leaf web-proxy-profile-name {
                 type string;
                 description "Web proxy profile name";
               }
             }
             container application-traffic-control {
               leaf rule-set-name {
                 type string;
                 description "Application traffic control rule-set name";
               }
             }
             container wx-optimizer {
               leaf wx-optimizer-profile-name {
                 type string;
                 description "Wan Optimizer Profile Name";
               }
               leaf wx-optimizer-service-options {
                 type string;
                 description "Wan Optimizer Service Options";
               }
             }
           }
           container policy-count-alarms {
             container alarm {
               leaf alarm-count {
                 type int32;
                 description "Number of the times alarm was raised";
               }
               leaf alarm-type {
                 type string;
                 description "Type of the alarm";
               }
             }
           }
           container policy-log {
             leaf log-session-creation {
               type empty;
               description "Log when a new session gets created for the policy";
             }
             leaf log-session-close {
               type empty;
               description "Log when a new session gets closed for the policy";
             }
           }
           container policy-feed {
             leaf policy-feed-type {
               type string;
               description "Add session element to security intellgence feed";
             }
           }
           container policy-scheduler {
             leaf attached-scheduler-name {
               type string;
               description "Information about the scheduler name";
             }
           }
           container policy-statistics-information {
             leaf pfe-identifier {
               type string;
               description "An identifier for a PFE";
             }
             leaf input-bytes {
               type int32;
               description "Number of incoming bytes";
             }
             leaf input-byte-rate {
               type int32;
               description "Number of incoming bytes per second";
             }
             leaf input-bytes-init {
               type int32;
               description "Number of incoming bytes in initial direction";
             }
             leaf input-byte-rate-init {
               type int32;
               description "Number of incoming bytes per second in initial direction";
             }
             leaf input-bytes-reply {
               type int32;
               description "Number of incoming bytes in reply direction";
             }
             leaf input-byte-rate-reply {
               type int32;
               description "Number of incoming bytes per second in reply direction";
             }
             leaf output-bytes {
               type int32;
               description "Number of outgoing bytes";
             }
             leaf output-byte-rate {
               type int32;
               description "Number of outgoing bytes per second";
             }
             leaf output-bytes-init {
               type int32;
               description "Number of outgoing bytes in initial direction";
             }
             leaf output-byte-rate-init {
               type int32;
               description "Number of outgoing bytes per second in initial direction";
             }
             leaf output-bytes-reply {
               type int32;
               description "Number of outgoing bytes in reply direction";
             }
             leaf output-byte-rate-reply {
               type int32;
               description "Number of outgoing bytes per second in reply direction";
             }
             leaf input-packets {
               type int32;
               description "Number of incoming packets";
             }
             leaf input-packet-rate {
               type int32;
               description "Number of incoming packets per second";
             }
             leaf input-packets-init {
               type int32;
               description "Number of incoming packets in initial direction";
             }
             leaf input-packet-rate-init {
               type int32;
               description "Number of incoming packets per second in initial direction";
             }
             leaf input-packets-reply {
               type int32;
               description "Number of incoming packets in reply direction";
             }
             leaf input-packet-rate-reply {
               type int32;
               description "Number of incoming packets per second in reply direction";
             }
             leaf output-packets {
               type int32;
               description "Number of outgoing packets";
             }
             leaf output-packet-rate {
               type int32;
               description "Number of outgoing packets per second";
             }
             leaf output-packets-init {
               type int32;
               description "Number of outgoing packets in initial direction";
             }
             leaf output-packet-rate-init {
               type int32;
               description "Number of outgoing packets per second in initial direction";
             }
             leaf output-packets-reply {
               type int32;
               description "Number of outgoing packets in reply direction";
             }
             leaf output-packet-rate-reply {
               type int32;
               description "Number of outgoing packets per second in reply direction";
             }
             leaf session-creations {
               type int32;
               description "Number of sessions created";
             }
             leaf session-creation-rate {
               type int32;
               description "Number of sessions created per second";
             }
             leaf active-sessions {
               type int32;
               description "Number of active sessions";
             }
             leaf session-deletions {
               type int32;
               description "Number of sessions deleted";
             }
             leaf policy-lookups {
               type int32;
               description "Number of policy lookups";
             }
           }
           container source-vrfs {
             container source-vrf {
               leaf source-vrf-name {
                 type string;
                 description "Name of the source vrf group";
               }
             }
           }
           container destination-vrfs {
             container destination-vrf {
               leaf destination-vrf-name {
                 type string;
                 description "Name of the destination vrf";
               }
             }
           }
         }
       }
     }
     list policy-internal-information {
       leaf current-policies {
         type int32;
         description "Number of policies";
       }
       leaf maximum-policies {
         type int32;
         description "Maximum number of policies";
       }
       leaf current-global-policies {
         type int32;
         description "Number of global policies";
       }
       leaf current-scheduler-policies {
         type int32;
         description "Number of policies with scheduler";
       }
       leaf current-statistic-counters {
         type int32;
         description "Number of statistics counters";
       }
       leaf maximum-statistic-counters {
         type int32;
         description "Maximum statistics counters";
       }
       leaf current-unified-policies {
         type int32;
         description "Number of unified policies";
       }
       leaf current-policy-context {
         type int32;
         description "Number of policy contexts";
       }
       leaf maximum-policy-context {
         type int32;
         description "Maximum Number of policy contexts";
       }
       leaf current-policy-per-context {
         type int32;
         description "Number of policies per contexts";
       }
       leaf maximum-policy-per-context {
         type int32;
         description "Maximum policies per contexts";
       }
       leaf current-source-address-per-policy {
         type int32;
         description "Number of source addresses per policy";
       }
       leaf maximum-source-address-per-policy {
         type int32;
         description "Maximum source addresses per policy";
       }
       leaf current-destination-address-per-policy {
         type int32;
         description "Number of destination addresses per policy";
       }
       leaf maximum-destination-address-per-policy {
         type int32;
         description "Maximum destination addresses per policy";
       }
       leaf current-application-per-policy {
         type int32;
         description "Number of applications per policy";
       }
       leaf maximum-application-per-policy {
         type int32;
         description "Maximum applications per policy";
       }
       leaf current-dynamic-application-per-policy {
         type int32;
         description "Number of dynamic applications per policy";
       }
       leaf maximum-dynamic-application-per-policy {
         type int32;
         description "Maximum dynamic applications per policy";
       }
       leaf current-url-category-per-policy {
         type int32;
         description "Number of url category per policy";
       }
       leaf maximum-url-category-per-policy {
         type int32;
         description "Maximum url category per policy";
       }
       leaf current-identity-per-policy {
         type int32;
         description "Number of identities per policy";
       }
       leaf maximum-identity-per-policy {
         type int32;
         description "Maximum identities per policy";
       }
       leaf current-userid-feed-per-policy {
         type int32;
         description "Number of match source/destination identity feeds per policy";
       }
       leaf maximum-userid-feed-per-policy {
         type int32;
         description "Maximum match source/destination identity feeds per policy";
       }
       leaf messages-received {
         type int32;
         description "Number of dynamic policy messages received";
       }
       leaf messages-rejected {
         type int32;
         description "Number of dynamic policy messages rejected";
       }
       leaf add-received {
         type int32;
         description "Number of add dynamic policy messages";
       }
       leaf delete-received {
         type int32;
         description "Number of delete dynamic policy messages";
       }
       leaf clear-received {
         type int32;
         description "Number of clear dynamic policy messages";
       }
       leaf invalid-received {
         type int32;
         description "Number of invalid dynamic policy messages";
       }
       leaf add-pfe {
         type int32;
         description "Number of add dynamic policy messages sent to PFE";
       }
       leaf delete-pfe {
         type int32;
         description "Number of delete dynamic policy messages sent to PFE";
       }
       leaf clear-pfe {
         type int32;
         description "Number of clear dynamic policy messages sent to PFE";
       }
       leaf add-success {
         type int32;
         description "Number of add dynamic policy added successfully";
       }
       leaf delete-success {
         type int32;
         description "Number of delete dynamic policy deleted successfully";
       }
       leaf clear-success {
         type int32;
         description "Number of clear dynamic policy cleared successfully";
       }
       leaf add-failed {
         type int32;
         description "Number of add dynamic policy messages failed";
       }
       leaf delete-failed {
         type int32;
         description "Number of delete dynamic policy messages failed";
       }
       leaf clear-failed {
         type int32;
         description "Number of clear dynamic policy messages failed";
       }
       leaf ssam-sent {
         type int32;
         description "Number of SSAM dynamic policy messages sent";
       }
       leaf ssam-success {
         type int32;
         description "Number of SSAM dynamic policy messages sent successfully";
       }
       leaf ssam-failed {
         type int32;
         description "Number of SSAM dynamic policy messages sent failures";
       }
       leaf invalid-configuration {
         type int32;
         description "Number of dynamic policy failed due to invalid config";
       }
       leaf invalid-scope {
         type int32;
         description "Number of dynamic policy failed due to invalid scope";
       }
       leaf dependent-lookup-status {
         type string;
         description "Dependent dynamic application lookup status";
       }
       leaf implicit-match-status {
         type string;
         description "Implicit match status";
       }
     }
     list policy-zone-context {
       leaf-list logical-system-name {
         type string;
         description "Name of the logical system";
       }
       leaf tenant-name {
         type string;
         description "Tenant name";
       }
       list policy-zone-context-entry {
         leaf policy-zone-context-from-zone {
           type string;
           description "From zone of the context";
         }
         leaf policy-zone-context-to-zone {
           type string;
           description "To zone of the context";
         }
         leaf policy-zone-context-policy-count {
           type uint32;
           description "Policy count of the context";
         }
       }
     }
     list policy-context-checksum-info {
       leaf-list logical-system-name {
         type string;
         description "Name of the logical system";
       }
       leaf tenant-name {
         type string;
         description "Tenant name";
       }
       list policy-context-checksum-entry {
         leaf source-zone-name {
           type string;
           description "Name of the source zone";
         }
         leaf destination-zone-name {
           type string;
           description "Name of the destination zone";
         }
         leaf context-checksum {
           type string;
           description "Checksum for the policy context";
         }
       }
     }
   }
   grouping explicit-proxy-policies-block {
     leaf-list logical-system-name {
       type string;
       description "Name of the logical system";
     }
     leaf policy-description {
       type string;
       description "Description of the policy";
     }
     leaf explicit-proxy-policy-description {
       type string;
       description "Description of the policy";
     }
     leaf policy-sequence-number {
       type int32;
       description "Sequence number for the policy in a given zone context";
     }
     leaf explicit-proxy-policy-sequence-number {
       type int32;
       description "Sequence number for the policy in a given zone context";
     }
     leaf all-logical-systems {
       type string;
       description "All logical systems";
     }
     leaf explicit-proxy-policy-name {
       type string;
       description "Name of the policy";
     }
     list explicit-proxy-security-context {
       list explicit-proxy-context-information {
         leaf explicit-proxy-profile-name {
           type string;
           description "Name of the source zone";
         }
         leaf-list ep-profile-pre-id-default-policy {
           type string;
           description "Explicit proxy Pre-id-default-policy for the logical system";
         }
         leaf-list ep-profile-default-policy {
           type string;
           description "Default explicit proxy profile policy for the logical system";
         }
       }
       container policies {
         list policy-information {
           leaf policy-name {
             type string;
             description "Name of the policy";
           }
           leaf policy-state {
             type string;
             description "State of the policy";
           }
           leaf policy-identifier {
             type uint32;
             description "Unique identifier for the policy";
           }
           leaf scope-policy-identifier {
             type uint32;
             description "Scope policy identifier for the policy";
           }
           leaf policy-sequence-number {
             type int32;
             description "Sequence number for the policy in a given zone context";
           }
           leaf log-profile-id {
             type uint32;
             description "Unique id for the log profile";
           }
           leaf service-set-name {
             type string;
             description "Name of the service set";
           }
           leaf interface-name {
             type string;
             description "Name of the services interface";
           }
           leaf sfw-rule-name {
             type string;
             description "Name of the stateful-firewall-rule";
           }
           leaf sfw-rule-set-name {
             type string;
             description "Name of the stateful-firewall-rule-set";
           }
           leaf match-direction {
             type string;
             description "Match Direction of the policy";
           }
           leaf policy-description {
             type string;
             description "Description of the policy";
           }
           leaf explicit-proxy-policy-sequence-number {
             type int32;
             description "Sequence number for the policy in a given zone context";
           }
           leaf explicit-proxy-policy-description {
             type string;
             description "Description of the policy";
           }
           container policy-action {
             leaf action-type {
               type string;
             }
             leaf tunnel {
               type empty;
               description "Tunnel packets that match this policy";
             }
             leaf nat-source {
               type empty;
               description "Apply source NAT to packets that match this policy";
             }
             leaf nat-destination {
               type string;
               description "Apply destination NAT to packets that match this policy";
             }
             leaf firewall-authentication {
               type empty;
               description "Authenticate the client that sent the packets that match this        policy";
             }
             leaf services-offload {
               type empty;
               description "Services-offload options of the policy";
             }
             leaf no-services-offload {
               type empty;
               description "No-services-offload options of the policy";
             }
             leaf advanced-connection-tracking {
               type empty;
               description "Advanced-connection-tracking option of the policy";
             }
             leaf application-services {
               type empty;
               description "Application services";
             }
             leaf feed {
               type empty;
               description "Feed";
             }
             leaf uac-enabled {
               type empty;
               description "Enable unified access control enforcement of policy";
             }
             leaf log {
               type empty;
               description "Log the session of packets that match this policy";
             }
             leaf count {
               type empty;
               description "Count packets that match this policy";
             }
             leaf scheduled {
               type empty;
               description "Schedule the policy based on a scheduler";
             }
           }
           list context-information {
             leaf global-context {
               type empty;
               description "Global policy conext";
             }
             leaf source-zone-name {
               type string;
               description "Name of the source zone";
             }
             leaf destination-zone-name {
               type string;
               description "Name of the destination zone";
             }
           }
           container policy-type-information {
             leaf policy-type-string {
               type string;
               description "Type of policy";
             }
             leaf policy-type-dynamic-policy-count {
               type int32;
               description "Number of dynamic policies under this scope";
             }
           }
           container multiple-source-zones {
             container source-zone {
               leaf source-zone-name {
                 type string;
                 description "Name of the source zone";
               }
             }
           }
           container multiple-destination-zones {
             container destination-zone {
               leaf destination-zone-name {
                 type string;
                 description "Name of the destination zone";
               }
             }
           }
           container source-addresses {
             container source-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container destination-addresses {
             container destination-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container source-end-user-profile {
             leaf source-end-user-profile-name {
               type string;
               description "Name of the source-end-user-profile";
             }
           }
           container destination-identity-context-profile {
             leaf destination-identity-context-profile-name {
               type string;
               description "Name of the destination-identity-context-profile-name";
             }
           }
           list applications {
             list application {
               leaf application-name {
                 type string;
                 description "Name of the application";
               }
               list application-term {
                 list source-port-range {
                   leaf low {
                     type int32;
                     description "The lower limit in the range of ports";
                   }
                   leaf high {
                     type int32;
                     description "The higher limit in the range of the ports";
                   }
                 }
                 list destination-port-range {
                   leaf ports_array {
                     type string;
                     description "The ports array string";
                   }
                   leaf single {
                     type int32;
                     description "The single port";
                   }
                   leaf low {
                     type int32;
                     description "The lower limit in the range of ports";
                   }
                   leaf high {
                     type int32;
                     description "The higher limit in the range of the ports";
                   }
                 }
                 container icmp-info {
                   leaf icmp-type {
                     type string;
                     description "The icmp application type";
                   }
                   leaf icmp-code {
                     type string;
                     description "The icmp application code";
                   }
                 }
                 container rpc-information {
                   leaf rpc-uuid {
                     type string;
                     description "The rpc application uuid";
                   }
                   container program-number-range {
                     leaf low {
                       type int32;
                       description "The lower limit in the range of ports";
                     }
                     leaf high {
                       type int32;
                       description "The higher limit in the range of the ports";
                     }
                   }
                 }
                 leaf protocol {
                   type string;
                   description "IP protocol";
                 }
                 leaf alg-name {
                   type string;
                   description "Name of the application layer gateway";
                 }
                 leaf inactivity-timeout {
                   type int32;
                   description "Idle timeout for any session that match this application";
                 }
                 leaf gate-timeout {
                   type int32;
                   description "Gate timeout for ALG child session to get established";
                 }
                 leaf child-inactivity-timeout {
                   type int32;
                   description "Idle timeout for ALG child session that is created after gate hit";
                 }
               }
             }
           }
           container policy-dynamic-applications {
             list policy-dynamic-application-name {
               leaf dynamic-application-name {
                 type string;
                 description "Dynamic application name in the policy";
               }
               leaf dynamic-application-id {
                 type uint32;
                 description "Dynamic application identifier in the policy";
               }
             }
             list policy-dynamic-application {
               leaf dynamic-application-name {
                 type string;
                 description "Dynamic application name in the policy";
               }
               leaf dynamic-application-id {
                 type uint32;
                 description "Dynamic application identifier in the policy";
               }
             }
             list policy-dynamic-application-group {
               leaf dynamic-application-group-name {
                 type string;
                 description "Dynamic application group name in the policy";
               }
               leaf dynamic-application-group-id {
                 type uint32;
                 description "Dynamic application group identifier in the policy";
               }
             }
           }
           container policy-url-categories {
             list policy-url-category-name {
               leaf url-category-name {
                 type string;
                 description "Url category name in the policy";
               }
               leaf url-category-id {
                 type uint32;
                 description "Url category identifier in the policy";
               }
             }
             list policy-url-category {
               leaf url-category-name {
                 type string;
                 description "Url category name in the policy";
               }
               leaf url-category-id {
                 type uint32;
                 description "Url category identifier in the policy";
               }
             }
           }
           container source-identities {
             container source-identity {
               leaf role-name {
                 type string;
                 description "Name of the role";
               }
             }
           }
           container destination-identity-context {
             container destination-context {
               leaf role-name {
                 type string;
                 description "Name of the role";
               }
             }
           }
           container source-identities-feeds {
             container source-identity-feed {
               leaf feed-name {
                 type string;
                 description "Name of the feed";
               }
             }
           }
           container destination-identities-feeds {
             container destination-identity-feed {
               leaf feed-name {
                 type string;
                 description "Name of the feed";
               }
             }
           }
           container aamw-policy-info {
             leaf aamw-info {
               type string;
             }
           }
           container dynapp-redir-profile {
             leaf dynapp-redir-profile-name {
               type string;
               description "Name of the redirect profile";
             }
           }
           container unknown-source-identities {
             leaf role-name {
               type string;
               description "Name of the role";
             }
           }
           container unknown-destination-identities {
             leaf role-name {
               type string;
               description "Name of the role";
             }
           }
           container policy-tcp-options {
             leaf policy-tcp-options-syn-check {
               type string;
               description "Per policy SYN check required flag";
             }
             leaf policy-tcp-options-sequence-check {
               type string;
               description "Per policy Sequence check required flag";
             }
             leaf policy-tcp-options-window-scale {
               type string;
               description "Per policy window scale enabled flag";
             }
             leaf policy-tcp-options-initial-tcp-mss {
               type uint32;
               description "Initial direction TCP MSS for the policy";
             }
             leaf policy-tcp-options-reverse-tcp-mss {
               type uint32;
               description "Reverse direction TCP MSS for the policy";
             }
           }
           container policy-tunnel {
             leaf tunnel-name {
               type string;
               description "Name of the tunnel";
             }
             leaf tunnel-type {
               type string;
               description "Type of tunnel";
             }
             leaf tunnel-identifier {
               type int32;
               description "Unique identifier for the tunnel";
             }
             leaf pair-policy-name {
               type string;
               description "Name of the pair policy";
             }
           }
           container policy-tunnel-inspection {
             leaf policy-tunnel-inspection-profile {
               type string;
               description "Policy tunnel inspection profile";
             }
           }
           container policy-firewall-authentication {
             leaf authentication-type {
               type string;
               description "Type of authentication";
             }
             leaf access-profile-name {
               type string;
               description "Name of the access profile";
             }
             leaf web-redirect {
               type string;
               description "Web-redirect flag for http";
             }
             leaf web-redirect-to-https {
               type string;
               description "Web-redirect-to-https flag";
             }
             leaf auth-only-browser {
               type string;
               description "Auth-only-browser flag";
             }
             leaf push-to-identity-management {
               type string;
               description "Push-to-identity-management flag";
             }
             leaf ssl-termination-profile {
               type string;
               description "Name of the ssl termination profile for HTTPS";
             }
             leaf domain {
               type string;
               description "Domain name";
             }
             leaf client-match-name {
               type string;
               description "Name to match, as given by client";
             }
             leaf auth-user-agent {
               type string;
               description "Responde to only HTTP request with given user agent";
             }
           }
           container policy-application-services {
             leaf gprs-gtp-profile {
               type string;
               description "Status of GPRS Tunneling Protocol Profile";
             }
             leaf gprs-sctp-profile {
               type string;
               description "Status of GPRS Stream Control Protocol profile";
             }
             leaf idp {
               type string;
             }
             leaf uac-policy {
               type string;
             }
             leaf utm {
               type string;
               description "Status of Unified Threat Management";
             }
             leaf advanced-anti-malware {
               type string;
               description "Advanced-anti-malware service";
             }
             leaf icap-redirect-profile {
               type string;
               description "ICAP Redirect service";
             }
             leaf security-intelligence {
               type string;
               description "Security intelligence service";
             }
             leaf wan-acceleration {
               type string;
             }
             leaf security-metadata-streaming-policy {
               type string;
               description "Security metadata streaming policy";
             }
             leaf anti-virus-policy {
               type string;
               description "Anti-virus policy";
             }
             leaf captive-portal {
               type string;
               description "Secure web gateway captive portal";
             }
             container application-firewall {
               container rule-set-info {
                 container rule-set {
                   leaf name {
                     type string;
                     description "Name information";
                   }
                   container rule-list {
                     list rule {
                       leaf name {
                         type string;
                         description "Name information";
                       }
                       leaf action {
                         type string;
                         description "Action specified for one rule";
                       }
                       container dynamic-application-list {
                         leaf-list dynamic-application {
                           type string;
                           description "Name of the dynamic application";
                         }
                       }
                       container dynamic-application-group-list {
                         leaf-list dynamic-application-group {
                           type string;
                           description "Name of the dynamic application group";
                         }
                       }
                     }
                     container default-rule {
                       leaf action {
                         type string;
                         description "Action specified for one rule";
                       }
                     }
                   }
                 }
               }
             }
             container application-acceleration {
               leaf application-acceleration-profile-name {
                 type string;
                 description "Application acceleration profile name";
               }
               leaf application-acceleration-service-options {
                 type string;
                 description "Application acceleration service options";
               }
             }
             container ssl-initiation {
               leaf ssl-initiation-profile-name {
                 type string;
                 description "SSL initiation profile name";
               }
             }
             container ssl-termination {
               leaf ssl-termination-profile-name {
                 type string;
                 description "SSL termination profile name";
               }
             }
             container ssl-proxy {
               leaf ssl-proxy-profile-name {
                 type string;
                 description "SSL proxy profile name";
               }
             }
             container web-proxy {
               leaf web-proxy-profile-name {
                 type string;
                 description "Web proxy profile name";
               }
             }
             container application-traffic-control {
               leaf rule-set-name {
                 type string;
                 description "Application traffic control rule-set name";
               }
             }
             container wx-optimizer {
               leaf wx-optimizer-profile-name {
                 type string;
                 description "Wan Optimizer Profile Name";
               }
               leaf wx-optimizer-service-options {
                 type string;
                 description "Wan Optimizer Service Options";
               }
             }
           }
           container policy-count-alarms {
             container alarm {
               leaf alarm-count {
                 type int32;
                 description "Number of the times alarm was raised";
               }
               leaf alarm-type {
                 type string;
                 description "Type of the alarm";
               }
             }
           }
           container policy-log {
             leaf log-session-creation {
               type empty;
               description "Log when a new session gets created for the policy";
             }
             leaf log-session-close {
               type empty;
               description "Log when a new session gets closed for the policy";
             }
           }
           container policy-feed {
             leaf policy-feed-type {
               type string;
               description "Add session element to security intellgence feed";
             }
           }
           container policy-scheduler {
             leaf attached-scheduler-name {
               type string;
               description "Information about the scheduler name";
             }
           }
           container policy-statistics-information {
             leaf pfe-identifier {
               type string;
               description "An identifier for a PFE";
             }
             leaf input-bytes {
               type int32;
               description "Number of incoming bytes";
             }
             leaf input-byte-rate {
               type int32;
               description "Number of incoming bytes per second";
             }
             leaf input-bytes-init {
               type int32;
               description "Number of incoming bytes in initial direction";
             }
             leaf input-byte-rate-init {
               type int32;
               description "Number of incoming bytes per second in initial direction";
             }
             leaf input-bytes-reply {
               type int32;
               description "Number of incoming bytes in reply direction";
             }
             leaf input-byte-rate-reply {
               type int32;
               description "Number of incoming bytes per second in reply direction";
             }
             leaf output-bytes {
               type int32;
               description "Number of outgoing bytes";
             }
             leaf output-byte-rate {
               type int32;
               description "Number of outgoing bytes per second";
             }
             leaf output-bytes-init {
               type int32;
               description "Number of outgoing bytes in initial direction";
             }
             leaf output-byte-rate-init {
               type int32;
               description "Number of outgoing bytes per second in initial direction";
             }
             leaf output-bytes-reply {
               type int32;
               description "Number of outgoing bytes in reply direction";
             }
             leaf output-byte-rate-reply {
               type int32;
               description "Number of outgoing bytes per second in reply direction";
             }
             leaf input-packets {
               type int32;
               description "Number of incoming packets";
             }
             leaf input-packet-rate {
               type int32;
               description "Number of incoming packets per second";
             }
             leaf input-packets-init {
               type int32;
               description "Number of incoming packets in initial direction";
             }
             leaf input-packet-rate-init {
               type int32;
               description "Number of incoming packets per second in initial direction";
             }
             leaf input-packets-reply {
               type int32;
               description "Number of incoming packets in reply direction";
             }
             leaf input-packet-rate-reply {
               type int32;
               description "Number of incoming packets per second in reply direction";
             }
             leaf output-packets {
               type int32;
               description "Number of outgoing packets";
             }
             leaf output-packet-rate {
               type int32;
               description "Number of outgoing packets per second";
             }
             leaf output-packets-init {
               type int32;
               description "Number of outgoing packets in initial direction";
             }
             leaf output-packet-rate-init {
               type int32;
               description "Number of outgoing packets per second in initial direction";
             }
             leaf output-packets-reply {
               type int32;
               description "Number of outgoing packets in reply direction";
             }
             leaf output-packet-rate-reply {
               type int32;
               description "Number of outgoing packets per second in reply direction";
             }
             leaf session-creations {
               type int32;
               description "Number of sessions created";
             }
             leaf session-creation-rate {
               type int32;
               description "Number of sessions created per second";
             }
             leaf active-sessions {
               type int32;
               description "Number of active sessions";
             }
             leaf session-deletions {
               type int32;
               description "Number of sessions deleted";
             }
             leaf policy-lookups {
               type int32;
               description "Number of policy lookups";
             }
           }
           container source-vrfs {
             container source-vrf {
               leaf source-vrf-name {
                 type string;
                 description "Name of the source vrf group";
               }
             }
           }
           container destination-vrfs {
             container destination-vrf {
               leaf destination-vrf-name {
                 type string;
                 description "Name of the destination vrf";
               }
             }
           }
         }
       }
     }
     list explicit-proxy-policy-zone-context {
       leaf-list logical-system-name {
         type string;
         description "Name of the logical system";
       }
       leaf tenant-name {
         type string;
         description "Tenant name";
       }
       list explicit-proxy-policy-zone-context-entry {
         leaf explicit-proxy-policy-zone-context-profile {
           type string;
           description "Profile of the context";
         }
         leaf explicit-proxy-policy-zone-context-policy-count {
           type uint32;
           description "Policy count of the context";
         }
       }
     }
     list explicit-proxy-policy-context-checksum-info {
       leaf-list logical-system-name {
         type string;
         description "Name of the logical system";
       }
       list explicit-proxy-policy-context-checksum-entry {
         leaf explicit-proxy-profile-name {
           type string;
           description "Name of the source zone";
         }
         leaf context-checksum {
           type string;
           description "Checksum for the policy context";
         }
       }
     }
   }
   grouping explicit-proxy-policy-hit-count-block {
     leaf-list logical-system-name {
       type string;
       description "Name of the logical system";
     }
     leaf tenant-name {
       type string;
       description "Tenant name";
     }
     leaf-list policy-hit-count-num {
       type uint32;
       description "Number of policy";
     }
     list explicit-proxy-policy-hit-count-entry {
       description "Information about policy hit-count";
       leaf ep_policy-hit-count-index {
         type uint32;
         description "Index";
       }
       leaf ep_policy-hit-count-profile-name {
         type string;
         description "Explicit proxy profile ";
       }
       leaf ep_policy-hit-count-policy-name {
         type string;
         description "Policy name";
       }
       leaf ep_policy-hit-count-count {
         type uint32;
         description "Policy hit-count ";
       }
       leaf ep_policy-hit-count-action {
         type string;
         description "Policy action ";
       }
       leaf ep_policy-redirect-count {
         type uint32;
         description "Policy redirected count ";
       }
     }
     container dynamic-application-count {
       description "Hit-count per dynamic-application";
       leaf-list dynamic-application {
         type string;
         description "Name of the dynamic application";
       }
       leaf-list dynamic-application-hit-count {
         type uint32;
         description "Dynamic-application hit-count";
       }
     }
     container url-category-count {
       description "Hit-count per Url-category";
       leaf-list url-category {
         type string;
         description "Name of url-category";
       }
       leaf-list url-category-hit-count {
         type uint32;
         description "Url-category hit-count";
       }
     }
   }
   grouping policy-hit-count-block {
     leaf-list logical-system-name {
       type string;
       description "Name of the logical system";
     }
     leaf tenant-name {
       type string;
       description "Tenant name";
     }
     leaf-list policy-hit-count-num {
       type uint32;
       description "Number of policy";
     }
     list policy-hit-count-entry {
       description "Information about policy hit-count";
       leaf policy-hit-count-index {
         type uint32;
         description "Index";
       }
       leaf policy-hit-count-from-zone {
         type string;
         description "From zone ";
       }
       leaf policy-hit-count-to-zone {
         type string;
         description "To zone ";
       }
       leaf policy-hit-count-policy-name {
         type string;
         description "Policy name";
       }
       leaf policy-hit-count-count {
         type uint32;
         description "Policy hit-count ";
       }
       leaf policy-hit-count-action {
         type string;
         description "Policy action ";
       }
       leaf policy-set-hit-count-index {
         type uint32;
         description "Index";
       }
       leaf policy-set-hit-count-from-zone {
         type string;
         description "From zone";
       }
       leaf policy-set-hit-count-policy-name {
         type string;
         description "Policy name";
       }
       leaf policy-set-hit-count-count {
         type uint32;
         description "Policy hit-count";
       }
       leaf policy-set-hit-count-action {
         type string;
         description "Policy action";
       }
       leaf policy-set-hit-count-to-zone {
         type string;
         description "To zone";
       }
       leaf policy-redirect-count {
         type uint32;
         description "Policy redirected count ";
       }
       leaf policy-set-redirect-count {
         type uint32;
         description "Policy redirected count";
       }
     }
     container dynamic-application-count {
       description "Hit-count per dynamic-application";
       leaf-list dynamic-application {
         type string;
         description "Name of the dynamic application";
       }
       leaf-list dynamic-application-hit-count {
         type uint32;
         description "Dynamic-application hit-count";
       }
     }
     container url-category-count {
       description "Hit-count per Url-category";
       leaf-list url-category {
         type string;
         description "Name of url-category";
       }
       leaf-list url-category-hit-count {
         type uint32;
         description "Url-category hit-count";
       }
     }
   }
   grouping security-policy-match-block {
     list policy-information {
       leaf policy-name {
         type string;
         description "Name of the policy";
       }
       leaf policy-state {
         type string;
         description "State of the policy";
       }
       leaf policy-identifier {
         type uint32;
         description "Unique identifier for the policy";
       }
       leaf policy-sequence-number {
         type int32;
         description "Sequence number for the policy in a given zone context";
       }
       leaf scope-policy-identifier {
         type uint32;
         description "Scope policy identifier for the policy";
       }
       leaf log-profile-id {
         type uint32;
         description "Unique id for the log profile";
       }
       leaf service-set-name {
         type string;
         description "Name of the service set";
       }
       leaf interface-name {
         type string;
         description "Name of the services interface";
       }
       leaf sfw-rule-name {
         type string;
         description "Name of the stateful-firewall-rule";
       }
       leaf sfw-rule-set-name {
         type string;
         description "Name of the stateful-firewall-rule-set";
       }
       leaf match-direction {
         type string;
         description "Match Direction of the policy";
       }
       leaf policy-description {
         type string;
         description "Description of the policy";
       }
       leaf explicit-proxy-policy-sequence-number {
         type int32;
         description "Sequence number for the policy in a given zone context";
       }
       leaf explicit-proxy-policy-description {
         type string;
         description "Description of the policy";
       }
       container policy-action {
         leaf action-type {
           type string;
         }
         leaf tunnel {
           type empty;
           description "Tunnel packets that match this policy";
         }
         leaf nat-source {
           type empty;
           description "Apply source NAT to packets that match this policy";
         }
         leaf nat-destination {
           type string;
           description "Apply destination NAT to packets that match this policy";
         }
         leaf firewall-authentication {
           type empty;
           description "Authenticate the client that sent the packets that match this        policy";
         }
         leaf services-offload {
           type empty;
           description "Services-offload options of the policy";
         }
         leaf no-services-offload {
           type empty;
           description "No-services-offload options of the policy";
         }
         leaf advanced-connection-tracking {
           type empty;
           description "Advanced-connection-tracking option of the policy";
         }
         leaf application-services {
           type empty;
           description "Application services";
         }
         leaf feed {
           type empty;
           description "Feed";
         }
         leaf uac-enabled {
           type empty;
           description "Enable unified access control enforcement of policy";
         }
         leaf log {
           type empty;
           description "Log the session of packets that match this policy";
         }
         leaf count {
           type empty;
           description "Count packets that match this policy";
         }
         leaf scheduled {
           type empty;
           description "Schedule the policy based on a scheduler";
         }
       }
       list context-information {
         leaf global-context {
           type empty;
           description "Global policy conext";
         }
         leaf source-zone-name {
           type string;
           description "Name of the source zone";
         }
         leaf destination-zone-name {
           type string;
           description "Name of the destination zone";
         }
       }
       container policy-type-information {
         leaf policy-type-string {
           type string;
           description "Type of policy";
         }
         leaf policy-type-dynamic-policy-count {
           type int32;
           description "Number of dynamic policies under this scope";
         }
       }
       container multiple-source-zones {
         container source-zone {
           leaf source-zone-name {
             type string;
             description "Name of the source zone";
           }
         }
       }
       container multiple-destination-zones {
         container destination-zone {
           leaf destination-zone-name {
             type string;
             description "Name of the destination zone";
           }
         }
       }
       container source-addresses {
         container source-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       container destination-addresses {
         container destination-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       container source-end-user-profile {
         leaf source-end-user-profile-name {
           type string;
           description "Name of the source-end-user-profile";
         }
       }
       container destination-identity-context-profile {
         leaf destination-identity-context-profile-name {
           type string;
           description "Name of the destination-identity-context-profile-name";
         }
       }
       list applications {
         list application {
           leaf application-name {
             type string;
             description "Name of the application";
           }
           list application-term {
             list source-port-range {
               leaf low {
                 type int32;
                 description "The lower limit in the range of ports";
               }
               leaf high {
                 type int32;
                 description "The higher limit in the range of the ports";
               }
             }
             list destination-port-range {
               leaf ports_array {
                 type string;
                 description "The ports array string";
               }
               leaf single {
                 type int32;
                 description "The single port";
               }
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
             container rpc-information {
               leaf rpc-uuid {
                 type string;
                 description "The rpc application uuid";
               }
               container program-number-range {
                 leaf low {
                   type int32;
                   description "The lower limit in the range of ports";
                 }
                 leaf high {
                   type int32;
                   description "The higher limit in the range of the ports";
                 }
               }
             }
             leaf protocol {
               type string;
               description "IP protocol";
             }
             leaf alg-name {
               type string;
               description "Name of the application layer gateway";
             }
             leaf inactivity-timeout {
               type int32;
               description "Idle timeout for any session that match this application";
             }
             leaf gate-timeout {
               type int32;
               description "Gate timeout for ALG child session to get established";
             }
             leaf child-inactivity-timeout {
               type int32;
               description "Idle timeout for ALG child session that is created after gate hit";
             }
           }
         }
       }
       container policy-dynamic-applications {
         list policy-dynamic-application-name {
           leaf dynamic-application-name {
             type string;
             description "Dynamic application name in the policy";
           }
           leaf dynamic-application-id {
             type uint32;
             description "Dynamic application identifier in the policy";
           }
         }
         list policy-dynamic-application {
           leaf dynamic-application-name {
             type string;
             description "Dynamic application name in the policy";
           }
           leaf dynamic-application-id {
             type uint32;
             description "Dynamic application identifier in the policy";
           }
         }
         list policy-dynamic-application-group {
           leaf dynamic-application-group-name {
             type string;
             description "Dynamic application group name in the policy";
           }
           leaf dynamic-application-group-id {
             type uint32;
             description "Dynamic application group identifier in the policy";
           }
         }
       }
       container policy-url-categories {
         list policy-url-category-name {
           leaf url-category-name {
             type string;
             description "Url category name in the policy";
           }
           leaf url-category-id {
             type uint32;
             description "Url category identifier in the policy";
           }
         }
         list policy-url-category {
           leaf url-category-name {
             type string;
             description "Url category name in the policy";
           }
           leaf url-category-id {
             type uint32;
             description "Url category identifier in the policy";
           }
         }
       }
       container source-identities {
         container source-identity {
           leaf role-name {
             type string;
             description "Name of the role";
           }
         }
       }
       container destination-identity-context {
         container destination-context {
           leaf role-name {
             type string;
             description "Name of the role";
           }
         }
       }
       container source-identities-feeds {
         container source-identity-feed {
           leaf feed-name {
             type string;
             description "Name of the feed";
           }
         }
       }
       container destination-identities-feeds {
         container destination-identity-feed {
           leaf feed-name {
             type string;
             description "Name of the feed";
           }
         }
       }
       container aamw-policy-info {
         leaf aamw-info {
           type string;
         }
       }
       container dynapp-redir-profile {
         leaf dynapp-redir-profile-name {
           type string;
           description "Name of the redirect profile";
         }
       }
       container unknown-source-identities {
         leaf role-name {
           type string;
           description "Name of the role";
         }
       }
       container unknown-destination-identities {
         leaf role-name {
           type string;
           description "Name of the role";
         }
       }
       container policy-tcp-options {
         leaf policy-tcp-options-syn-check {
           type string;
           description "Per policy SYN check required flag";
         }
         leaf policy-tcp-options-sequence-check {
           type string;
           description "Per policy Sequence check required flag";
         }
         leaf policy-tcp-options-window-scale {
           type string;
           description "Per policy window scale enabled flag";
         }
         leaf policy-tcp-options-initial-tcp-mss {
           type uint32;
           description "Initial direction TCP MSS for the policy";
         }
         leaf policy-tcp-options-reverse-tcp-mss {
           type uint32;
           description "Reverse direction TCP MSS for the policy";
         }
       }
       container policy-tunnel {
         leaf tunnel-name {
           type string;
           description "Name of the tunnel";
         }
         leaf tunnel-type {
           type string;
           description "Type of tunnel";
         }
         leaf tunnel-identifier {
           type int32;
           description "Unique identifier for the tunnel";
         }
         leaf pair-policy-name {
           type string;
           description "Name of the pair policy";
         }
       }
       container policy-tunnel-inspection {
         leaf policy-tunnel-inspection-profile {
           type string;
           description "Policy tunnel inspection profile";
         }
       }
       container policy-firewall-authentication {
         leaf authentication-type {
           type string;
           description "Type of authentication";
         }
         leaf access-profile-name {
           type string;
           description "Name of the access profile";
         }
         leaf web-redirect {
           type string;
           description "Web-redirect flag for http";
         }
         leaf web-redirect-to-https {
           type string;
           description "Web-redirect-to-https flag";
         }
         leaf auth-only-browser {
           type string;
           description "Auth-only-browser flag";
         }
         leaf push-to-identity-management {
           type string;
           description "Push-to-identity-management flag";
         }
         leaf ssl-termination-profile {
           type string;
           description "Name of the ssl termination profile for HTTPS";
         }
         leaf domain {
           type string;
           description "Domain name";
         }
         leaf client-match-name {
           type string;
           description "Name to match, as given by client";
         }
         leaf auth-user-agent {
           type string;
           description "Responde to only HTTP request with given user agent";
         }
       }
       container policy-application-services {
         leaf gprs-gtp-profile {
           type string;
           description "Status of GPRS Tunneling Protocol Profile";
         }
         leaf gprs-sctp-profile {
           type string;
           description "Status of GPRS Stream Control Protocol profile";
         }
         leaf idp {
           type string;
         }
         leaf uac-policy {
           type string;
         }
         leaf utm {
           type string;
           description "Status of Unified Threat Management";
         }
         leaf advanced-anti-malware {
           type string;
           description "Advanced-anti-malware service";
         }
         leaf icap-redirect-profile {
           type string;
           description "ICAP Redirect service";
         }
         leaf security-intelligence {
           type string;
           description "Security intelligence service";
         }
         leaf wan-acceleration {
           type string;
         }
         leaf security-metadata-streaming-policy {
           type string;
           description "Security metadata streaming policy";
         }
         leaf anti-virus-policy {
           type string;
           description "Anti-virus policy";
         }
         leaf captive-portal {
           type string;
           description "Secure web gateway captive portal";
         }
         container application-firewall {
           container rule-set-info {
             container rule-set {
               leaf name {
                 type string;
                 description "Name information";
               }
               container rule-list {
                 list rule {
                   leaf name {
                     type string;
                     description "Name information";
                   }
                   leaf action {
                     type string;
                     description "Action specified for one rule";
                   }
                   container dynamic-application-list {
                     leaf-list dynamic-application {
                       type string;
                       description "Name of the dynamic application";
                     }
                   }
                   container dynamic-application-group-list {
                     leaf-list dynamic-application-group {
                       type string;
                       description "Name of the dynamic application group";
                     }
                   }
                 }
                 container default-rule {
                   leaf action {
                     type string;
                     description "Action specified for one rule";
                   }
                 }
               }
             }
           }
         }
         container application-acceleration {
           leaf application-acceleration-profile-name {
             type string;
             description "Application acceleration profile name";
           }
           leaf application-acceleration-service-options {
             type string;
             description "Application acceleration service options";
           }
         }
         container ssl-initiation {
           leaf ssl-initiation-profile-name {
             type string;
             description "SSL initiation profile name";
           }
         }
         container ssl-termination {
           leaf ssl-termination-profile-name {
             type string;
             description "SSL termination profile name";
           }
         }
         container ssl-proxy {
           leaf ssl-proxy-profile-name {
             type string;
             description "SSL proxy profile name";
           }
         }
         container web-proxy {
           leaf web-proxy-profile-name {
             type string;
             description "Web proxy profile name";
           }
         }
         container application-traffic-control {
           leaf rule-set-name {
             type string;
             description "Application traffic control rule-set name";
           }
         }
         container wx-optimizer {
           leaf wx-optimizer-profile-name {
             type string;
             description "Wan Optimizer Profile Name";
           }
           leaf wx-optimizer-service-options {
             type string;
             description "Wan Optimizer Service Options";
           }
         }
       }
       container policy-count-alarms {
         container alarm {
           leaf alarm-count {
             type int32;
             description "Number of the times alarm was raised";
           }
           leaf alarm-type {
             type string;
             description "Type of the alarm";
           }
         }
       }
       container policy-log {
         leaf log-session-creation {
           type empty;
           description "Log when a new session gets created for the policy";
         }
         leaf log-session-close {
           type empty;
           description "Log when a new session gets closed for the policy";
         }
       }
       container policy-feed {
         leaf policy-feed-type {
           type string;
           description "Add session element to security intellgence feed";
         }
       }
       container policy-scheduler {
         leaf attached-scheduler-name {
           type string;
           description "Information about the scheduler name";
         }
       }
       container policy-statistics-information {
         leaf pfe-identifier {
           type string;
           description "An identifier for a PFE";
         }
         leaf input-bytes {
           type int32;
           description "Number of incoming bytes";
         }
         leaf input-byte-rate {
           type int32;
           description "Number of incoming bytes per second";
         }
         leaf input-bytes-init {
           type int32;
           description "Number of incoming bytes in initial direction";
         }
         leaf input-byte-rate-init {
           type int32;
           description "Number of incoming bytes per second in initial direction";
         }
         leaf input-bytes-reply {
           type int32;
           description "Number of incoming bytes in reply direction";
         }
         leaf input-byte-rate-reply {
           type int32;
           description "Number of incoming bytes per second in reply direction";
         }
         leaf output-bytes {
           type int32;
           description "Number of outgoing bytes";
         }
         leaf output-byte-rate {
           type int32;
           description "Number of outgoing bytes per second";
         }
         leaf output-bytes-init {
           type int32;
           description "Number of outgoing bytes in initial direction";
         }
         leaf output-byte-rate-init {
           type int32;
           description "Number of outgoing bytes per second in initial direction";
         }
         leaf output-bytes-reply {
           type int32;
           description "Number of outgoing bytes in reply direction";
         }
         leaf output-byte-rate-reply {
           type int32;
           description "Number of outgoing bytes per second in reply direction";
         }
         leaf input-packets {
           type int32;
           description "Number of incoming packets";
         }
         leaf input-packet-rate {
           type int32;
           description "Number of incoming packets per second";
         }
         leaf input-packets-init {
           type int32;
           description "Number of incoming packets in initial direction";
         }
         leaf input-packet-rate-init {
           type int32;
           description "Number of incoming packets per second in initial direction";
         }
         leaf input-packets-reply {
           type int32;
           description "Number of incoming packets in reply direction";
         }
         leaf input-packet-rate-reply {
           type int32;
           description "Number of incoming packets per second in reply direction";
         }
         leaf output-packets {
           type int32;
           description "Number of outgoing packets";
         }
         leaf output-packet-rate {
           type int32;
           description "Number of outgoing packets per second";
         }
         leaf output-packets-init {
           type int32;
           description "Number of outgoing packets in initial direction";
         }
         leaf output-packet-rate-init {
           type int32;
           description "Number of outgoing packets per second in initial direction";
         }
         leaf output-packets-reply {
           type int32;
           description "Number of outgoing packets in reply direction";
         }
         leaf output-packet-rate-reply {
           type int32;
           description "Number of outgoing packets per second in reply direction";
         }
         leaf session-creations {
           type int32;
           description "Number of sessions created";
         }
         leaf session-creation-rate {
           type int32;
           description "Number of sessions created per second";
         }
         leaf active-sessions {
           type int32;
           description "Number of active sessions";
         }
         leaf session-deletions {
           type int32;
           description "Number of sessions deleted";
         }
         leaf policy-lookups {
           type int32;
           description "Number of policy lookups";
         }
       }
       container source-vrfs {
         container source-vrf {
           leaf source-vrf-name {
             type string;
             description "Name of the source vrf group";
           }
         }
       }
       container destination-vrfs {
         container destination-vrf {
           leaf destination-vrf-name {
             type string;
             description "Name of the destination vrf";
           }
         }
       }
     }
   }
   grouping security-dns-cache-block {
     leaf dns-address-number {
       type uint32;
       description "DNS entry number";
     }
     leaf dns-prefetch-interval {
       type int32;
       description "DNS Prefetch interval for DNS Cache";
     }
     list dns-cache {
       description "DNS cache of a DNS name";
       leaf dns-name {
         type string;
         description "DNS name";
       }
       list dns-address {
         description "DNS address";
         leaf address-family {
           type string;
           description "IP address family";
         }
         leaf address-ttl {
           type int32;
           description "TTL value of this address";
         }
         leaf query-ttl {
           type int32;
           description "Query-interval of this address";
         }
         container address-table {
           description "DNS address table";
           leaf-list address-entry {
             type string;
             description "IP address entry";
           }
         }
       }
     }
   }
   grouping security-policy-shadow-block {
     list policy-shadow-policies {
       list policy-shadow-policy {
         leaf policy-shadow-policy-original-policy {
           type string;
           description "The policy which shadows others";
         }
         leaf policy-shadow-policy-shadowed-policy {
           type string;
           description "The policy which is shadowed";
         }
       }
     }
   }
   grouping security-policy-report-block {
     list policy-report-problem {
       leaf report-problem-str {
         type string;
         description "Report problem";
       }
       leaf-list report-problem-recommendation {
         type string;
         description "Report recommendation";
       }
     }
     list policy-report-policy-entry {
       leaf-list logical-system-name {
         type string;
         description "Name of the logical system";
       }
       leaf-list report-policy-name {
         type string;
         description "Name of the report policy";
       }
       leaf report-policy-identifier {
         type uint32;
         description "Name of the report policy id";
       }
       list context-information {
         leaf source-zone-name {
           type string;
           description "Name of the source zone";
         }
         leaf destination-zone-name {
           type string;
           description "Name of the destination zone";
         }
       }
       container source-addresses {
         container source-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       container destination-addresses {
         container destination-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       list applications {
         list application {
           leaf application-name {
             type string;
             description "Name of the application";
           }
           list application-term {
             list source-port-range {
               leaf low {
                 type int32;
                 description "The lower limit in the range of ports";
               }
               leaf high {
                 type int32;
                 description "The higher limit in the range of the ports";
               }
             }
             list destination-port-range {
               leaf ports_array {
                 type string;
                 description "The ports array string";
               }
               leaf single {
                 type int32;
                 description "The single port";
               }
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
             container rpc-information {
               leaf rpc-uuid {
                 type string;
                 description "The rpc application uuid";
               }
               container program-number-range {
                 leaf low {
                   type int32;
                   description "The lower limit in the range of ports";
                 }
                 leaf high {
                   type int32;
                   description "The higher limit in the range of the ports";
                 }
               }
             }
             leaf protocol {
               type string;
               description "IP protocol";
             }
             leaf alg-name {
               type string;
               description "Name of the application layer gateway";
             }
             leaf inactivity-timeout {
               type int32;
               description "Idle timeout for any session that match this application";
             }
             leaf gate-timeout {
               type int32;
               description "Gate timeout for ALG child session to get established";
             }
             leaf child-inactivity-timeout {
               type int32;
               description "Idle timeout for ALG child session that is created after gate hit";
             }
           }
         }
       }
       container policy-dynamic-applications {
         list policy-dynamic-application-name {
           leaf dynamic-application-name {
             type string;
             description "Dynamic application name in the policy";
           }
           leaf dynamic-application-id {
             type uint32;
             description "Dynamic application identifier in the policy";
           }
         }
         list policy-dynamic-application {
           leaf dynamic-application-name {
             type string;
             description "Dynamic application name in the policy";
           }
           leaf dynamic-application-id {
             type uint32;
             description "Dynamic application identifier in the policy";
           }
         }
         list policy-dynamic-application-group {
           leaf dynamic-application-group-name {
             type string;
             description "Dynamic application group name in the policy";
           }
           leaf dynamic-application-group-id {
             type uint32;
             description "Dynamic application group identifier in the policy";
           }
         }
       }
       container source-identities {
         container source-identity {
           leaf role-name {
             type string;
             description "Name of the role";
           }
         }
       }
       container destination-identity-context {
         container destination-context {
           leaf role-name {
             type string;
             description "Name of the role";
           }
         }
       }
       container source-identities-feeds {
         container source-identity-feed {
           leaf feed-name {
             type string;
             description "Name of the feed";
           }
         }
       }
       container destination-identities-feeds {
         container destination-identity-feed {
           leaf feed-name {
             type string;
             description "Name of the feed";
           }
         }
       }
       container policy-action {
         leaf action-type {
           type string;
         }
         leaf tunnel {
           type empty;
           description "Tunnel packets that match this policy";
         }
         leaf nat-source {
           type empty;
           description "Apply source NAT to packets that match this policy";
         }
         leaf nat-destination {
           type string;
           description "Apply destination NAT to packets that match this policy";
         }
         leaf firewall-authentication {
           type empty;
           description "Authenticate the client that sent the packets that match this        policy";
         }
         leaf services-offload {
           type empty;
           description "Services-offload options of the policy";
         }
         leaf no-services-offload {
           type empty;
           description "No-services-offload options of the policy";
         }
         leaf advanced-connection-tracking {
           type empty;
           description "Advanced-connection-tracking option of the policy";
         }
         leaf application-services {
           type empty;
           description "Application services";
         }
         leaf feed {
           type empty;
           description "Feed";
         }
         leaf uac-enabled {
           type empty;
           description "Enable unified access control enforcement of policy";
         }
         leaf log {
           type empty;
           description "Log the session of packets that match this policy";
         }
         leaf count {
           type empty;
           description "Count packets that match this policy";
         }
         leaf scheduled {
           type empty;
           description "Schedule the policy based on a scheduler";
         }
       }
     }
   }
   grouping security-explicit-proxy-policy-report-block {
     list policy-report-problem {
       leaf report-problem-str {
         type string;
         description "Report problem";
       }
       leaf-list report-problem-recommendation {
         type string;
         description "Report recommendation";
       }
     }
     list policy-report-policy-entry {
       leaf-list logical-system-name {
         type string;
         description "Name of the logical system";
       }
       leaf-list report-policy-name {
         type string;
         description "Name of the report policy";
       }
       leaf report-policy-identifier {
         type uint32;
         description "Name of the report policy id";
       }
       container source-addresses {
         container source-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       container destination-addresses {
         container destination-address {
           leaf address-name {
             type string;
             description "Name of the address";
           }
           leaf dynamic-address-id {
             type uint32;
             description "Dynamic address identifier in the policy";
           }
           container prefixes {
             leaf-list address-prefix {
               type jt:ipaddr;
               description "Address in IP prefix notation";
             }
           }
           list address-range {
             leaf address-low {
               type jt:ipaddr;
               description "The lower limit in the range addresses";
             }
             leaf address-high {
               type jt:ipaddr;
               description "The higher limit in the range addresses";
             }
           }
         }
       }
       list applications {
         list application {
           leaf application-name {
             type string;
             description "Name of the application";
           }
           list application-term {
             list source-port-range {
               leaf low {
                 type int32;
                 description "The lower limit in the range of ports";
               }
               leaf high {
                 type int32;
                 description "The higher limit in the range of the ports";
               }
             }
             list destination-port-range {
               leaf ports_array {
                 type string;
                 description "The ports array string";
               }
               leaf single {
                 type int32;
                 description "The single port";
               }
               leaf low {
                 type int32;
                 description "The lower limit in the range of ports";
               }
               leaf high {
                 type int32;
                 description "The higher limit in the range of the ports";
               }
             }
             container icmp-info {
               leaf icmp-type {
                 type string;
                 description "The icmp application type";
               }
               leaf icmp-code {
                 type string;
                 description "The icmp application code";
               }
             }
             container rpc-information {
               leaf rpc-uuid {
                 type string;
                 description "The rpc application uuid";
               }
               container program-number-range {
                 leaf low {
                   type int32;
                   description "The lower limit in the range of ports";
                 }
                 leaf high {
                   type int32;
                   description "The higher limit in the range of the ports";
                 }
               }
             }
             leaf protocol {
               type string;
               description "IP protocol";
             }
             leaf alg-name {
               type string;
               description "Name of the application layer gateway";
             }
             leaf inactivity-timeout {
               type int32;
               description "Idle timeout for any session that match this application";
             }
             leaf gate-timeout {
               type int32;
               description "Gate timeout for ALG child session to get established";
             }
             leaf child-inactivity-timeout {
               type int32;
               description "Idle timeout for ALG child session that is created after gate hit";
             }
           }
         }
       }
       container policy-dynamic-applications {
         list policy-dynamic-application-name {
           leaf dynamic-application-name {
             type string;
             description "Dynamic application name in the policy";
           }
           leaf dynamic-application-id {
             type uint32;
             description "Dynamic application identifier in the policy";
           }
         }
         list policy-dynamic-application {
           leaf dynamic-application-name {
             type string;
             description "Dynamic application name in the policy";
           }
           leaf dynamic-application-id {
             type uint32;
             description "Dynamic application identifier in the policy";
           }
         }
         list policy-dynamic-application-group {
           leaf dynamic-application-group-name {
             type string;
             description "Dynamic application group name in the policy";
           }
           leaf dynamic-application-group-id {
             type uint32;
             description "Dynamic application group identifier in the policy";
           }
         }
       }
       container source-identities {
         container source-identity {
           leaf role-name {
             type string;
             description "Name of the role";
           }
         }
       }
       container destination-identity-context {
         container destination-context {
           leaf role-name {
             type string;
             description "Name of the role";
           }
         }
       }
       container source-identities-feeds {
         container source-identity-feed {
           leaf feed-name {
             type string;
             description "Name of the feed";
           }
         }
       }
       container destination-identities-feeds {
         container destination-identity-feed {
           leaf feed-name {
             type string;
             description "Name of the feed";
           }
         }
       }
       container policy-action {
         leaf action-type {
           type string;
         }
         leaf tunnel {
           type empty;
           description "Tunnel packets that match this policy";
         }
         leaf nat-source {
           type empty;
           description "Apply source NAT to packets that match this policy";
         }
         leaf nat-destination {
           type string;
           description "Apply destination NAT to packets that match this policy";
         }
         leaf firewall-authentication {
           type empty;
           description "Authenticate the client that sent the packets that match this        policy";
         }
         leaf services-offload {
           type empty;
           description "Services-offload options of the policy";
         }
         leaf no-services-offload {
           type empty;
           description "No-services-offload options of the policy";
         }
         leaf advanced-connection-tracking {
           type empty;
           description "Advanced-connection-tracking option of the policy";
         }
         leaf application-services {
           type empty;
           description "Application services";
         }
         leaf feed {
           type empty;
           description "Feed";
         }
         leaf uac-enabled {
           type empty;
           description "Enable unified access control enforcement of policy";
         }
         leaf log {
           type empty;
           description "Log the session of packets that match this policy";
         }
         leaf count {
           type empty;
           description "Count packets that match this policy";
         }
         leaf scheduled {
           type empty;
           description "Schedule the policy based on a scheduler";
         }
       }
     }
   }
   grouping apbr-policies-block {
     leaf-list logical-system-name {
       type string;
       description "Name of the logical system";
     }
     leaf-list policy-internal-information {
       type string;
     }
     list security-context {
       list context-information {
         leaf source-zone-name {
           type string;
           description "Name of the source zone";
         }
       }
       container policies {
         list policy-information {
           leaf policy-name {
             type string;
             description "Name of the policy";
           }
           leaf policy-state {
             type string;
             description "State of the policy";
           }
           leaf policy-identifier {
             type uint32;
             description "Unique identifier for the policy";
           }
           leaf scope-policy-identifier {
             type uint32;
             description "Scope policy identifier for the policy";
           }
           leaf policy-sequence-number {
             type int32;
             description "Sequence number for the policy in a given zone context";
           }
           leaf policy-log {
             type string;
           }
           leaf policy-statistics-information {
             type string;
           }
           list context-information {
             leaf source-zone-name {
               type string;
               description "Name of the source zone";
             }
           }
           container source-addresses {
             container source-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           container destination-addresses {
             container destination-address {
               leaf address-name {
                 type string;
                 description "Name of the address";
               }
               leaf dynamic-address-id {
                 type uint32;
                 description "Dynamic address identifier in the policy";
               }
               container prefixes {
                 leaf-list address-prefix {
                   type jt:ipaddr;
                   description "Address in IP prefix notation";
                 }
               }
               list address-range {
                 leaf address-low {
                   type jt:ipaddr;
                   description "The lower limit in the range addresses";
                 }
                 leaf address-high {
                   type jt:ipaddr;
                   description "The higher limit in the range addresses";
                 }
               }
             }
           }
           list applications {
             list application {
               leaf application-name {
                 type string;
                 description "Name of the application";
               }
               list application-term {
                 list source-port-range {
                   leaf low {
                     type int32;
                     description "The lower limit in the range of ports";
                   }
                   leaf high {
                     type int32;
                     description "The higher limit in the range of the ports";
                   }
                 }
                 list destination-port-range {
                   leaf low {
                     type int32;
                     description "The lower limit in the range of ports";
                   }
                   leaf high {
                     type int32;
                     description "The higher limit in the range of the ports";
                   }
                 }
                 container icmp-info {
                   leaf icmp-type {
                     type string;
                     description "The icmp application type";
                   }
                   leaf icmp-code {
                     type string;
                     description "The icmp application code";
                   }
                 }
                 container rpc-information {
                   leaf rpc-uuid {
                     type string;
                     description "The rpc application uuid";
                   }
                   container program-number-range {
                     leaf low {
                       type int32;
                       description "The lower limit in the range of ports";
                     }
                     leaf high {
                       type int32;
                       description "The higher limit in the range of the ports";
                     }
                   }
                 }
                 leaf protocol {
                   type string;
                   description "IP protocol";
                 }
                 leaf alg-name {
                   type string;
                   description "Name of the application layer gateway";
                 }
                 leaf inactivity-timeout {
                   type int32;
                   description "Idle timeout for any session that match this application";
                 }
                 leaf gate-timeout {
                   type int32;
                   description "Gate timeout for ALG child session to get established";
                 }
                 leaf child-inactivity-timeout {
                   type int32;
                   description "Idle timeout for ALG child session that is created after gate hit";
                 }
               }
             }
           }
           container policy-scheduler {
             leaf attached-scheduler-name {
               type string;
               description "Information about the scheduler name";
             }
           }
           container application-services {
             leaf apbr-profile {
               type string;
               description "Profile attached to apbr_policy";
             }
           }
           container source-identities {
             container source-identity {
               leaf role-name {
                 type string;
                 description "Name of the role";
               }
             }
           }
           container unknown-source-identities {
             leaf role-name {
               type string;
               description "Name of the role";
             }
           }
         }
       }
     }
   }
   grouping sla-hit-count-block {
     leaf-list logical-system-name {
       type string;
       description "Name of the logical system";
     }
     leaf-list policy-hit-count-num {
       type uint32;
       description "Number of policy";
     }
     list policy-hit-count-entry {
       description "Information about policy hit-count";
       leaf policy-hit-count-index {
         type uint32;
         description "Index";
       }
       leaf policy-hit-count-from-zone {
         type string;
         description "From zone ";
       }
       leaf policy-hit-count-policy-name {
         type string;
         description "Policy name";
       }
       leaf policy-hit-count-count {
         type uint32;
         description "Policy hit-count ";
       }
     }
   }
   grouping apbr-statistics-block {
     leaf apbr-statistics-sessions-processed {
       type uint32;
     }
     leaf apbr-statistics-app-rule-hit-cache-hit {
       type uint32;
     }
     leaf apbr-statistics-app-rule-hit-first-packet-classification {
       type uint32;
     }
     leaf apbr-statistics-appid-sess-gate-hits {
       type uint32;
     }
     leaf apbr-statistics-midstream-disabled-rule-hit-on-cache-hit {
       type uint32;
     }
     leaf apbr-statistics-url-rule-hit-cache-hit {
       type uint32;
     }
     leaf apbr-statistics-dscp-rule-hit {
       type uint32;
     }
     leaf apbr-statistics-app-dscp-rule-hit {
       type uint32;
     }
     leaf apbr-statistics-app-rule-hit-midstream {
       type uint32;
     }
     leaf apbr-statistics-default-rule-match {
       type uint32;
     }
     leaf apbr-statistics-midstream-disabled-rule-hit-midstream {
       type uint32;
     }
     leaf apbr-statistics-url-rule-hit-midstream {
       type uint32;
     }
     leaf apbr-statistics-app-dscp-rule-hit-midstream {
       type uint32;
     }
     leaf apbr-statistics-dscp-rule-hit-midstream {
       type uint32;
     }
     leaf apbr-statistics-route-changed-cache-hits {
       type uint32;
     }
     leaf apbr-statistics-route-changed-first-packet-classification {
       type uint32;
     }
     leaf apbr-statistics-route-changed-on-sess-gate-hits {
       type uint32;
     }
     leaf apbr-statistics-route-changed-midstream {
       type uint32;
     }
     leaf apbr-statistics-default-rule-applied {
       type uint32;
     }
     leaf apbr-statistics-zone-mismatch {
       type uint32;
     }
     leaf apbr-statistics-drop-zone-mismatch {
       type uint32;
     }
     leaf apbr-statistics-next-hop-not-found {
       type uint32;
     }
     leaf apbr-statistics-application-services-bypass {
       type uint32;
     }
     leaf apbr-statistics-appid-requested {
       type uint32;
     }
   }
   grouping apbr-sla-status-block {
     leaf status {
       type string;
     }
   }
   grouping apbr-sla-version-block {
     leaf version {
       type string;
     }
   }
   grouping apbr-sla-statistics-block {
     leaf apbr-sla-statistics-passive-sessions-sampled {
       type uint32;
     }
     leaf apbr-sla-statistics-passive-ongoing-sessions {
       type uint32;
     }
     leaf apbr-sla-statistics-passive-sla-violations {
       type uint32;
     }
     leaf apbr-sla-statistics-active-probe-sessions {
       type uint32;
     }
     leaf apbr-sla-statistics-active-probe-sent {
       type uint32;
     }
     leaf apbr-sla-statistics-active-path-down {
       type uint32;
     }
   }
   grouping apbr-active-statistics-block {
     list apbr-active-statistics-info {
       leaf apbr-active-statistics-details-src-ip {
         type string;
       }
       leaf apbr-active-statistics-details-dest-ip {
         type string;
       }
       leaf apbr-active-statistics-details-pkt-loss {
         type uint32;
       }
       leaf apbr-active-statistics-details-rtt {
         type uint32;
       }
       leaf apbr-active-statistics-details-two-way {
         type uint32;
       }
       leaf apbr-active-statistics-details-ingress-jit {
         type uint32;
       }
       leaf apbr-active-statistics-details-egress-jit {
         type uint32;
       }
       leaf apbr-active-statistics-details-outgoing-ip {
         type string;
       }
     }
   }
   grouping apbr-prof-app-block {
     leaf apbr-prof-app-appname {
       type string;
     }
     leaf apbr-prof-app-appid {
       type uint32;
     }
     leaf apbr-prof-app-dscp {
       type uint32;
     }
     leaf apbr-prof-app-profname {
       type string;
     }
     leaf apbr-prof-app-rulename {
       type string;
     }
     leaf apbr-prof-app-appstate {
       type string;
     }
     leaf apbr-prof-app-idlestate {
       type uint32;
     }
     leaf apbr-prof-app-riname {
       type string;
     }
     leaf apbr-prof-app-slaname {
       type string;
     }
     leaf apbr-prof-app-prbname {
       type string;
     }
     leaf apbr-prof-app-ip {
       type string;
     }
     leaf apbr-prof-app-link-tag {
       type string;
     }
     leaf apbr-prof-app-link-priority {
       type uint32;
     }
     leaf apbr-prof-app-avg-pkt-loss {
       type uint32;
     }
     leaf apbr-prof-app-avg-rtt {
       type uint32;
     }
     leaf apbr-prof-app-avg-two-way {
       type uint32;
     }
     leaf apbr-prof-app-avg-ing-jit {
       type uint32;
     }
     leaf apbr-prof-app-avg-egr-jit {
       type uint32;
     }
     leaf apbr-prof-app-min-pkt-loss {
       type uint32;
     }
     leaf apbr-prof-app-min-rtt {
       type uint32;
     }
     leaf apbr-prof-app-min-two-way {
       type uint32;
     }
     leaf apbr-prof-app-min-ing-jit {
       type uint32;
     }
     leaf apbr-prof-app-min-egr-jit {
       type uint32;
     }
     leaf apbr-prof-app-max-pkt-loss {
       type uint32;
     }
     leaf apbr-prof-app-max-rtt {
       type uint32;
     }
     leaf apbr-prof-app-max-two-way {
       type uint32;
     }
     leaf apbr-prof-app-max-ing-jit {
       type uint32;
     }
     leaf apbr-prof-app-max-egr-jit {
       type uint32;
     }
     leaf apbr-prof-app-link-weight {
       type uint32;
     }
   }
   grouping multipath-rule-status-block {
     container common-information {
       description "Multipath rule common information";
       leaf logical-system {
         type string;
       }
       leaf name {
         type string;
       }
       leaf rule-type {
         type string;
       }
       leaf state {
         type string;
       }
       leaf cfg-num-paths {
         type uint32;
       }
       leaf cfg-app-grps {
         type string;
       }
       leaf cfg-apps {
         type string;
       }
     }
     container common-path-groups-information {
       description "Path groups information";
       leaf total-path-groups {
         type uint32;
       }
       list common-path-group-information {
         description "Path group information";
         leaf id {
           type uint32;
         }
         leaf state {
           type string;
         }
         leaf avail-num-paths {
           type uint32;
         }
       }
     }
     container sender-information {
       description "Sender information";
       container policy-statistics {
         description "Policy statistics";
         leaf cur-sessions {
           type uint32;
         }
         leaf ignored-sessions {
           type uint32;
         }
         leaf app-matched {
           type uint32;
         }
         leaf app-switched {
           type uint32;
         }
         leaf stopped-bw-limit {
           type uint32;
         }
         leaf packets-rule-inactive {
           type uint32;
         }
         leaf packets-rule-active {
           type uint32;
         }
         leaf less-paths {
           type uint32;
         }
         leaf packets-ignored {
           type uint32;
         }
         leaf packets-processed {
           type uint32;
         }
         leaf packets-copied {
           type uint32;
         }
         leaf sla-violated {
           type uint32;
         }
         leaf sla-met {
           type uint32;
         }
       }
       container sender-status {
         description "Sender status";
         leaf policy-ref-cnt {
           type uint32;
         }
         leaf credit-limit {
           type uint32;
         }
         leaf policer-rate {
           type uint32;
         }
         leaf is-bw-limit-reached {
           type string;
         }
         leaf max-wait-time {
           type uint32;
         }
         leaf time-to-reinforce {
           type uint32;
         }
         leaf app-hit-list {
           type string;
         }
       }
       container sender-path-groups-information {
         description "Sender path groups information";
         leaf total-sender-path-groups {
           type uint32;
         }
         list sender-path-group-information {
           description "Sender path group information";
           leaf id {
             type uint32;
           }
           leaf cur-num-paths {
             type uint32;
           }
           list sender-ctxt-path-information {
             description "Path information";
             leaf nh-ip {
               type string;
             }
             leaf nh-pkts-sent {
               type uint32;
             }
             leaf nh-link-type {
               type string;
             }
           }
           container sender-app-groups-information {
             description "Sender app groups information";
             leaf total-sender-apps {
               type uint32;
             }
             list sender-app-information {
               description "Sender application information";
               leaf name {
                 type string;
               }
               leaf id {
                 type uint32;
               }
               leaf pkts-sent {
                 type uint32;
               }
               list sender-path-information {
                 description "Path information";
                 leaf nh-ip {
                   type string;
                 }
                 leaf nh-pkts-sent {
                   type uint32;
                 }
                 leaf nh-link-type {
                   type string;
                 }
               }
             }
           }
           container sender-cosq-groups-information {
             description "Sender cosq groups information";
             leaf total-sender-cosqs {
               type uint32;
             }
             list sender-cosq-information {
               description "Sender cosq information";
               leaf id {
                 type uint32;
               }
               leaf pkts-sent {
                 type uint32;
               }
               list sender-path-information {
                 description "Path information";
                 leaf nh-ip {
                   type string;
                 }
                 leaf nh-pkts-sent {
                   type uint32;
                 }
                 leaf nh-link-type {
                   type string;
                 }
               }
             }
           }
         }
       }
     }
     container receiver-information {
       description "Receiver information";
       container receiver-path-groups-information {
         description "Receiver path groups information";
         leaf total-receiver-path-groups {
           type uint32;
         }
         list receiver-path-group-information {
           description "Receiver path group information";
           leaf id {
             type uint32;
           }
           leaf cur-num-paths {
             type uint32;
           }
           leaf pkts-rcvd {
             type uint32;
           }
           leaf avg-pkt-loss {
             type uint32;
           }
           leaf avg-ingress-jitter {
             type uint32;
           }
           leaf oos-pkts-dropped {
             type uint32;
           }
           list receiver-ctxt-path-information {
             description "Path information";
             leaf nh-ip {
               type string;
             }
             leaf nh-pkts-rcvd {
               type uint32;
             }
             leaf nh-packet-loss {
               type uint32;
             }
             leaf nh-ingress-jitter {
               type uint32;
             }
             leaf nh-reduction-packet-loss {
               type uint32;
             }
             leaf nh-reduction-ingress-jitter {
               type uint32;
             }
           }
           container receiver-app-groups-information {
             description "Receiver app groups information";
             leaf total-receiver-apps {
               type uint32;
             }
             list receiver-ctxt-information {
               description "Receiver context information";
               leaf id {
                 type uint32;
               }
               leaf name {
                 type string;
               }
               leaf pkts-rcvd {
                 type uint32;
               }
               leaf avg-pkt-loss {
                 type uint32;
               }
               leaf avg-ingress-jitter {
                 type uint32;
               }
               leaf oos-pkts-dropped {
                 type uint32;
               }
               list receiver-path-information {
                 description "Path information";
                 leaf nh-ip {
                   type string;
                 }
                 leaf nh-pkts-rcvd {
                   type uint32;
                 }
                 leaf nh-packet-loss {
                   type uint32;
                 }
                 leaf nh-ingress-jitter {
                   type uint32;
                 }
                 leaf nh-reduction-packet-loss {
                   type uint32;
                 }
                 leaf nh-reduction-ingress-jitter {
                   type uint32;
                 }
               }
             }
           }
           container receiver-cosq-groups-information {
             description "Receiver cosq groups information";
             leaf total-receiver-cosqs {
               type uint32;
             }
             list receiver-ctxt-information {
               description "Receiver context information";
               leaf id {
                 type uint32;
               }
               leaf name {
                 type string;
               }
               leaf pkts-rcvd {
                 type uint32;
               }
               leaf avg-pkt-loss {
                 type uint32;
               }
               leaf avg-ingress-jitter {
                 type uint32;
               }
               leaf oos-pkts-dropped {
                 type uint32;
               }
               list receiver-path-information {
                 description "Path information";
                 leaf nh-ip {
                   type string;
                 }
                 leaf nh-pkts-rcvd {
                   type uint32;
                 }
                 leaf nh-packet-loss {
                   type uint32;
                 }
                 leaf nh-ingress-jitter {
                   type uint32;
                 }
                 leaf nh-reduction-packet-loss {
                   type uint32;
                 }
                 leaf nh-reduction-ingress-jitter {
                   type uint32;
                 }
               }
             }
           }
         }
       }
     }
   }
   grouping multipath-policy-information-block {
     leaf policy-id {
       type uint32;
       description "Policy identifier";
     }
     leaf policy-state {
       type string;
       description "Policy state";
     }
     leaf ref-cnt {
       type uint32;
       description "Policy reference count";
     }
     leaf rule-id {
       type uint32;
       description "Rule identifier";
     }
     leaf application-name {
       type string;
       description "Application name";
     }
     leaf multipath-rule-name {
       type string;
       description "Multipath rule name";
     }
     container policy-statistics {
       description "Policy statistics";
       leaf cur-sessions {
         type uint32;
       }
       leaf ignored-sessions {
         type uint32;
       }
       leaf app-matched {
         type uint32;
       }
       leaf app-switched {
         type uint32;
       }
       leaf stopped-bw-limit {
         type uint32;
       }
       leaf packets-rule-inactive {
         type uint32;
       }
       leaf packets-rule-active {
         type uint32;
       }
       leaf less-paths {
         type uint32;
       }
       leaf packets-ignored {
         type uint32;
       }
       leaf packets-processed {
         type uint32;
       }
       leaf packets-copied {
         type uint32;
       }
       leaf sla-violated {
         type uint32;
       }
       leaf sla-met {
         type uint32;
       }
     }
   }
   grouping ragw-statistics-block {
     container ragw-location {
       leaf ragw-fpc {
         type uint32;
         description "FPC number";
       }
       leaf ragw-pic {
         type uint32;
         description "PIC number";
       }
       leaf ragw-pic-name {
         type string;
         description "PIC name";
       }
     }
     container ragw-statistics-info {
       leaf ragw-statistics-policy-match {
         type uint32;
       }
       leaf ragw-statistics-sess-tcp {
         type uint32;
       }
       leaf ragw-statistics-sess-ssl {
         type uint32;
       }
     }
   }
   grouping resmgr-group-active-block {
     leaf resmgr-group-active-fpc-number {
       type uint32;
       description "FPC number";
     }
     leaf resmgr-group-active-pic-number {
       type uint32;
       description "PIC number";
     }
     leaf resmgr-group-active-total {
       type uint32;
       description "Total groups";
     }
     leaf resmgr-group-active-count {
       type uint32;
       description "Active groups";
     }
     list resmgr-group-active-data {
       leaf resmgr-group-active-data-grp-id {
         type uint32;
         description "Resource Manager Group ID";
       }
       leaf resmgr-group-active-data-client {
         type string;
         description "Application using the Resource Manager Group";
       }
     }
   }
   grouping resmgr-resource-active-block {
     leaf resmgr-resource-active-fpc-number {
       type uint32;
       description "FPC number";
     }
     leaf resmgr-resource-active-pic-number {
       type uint32;
       description "PIC number";
     }
     leaf resmgr-resource-active-total {
       type uint32;
       description "Total resource";
     }
     leaf resmgr-resource-active-count {
       type uint32;
       description "Active resource";
     }
     list resmgr-resource-active-data {
       leaf resmgr-resource-active-data-res-id {
         type uint32;
         description "Resource ID";
       }
       leaf resmgr-resource-active-data-grp-id {
         type uint32;
         description "Parent group ID of the resource";
       }
       leaf resmgr-resource-active-data-client {
         type string;
         description "Application using the resource";
       }
     }
   }
   grouping resmgr-settings-block {
     leaf resmgr-settings-fpc-number {
       type uint32;
       description "FPC number";
     }
     leaf resmgr-settings-pic-number {
       type uint32;
       description "PIC number";
     }
     leaf resmgr-settings-timeout {
       type uint32;
       description "Client heartbeat timeout";
     }
     leaf resmgr-settings-count {
       type uint32;
       description "Client heartbeat count";
     }
     leaf resmgr-settings-pinhole-age {
       type uint32;
       description "Pinhole age";
     }
   }
   grouping resource-manager-summary-information-block {
     leaf resmgr-summary-fpc-number {
       type uint32;
       description "FPC number";
     }
     leaf resmgr-summary-pic-number {
       type uint32;
       description "PIC number";
     }
     leaf active-client-count {
       type uint32;
       description "Number of active resource-manager clients";
     }
     leaf active-group-count {
       type uint32;
       description "Number of active resource-manager groups";
     }
     leaf active-resource-count {
       type uint32;
       description "Number of active resource-manager resources";
     }
     leaf active-session-count {
       type uint32;
       description "Number of active resource-manager sessions";
     }
   }
   grouping performance-summary-information-block {
     list performance-summary-statistics {
       leaf fpc-number {
         type uint32;
         description "FPC number";
       }
       leaf pic-number {
         type uint32;
         description "PIC number";
       }
       leaf spu-cpu-utilization {
         type uint32;
         description "SPU CPU utilization in percentage";
       }
       leaf spu-memory-utilization {
         type uint32;
         description "SPU memory utilization in percentage";
       }
       leaf spu-current-flow-session {
         type uint32;
         description "SPU current flow session";
       }
       leaf spu-max-flow-session {
         type uint32;
         description "SPU max flow session";
       }
       leaf spu-current-cp-session {
         type uint32;
         description "SPU current cp session";
       }
       leaf spu-max-cp-session {
         type uint32;
         description "SPU max cp session";
       }
       container fpc {
         description "FPC";
       }
     }
   }
   grouping spu-monitroing-re-ipc-debug-block {
     leaf-list entry {
       type string;
     }
   }
   grouping performance-spu-information-block {
     list performance-spu-statistics {
       leaf fpc-number {
         type uint32;
         description "FPC number";
       }
       leaf pic-number {
         type uint32;
         description "PIC number";
       }
       list performance-spu-info {
         leaf-list performance-spu-info-sec-col1 {
           type uint32;
           description "SPU CPU average usage #sec ago";
         }
         leaf-list performance-spu-info-usage-col1 {
           type uint32;
           description "SPU CPU average usage";
         }
         leaf-list performance-spu-info-sec-col2 {
           type uint32;
           description "SPU CPU average usage #sec ago";
         }
         leaf-list performance-spu-info-usage-col2 {
           type uint32;
           description "SPU CPU average usage";
         }
         leaf-list performance-spu-info-sec-col3 {
           type uint32;
           description "SPU CPU average usage #sec ago";
         }
         leaf-list performance-spu-info-usage-col3 {
           type uint32;
           description "SPU CPU average usage";
         }
         leaf-list performance-spu-info-sec-col4 {
           type uint32;
           description "SPU CPU average usage #sec ago";
         }
         leaf-list performance-spu-info-usage-col4 {
           type uint32;
           description "SPU CPU average usage";
         }
         leaf-list performance-spu-info-sec-col5 {
           type uint32;
           description "SPU CPU average usage #sec ago";
         }
         leaf-list performance-spu-info-usage-col5 {
           type uint32;
           description "SPU CPU average usage";
         }
         leaf-list performance-spu-info-sec-col6 {
           type uint32;
           description "SPU CPU average usage #sec ago";
         }
         leaf-list performance-spu-info-usage-col6 {
           type uint32;
           description "SPU CPU average usage";
         }
       }
     }
   }
   grouping performance-spu-extensive-information-block {
     list performance-spu-extensive-statistics {
       leaf fpc-number {
         type uint32;
         description "FPC number";
       }
       leaf pic-number {
         type uint32;
         description "PIC number";
       }
       container fpc {
         description "FPC";
       }
       list performance-spu-statistics-cpu {
         leaf cpu-number {
           type uint32;
           description "CPU number";
         }
         leaf spu-cpu-utilization {
           type uint32;
           description "SPU CPU utilization in percentage";
         }
         leaf spu-cpu-weighted-utilization {
           type uint32;
           description "SPU CPU weighted utilization in percentage";
         }
         leaf spu-cpu-status {
           type string;
           description "SPU CPU status";
         }
         leaf spu-cpu-schedcounter {
           type uint32;
           description "SPU CPU scheduler counter";
         }
       }
     }
   }
   grouping performance-spu-summary-information-block {
     list performance-spu-summary-statistics {
       leaf fpc-number {
         type uint32;
         description "FPC number";
       }
       leaf pic-number {
         type uint32;
         description "PIC number";
       }
       list performance-spu-summary-cpu {
         leaf cpu-number {
           type uint32;
           description "CPU number";
         }
         leaf last-min-usage {
           type uint32;
           description "SPU thread last minute average CPU usage";
         }
         leaf last-hour-usage {
           type uint32;
           description "SPU thread last hour average CPU usage";
         }
         leaf last-day-usage {
           type uint32;
           description "SPU thread last day average CPU usage";
         }
       }
     }
   }
   grouping performance-session-information-block {
     list performance-session-statistics {
       leaf fpc-number {
         type uint32;
         description "FPC number";
       }
       leaf pic-number {
         type uint32;
         description "PIC number";
       }
       leaf performance-info {
         type string;
         description "Performance info";
       }
     }
   }
   grouping user-identification-block {
     container local-authentication-table {
       leaf total-count {
         type uint32;
         description "Total count of local authentication table records";
       }
       list local-authentication-info {
         leaf ip-address {
           type jt:ipaddr;
           description "Name of the ip-address";
         }
         leaf user-name {
           type string;
           description "Name of the user";
         }
         container role-name-list {
           leaf-list role-name {
             type string;
             description "Name of the role";
           }
         }
       }
     }
   }
   grouping zones-information-block {
     container zones-functional {
       container zones-management {
         leaf zones-management-zonename {
           type string;
           description "Management zone name";
         }
         leaf zones-management-description {
           type string;
           description "Text description of management zone";
         }
         leaf zones-management-policy-configurable {
           type string;
           description "Policy configurable option";
         }
         leaf zones-management-screen {
           type string;
           description "Name of ids option object applied to the zone";
         }
         leaf zones-management-interfaces-bound {
           type string;
           description "Number of interfaces bound to the zone";
         }
         container zones-management-interfaces {
           leaf-list zones-management-interface-name {
             type string;
             description "Name of an interface bound to the zone";
           }
         }
       }
     }
     list zones-security {
       leaf zones-security-zonename {
         type string;
         description "Security zone name";
       }
       leaf zones-security-scope {
         type string;
         description "Security zone scope of shared, or imported, or local";
       }
       leaf zone-id {
         type int32;
         description "Zone ID";
       }
       leaf zones-security-description {
         type string;
         description "Text description of zone";
       }
       leaf zones-security-send-reset {
         type string;
         description "Send-reset option";
       }
       leaf zones-security-policy-configurable {
         type string;
         description "Policy configurable option";
       }
       leaf zones-security-screen {
         type string;
         description "Name of ids option object applied to the zone";
       }
       leaf zones-security-whitelist-count {
         type string;
         description "Screen whitelist count bound to the zone";
       }
       leaf zones-security-interfaces-bound {
         type string;
         description "Number of interfaces bound to the zone";
       }
       leaf zones-security-advanced-connection-tracking-timeout {
         type uint32;
         description "Advanced-connection-tracking entries' timeout value in seconds";
       }
       leaf zones-security-advanced-connection-tracking-action-name {
         type string;
         description "Name of advanced-connection-tracking action";
       }
       leaf zones-security-advanced-connection-tracking-to-zone {
         type string;
         description "Mandate all policies with to-zone set to this zone to do advanced-connection-tracking lookup";
       }
       leaf zones-security-unidirectional-session-refreshing {
         type string;
         description "Unidirectional session refreshing option";
       }
       container zones-security-whitelist {
         leaf-list zones-security-whitelist-name {
           type string;
           description "Name of the screen whitelist bound to the zone";
         }
       }
       container zones-security-interfaces {
         leaf-list zones-security-interface-name {
           type string;
           description "Name of an interface bound to the zone";
         }
       }
     }
     list zones-logical-system {
       leaf name {
         type string;
         description "Logical system name";
       }
     }
     list zones-tenant {
       leaf zone-name {
         type string;
         description "Tenant name";
       }
     }
   }
   grouping vrf-group-information-block {
     container vrf-group {
       leaf vrf-group-groupname {
         type string;
         description "Vrf-group name";
       }
       leaf vrf-group-vrfnum {
         type string;
         description "Number of vrfs bound to the vrf-group";
       }
       container vrf-group-vrf {
         leaf-list vrf-group-vrfname {
           type string;
           description "Name of an vrf bound to the vrf-group";
         }
       }
     }
     list vrf-group-logical-system {
       leaf name {
         type string;
         description "Logical system name";
       }
     }
   }
   grouping tunnel-inspection-profile-information-block {
     leaf-list logical-system-name {
       type string;
       description "Name of the logical system";
     }
     leaf tenant-name {
       type string;
       description "Tenant name";
     }
     leaf-list tunnel-inspection-profile-num {
       type uint32;
       description "Number of profiles";
     }
     container tunnel-inspection-profile-entry {
       leaf-list profile-name {
         type string;
         description "Name of the tunnel-inspection profile";
       }
       leaf-list profile-type {
         type string;
         description "Type of the tunnel-inspection profile";
       }
       leaf-list profile-rule-num {
         type uint32;
         description "Number of rules";
       }
       leaf-list profile-rule-num-geneve {
         type uint32;
         description "Number of rules";
       }
       list tunnel-inspection-profile-rule {
         leaf vxlan-name {
           type string;
           description "Name of the vxlan";
         }
         leaf geneve-name {
           type string;
           description "Geneve profile name";
         }
         leaf-list vxlan-vni-obj-num {
           type uint32;
           description "Number of Vxlan";
         }
         leaf geneve-profile-obj-num {
           type uint32;
           description "Number of GENEVE profile";
         }
         leaf-list policy-set-name {
           type string;
           description "Name of the policy set";
         }
         leaf-list inspection-level {
           type string;
           description "Inspection level";
         }
         container vxlan-vni-list {
           leaf-list vni-name {
             type string;
             description "Name of VNI";
           }
         }
         list geneve-profile-list {
           leaf geneve-profile-name {
             type string;
             description "Name of GENEVE profile";
           }
         }
       }
     }
   }
   grouping tunnel-inspection-geneve-profile-information-block {
     leaf-list logical-system-name {
       type string;
       description "Name of the logical system";
     }
     leaf tenant-name {
       type string;
       description "Tenant name";
     }
     leaf geneve-obj-num {
       type uint32;
       description "Number of GENEVE profiles";
     }
     list tunnel-inspection-geneve-profiles {
       leaf geneve-profile-name {
         type string;
         description "Name of GENEVE profile";
       }
       leaf geneve-profile-option-class {
         type string;
         description "The type of GENEVE option class";
       }
       leaf geneve-profile-attribute-type {
         type string;
         description "The type of attribute for a GENEVE option class";
       }
       leaf geneve-profile-nums {
         type uint32;
         description "Number of attributes count";
       }
       list geneve-attribute-id {
         description "List of attributes";
         container geneve-attribute-id-list {
           description "List of all attributes";
           leaf geneve-attribute-id-mid {
             type uint64;
             description "Attribute ID";
           }
         }
       }
     }
   }
   grouping remote-access-default-config-block {
     leaf remote-access-default-config-client-name {
       type string;
     }
     leaf remote-access-default-config-connection-mode {
       type string;
     }
     leaf remote-access-default-config-biometric-auth {
       type string;
     }
     leaf remote-access-default-config-dpd-interval {
       type uint32;
     }
     leaf remote-access-default-config-dpd-threshold {
       type uint32;
     }
     leaf remote-access-default-config-tcp-encap {
       type string;
     }
     leaf remote-access-default-config-path-finder-sni {
       type string;
     }
   }
   grouping gtp-show-counters-block {
     container path-rate-limit {
       leaf gtp-message-type {
         type string;
         description "GTP message type for path rate limit";
       }
       leaf prlimit-drop {
         type uint32;
         description "Message number after reaching drop-threshold";
       }
       leaf prlimit-alarm {
         type uint32;
         description "Message number after reaching alarm-threshold";
       }
     }
     container rate-limit {
       description "Number of packets rate limit error";
       leaf arl-drop {
         type uint32;
         description "Message number after reaching drop-threshold";
       }
       leaf arl-alarm {
         type uint32;
         description "Message number after reaching alarm-threshold";
       }
     }
     container mask-uli-ie {
       leaf total-uli-ie-mask {
         type uint32;
         description "Total GTP ULI IE Packets Masked";
       }
       leaf lac-mask {
         type uint32;
         description "Total GTP LAC ULI IE Packets Masked";
       }
       leaf sac-mask {
         type uint32;
         description "Total GTP SAC ULI IE Packets Masked";
       }
       leaf rac-mask {
         type uint32;
         description "Total GTP RAC ULI IE Packets Masked";
       }
       leaf tac-mask {
         type uint32;
         description "Total GTP TAC ULI IE Packets Masked";
       }
       leaf ci-mask {
         type uint32;
         description "Total GTP CI ULI IE Packets Masked";
       }
       leaf eci-mask {
         type uint32;
         description "Total GTP ECI ULI IE Packets Masked";
       }
     }
     container packet {
       leaf packet-proc-action {
         type string;
         description "Packet process action";
       }
       leaf packet-cntr-total {
         type uint32;
         description "Packet counter number in total";
       }
       leaf packet-cntr-gtpv0 {
         type uint32;
         description "Packet counter number for GTPv0";
       }
       leaf packet-cntr-gtpv1 {
         type uint32;
         description "Packet counter number for GTPv1";
       }
       leaf packet-cntr-gtpv2 {
         type uint32;
         description "Packet counter number for GTPv2";
       }
       leaf packet-cntr-gtp-prime {
         type uint32;
         description "Packet counter number fot GTP'";
       }
     }
     container ha {
       leaf total-recv {
         type uint32;
         description "GTP HA message received";
       }
       leaf total-recv-ok {
         type uint32;
         description "GTP HA message received success";
       }
       leaf total-recv-bad-msg {
         type uint32;
         description "GTP HA bad message received";
       }
       leaf total-recv-unknown-type {
         type uint32;
         description "GTP HA unknown message received";
       }
       leaf total-recv-unknown-version {
         type uint32;
         description "GTP HA unknown version message received";
       }
       leaf total-send {
         type uint32;
         description "GTP HA message send";
       }
       leaf total-send-ok {
         type uint32;
         description "GTP HA message send success";
       }
       leaf total-send-fail {
         type uint32;
         description "GTP HA message send failed";
       }
       leaf total-alloc-memory-fail {
         type uint32;
         description "GTP HA allocate memory failed";
       }
       leaf total-under-reset {
         type uint32;
         description "GTP HA message received during tunnel reset";
       }
     }
     container request {
       leaf allocate-request {
         type uint32;
         description "Allocate request";
       }
       leaf free-request {
         type uint32;
         description "Free request";
       }
       leaf allocate-request-fail {
         type uint32;
         description "Allocate request failed";
       }
       leaf request-hit-error {
         type uint32;
         description "Remote request hit by local SPU";
       }
       leaf pending-timeout {
         type uint32;
         description "Pending for JMPI message acknowledgment";
       }
     }
     container data-packet {
       leaf gtpu_v1_pkt_rcv {
         type uint32;
         description "GTPv1 data pkt received";
       }
       leaf gtpu_v1_pkt_pass {
         type uint32;
         description "GTPv1 data pkt passed";
       }
       leaf gtpu_v1_pkt_drop {
         type uint32;
         description "GTPv1 data pkt dropped";
       }
       leaf gtpu_v1_pkt_no_tnl_drop {
         type uint32;
         description "GTPv1 data pkt no-tunnel dropped";
       }
       leaf gtpu_v1_pkt_seq_check_drop {
         type uint32;
         description "GTPv1 data pkt sequence error dropped";
       }
       leaf gtpu_v1_pkt_end_user_check_drop {
         type uint32;
         description "GTPv1 data pkt end-user dropped";
       }
       leaf gtpu_v1_pkt_other_check_drop {
         type uint32;
         description "GTPv1 data pkt other dropped";
       }
       leaf gtpu_v0_pkt_rcv {
         type uint32;
         description "GTPv0 data pkt received";
       }
       leaf gtpu_v0_pkt_pass {
         type uint32;
         description "GTPv0 data pkt passed";
       }
       leaf gtpu_v0_pkt_drop {
         type uint32;
         description "GTPv0 data pkt dropped";
       }
       leaf gtpu_v0_pkt_no_tnl_drop {
         type uint32;
         description "GTPv0 data pkt no-tunnel dropped";
       }
       leaf gtpu_v0_pkt_seq_check_drop {
         type uint32;
         description "GTPv0 data pkt sequence error dropped";
       }
       leaf gtpu_v0_pkt_end_user_check_drop {
         type uint32;
         description "GTPv0 data pkt end-user dropped";
       }
       leaf gtpu_v0_pkt_other_check_drop {
         type uint32;
         description "GTPv0 data pkt other dropped";
       }
     }
     container error {
       leaf total {
         type string;
         description "Total error";
       }
       leaf exception {
         type string;
         description "Exception error";
       }
       leaf gtp-header {
         type string;
         description "GTP header error";
       }
       leaf length {
         type string;
         description "Inconsistent message length error";
       }
       leaf imsi {
         type string;
         description "IMSI IE error";
       }
       leaf charge-id {
         type string;
         description "Charge ID error";
       }
       leaf sequence {
         type string;
         description "Sequence number error";
       }
       leaf apn {
         type string;
         description "APN filter error";
       }
       leaf transport {
         type string;
         description "Transport port error";
       }
       leaf gtp-in-gtp {
         type string;
         description "GTP-in-GTP error";
       }
       leaf length-short {
         type string;
         description "Message too short error";
       }
       leaf length-long {
         type string;
         description "Message too long error";
       }
       leaf gsn-not-exist {
         type string;
         description "GSN not exist error";
       }
       leaf rate-limit {
         type string;
         description "Number of packets rate limit error";
       }
       leaf response-not-match {
         type string;
         description "Response not match error";
       }
       leaf response-retransmit {
         type string;
         description "Response retransmit error";
       }
       leaf missing-ie {
         type string;
         description "Missing IE error";
       }
       leaf unexpect-ie {
         type string;
         description "Unexpected IE error";
       }
       leaf ie-type {
         type string;
         description "GTP IE type error";
       }
       leaf ie-order {
         type string;
         description "IE order error";
       }
       leaf ie-length {
         type string;
         description "IE length error";
       }
       leaf duplicate-ie {
         type string;
         description "Duplicate IE error";
       }
       leaf non-digit {
         type string;
         description "TID non-digit error";
       }
       leaf tid-not-0 {
         type string;
         description "TID not 0 error";
       }
       leaf tid-0 {
         type string;
         description "TID is 0 error";
       }
       leaf tid-control {
         type string;
         description "Control TID/TEID error";
       }
       leaf tid-data {
         type string;
         description "Data TID/TEID error";
       }
       leaf control-ip {
         type string;
         description "Control IP address error";
       }
       leaf data-ip {
         type string;
         description "Data IP address error";
       }
       leaf end-user-ip {
         type string;
         description "End user IP address error";
       }
       leaf ggsn-ip {
         type string;
         description "GGSN IP error";
       }
       leaf message-v0 {
         type string;
         description "GTPv0 message error";
       }
       leaf message-v1 {
         type string;
         description "GTPv1 message error";
       }
       leaf message-v2 {
         type string;
         description "GTPv2 message error";
       }
       leaf message-type {
         type string;
         description "GTP message type error";
       }
       leaf no-tunnel-0 {
         type string;
         description "Tunnel0 not found error";
       }
       leaf no-control-tunnel {
         type string;
         description "Control tunnel not found error";
       }
       leaf no-user-tunnel {
         type string;
         description "User tunnel not found error";
       }
       leaf invalid-tunnel-0 {
         type string;
         description "Invalid tunnel0 error";
       }
       leaf invalid-control-tunnel {
         type string;
         description "Invalid control tunnel error";
       }
       leaf invalid-user-tunnel {
         type string;
         description "Invalid user tunnel error";
       }
       leaf create-tunnel-0 {
         type string;
         description "Create tunnel0 error";
       }
       leaf create-control-tunnel {
         type string;
         description "Create control tunnel error";
       }
       leaf create-user-tunnel {
         type string;
         description "Create user tunnel error";
       }
       leaf no-request {
         type string;
         description "Request not found error";
       }
       leaf new-request {
         type string;
         description "Out of request error";
       }
       leaf no-action {
         type string;
         description "Action not found error";
       }
       leaf new-action {
         type string;
         description "Out of action error";
       }
       leaf not-unique-tid {
         type string;
         description "TID/TEID not unique error";
       }
       leaf missing-tid {
         type string;
         description "TID/TEID missing error";
       }
       leaf ebi-not-0 {
         type string;
         description "EBI not 0 error";
       }
       leaf ebi-not-exist {
         type string;
         description "EBI not exist error";
       }
       leaf bearer-ie {
         type string;
         description "Bearer IE error";
       }
       leaf dup-jbuf {
         type uint32;
         description "Duplicate new jbuf error";
       }
       leaf new-jmpi-cookie {
         type uint32;
         description "Out of jmpi cookie error";
       }
       leaf send-jmpi-msg {
         type uint32;
         description "Send jmpi message error";
       }
       leaf jmpi-target-failed {
         type uint32;
         description "JMPI target error";
       }
       leaf new-rt-cookie {
         type uint32;
         description "Out of callback cookie error";
       }
       leaf reinject {
         type uint32;
         description "Reinject packet error";
       }
       leaf wrong-spu {
         type uint32;
         description "Distribute to wrong spu error";
       }
       leaf under-reset {
         type uint32;
         description "System under reset error";
       }
       leaf src-ip {
         type uint32;
         description "Source IP error";
       }
       leaf dst-ip {
         type uint32;
         description "Destination IP error";
       }
       leaf v2-invalid-ebi {
         type uint32;
         description "Invalid EBI value";
       }
       leaf all-up {
         type uint32;
         description "SPU all up for GTP plugin";
       }
       leaf interface {
         type uint32;
         description "Not support interface";
       }
       leaf new_path {
         type uint32;
         description "Out of path";
       }
       leaf path_over_rate {
         type uint32;
         description "Over path rate limit";
       }
       leaf new_utnl_key {
         type uint32;
         description "New utnl key";
       }
       leaf no_utnl_key {
         type uint32;
         description "No utnl key";
       }
       leaf end_user {
         type uint32;
         description "End user";
       }
       leaf new_sync_action {
         type uint32;
         description "New sync action";
       }
       leaf nsapi {
         type uint32;
         description "NSAPI";
       }
       leaf conflict_sync_action {
         type uint32;
         description "New conflict sync action";
       }
       leaf pri_uid_not_exist {
         type uint32;
         description "Primary u-tunnel id not exist";
       }
       leaf too_many_same_type_ie {
         type uint32;
         description "Too many same type ie";
       }
       leaf v2_lbi {
         type uint32;
         description "Invalid v2 lbi";
       }
       leaf rm_conflict_utnl {
         type uint32;
         description "Remove conflict utnl";
       }
       leaf conflict_pri_utnl {
         type uint32;
         description "Conflict primary u-tunnel";
       }
       leaf ctnl_recovery {
         type uint32;
         description "Ctnl recovery error";
       }
       leaf link_ctnl_conflict {
         type uint32;
         description "Link ctnl conflict";
       }
       leaf link_utnl_conflict {
         type uint32;
         description "Link utnl conflict";
       }
       leaf link_tnl0_conflict {
         type uint32;
         description "Link tnl0 conflict";
       }
       leaf v0_ggsn_ip_chg {
         type uint32;
         description "Error ggsn ip for v0 packet";
       }
       leaf invalid_payload {
         type uint32;
         description "Invalid payload(GTP-NAT)";
       }
       leaf wrong_spu_sinfo {
         type uint32;
         description "Wrong SPU since NULL sinfor";
       }
       leaf wrong_spu_wing {
         type uint32;
         description "Wrong SPU since no match wings";
       }
       leaf wrong_spu_anchor {
         type uint32;
         description "Wrong SPU since no anchor GSN";
       }
       leaf req_retrans {
         type uint32;
         description "GTP request retransmit";
       }
       leaf cross_group_handover_deny {
         type uint32;
         description "Cross group handover deny";
       }
       leaf handover_default_deny {
         type uint32;
         description "Handover default deny";
       }
       leaf tunnel_in_process {
         type uint32;
         description "Tunnel is in processing";
       }
       leaf ne_group_check_fail {
         type uint32;
         description "NE group check fails";
       }
       leaf ue_group_check_fail {
         type uint32;
         description "UE group check fails";
       }
       leaf apn_rate_limit {
         type uint32;
         description "Over AP-controlled rate limit";
       }
     }
     container tunnel {
       leaf alloc-free-action {
         type string;
         description "Allocation or free tunnel";
       }
       leaf tunnel-cntr-total {
         type uint32;
         description "Tunnel counter number in total";
       }
       leaf tunnel-cntr-gtpv0 {
         type uint32;
         description "Tunnel counter number for GTPv0";
       }
       leaf tunnel-cntr-gtpv1c {
         type uint32;
         description "Tunnel counter number for GTPv1c";
       }
       leaf tunnel-cntr-gtpv1u {
         type uint32;
         description "Tunnel counter number for GTPv1u";
       }
       leaf tunnel-cntr-gtpv2c {
         type uint32;
         description "Tunnel counter number for GTPv2c";
       }
       leaf tunnel-cntr-gtpv2u {
         type uint32;
         description "Tunnel counter number for GTPv2u";
       }
     }
     container message {
       leaf packet-recv {
         type uint32;
         description "GTP message packet received";
       }
       leaf packet-fwd {
         type uint32;
         description "GTP message packet forwarded";
       }
       leaf packet-drop {
         type uint32;
         description "GTP message packet dropped";
       }
     }
     container message-brief {
       leaf v0-create-req-rcv {
         type uint32;
         description "GTPv0 create PDP request message packet";
       }
       leaf v0-create-req-fwd {
         type uint32;
         description "GTPv0 create PDP request message packet";
       }
       leaf v0-create-req-drp {
         type uint32;
         description "GTPv0 create PDP request message packet";
       }
       leaf v0-create-rsp-rcv {
         type uint32;
         description "GTPv0 create PDP response message packet";
       }
       leaf v0-create-rsp-fwd {
         type uint32;
         description "GTPv0 create PDP response message packet";
       }
       leaf v0-create-rsp-drp {
         type uint32;
         description "GTPv0 create PDP response message packet";
       }
       leaf v0-update-req-rcv {
         type uint32;
         description "GTPv0 update PDP request message packet";
       }
       leaf v0-update-req-fwd {
         type uint32;
         description "GTPv0 update PDP request message packet";
       }
       leaf v0-update-req-drp {
         type uint32;
         description "GTPv0 update PDP request message packet";
       }
       leaf v0-update-rsp-rcv {
         type uint32;
         description "GTPv0 update PDP response message packet";
       }
       leaf v0-update-rsp-fwd {
         type uint32;
         description "GTPv0 update PDP response message packet";
       }
       leaf v0-update-rsp-drp {
         type uint32;
         description "GTPv0 update PDP response message packet";
       }
       leaf v0-delete-req-rcv {
         type uint32;
         description "GTPv0 delete PDP request message packet";
       }
       leaf v0-delete-req-fwd {
         type uint32;
         description "GTPv0 delete PDP request message packet";
       }
       leaf v0-delete-req-drp {
         type uint32;
         description "GTPv0 delete PDP request message packet";
       }
       leaf v0-delete-rsp-rcv {
         type uint32;
         description "GTPv0 delete PDP response message packet";
       }
       leaf v0-delete-rsp-fwd {
         type uint32;
         description "GTPv0 delete PDP response message packet";
       }
       leaf v0-delete-rsp-drp {
         type uint32;
         description "GTPv0 delete PDP response message packet";
       }
       leaf v0-create-aa-req-rcv {
         type uint32;
         description "GTPv0 create PDP AA request message packet";
       }
       leaf v0-create-aa-req-fwd {
         type uint32;
         description "GTPv0 create PDP AA request message packet";
       }
       leaf v0-create-aa-req-drp {
         type uint32;
         description "GTPv0 create PDP AA request message packet";
       }
       leaf v0-create-aa-rsp-rcv {
         type uint32;
         description "GTPv0 create PDP AA response message packet";
       }
       leaf v0-create-aa-rsp-fwd {
         type uint32;
         description "GTPv0 create PDP AA response message packet";
       }
       leaf v0-create-aa-rsp-drp {
         type uint32;
         description "GTPv0 create PDP AA response message packet";
       }
       leaf v0-delete-aa-req-rcv {
         type uint32;
         description "GTPv0 delete PDP AA request message packet";
       }
       leaf v0-delete-aa-req-fwd {
         type uint32;
         description "GTPv0 delete PDP AA request message packet";
       }
       leaf v0-delete-aa-req-drp {
         type uint32;
         description "GTPv0 delete PDP AA request message packet";
       }
       leaf v0-delete-aa-rsp-rcv {
         type uint32;
         description "GTPv0 delete PDP AA response message packet";
       }
       leaf v0-delete-aa-rsp-fwd {
         type uint32;
         description "GTPv0 delete PDP AA response message packet";
       }
       leaf v0-delete-aa-rsp-drp {
         type uint32;
         description "GTPv0 delete PDP AA response message packet";
       }
       leaf v0-sgsn-context-req-rcv {
         type uint32;
         description "GTPv0 sgsn context request message packet";
       }
       leaf v0-sgsn-context-req-fwd {
         type uint32;
         description "GTPv0 sgsn context request message packet";
       }
       leaf v0-sgsn-context-req-drp {
         type uint32;
         description "GTPv0 sgsn context request message packet";
       }
       leaf v0-sgsn-context-rsp-rcv {
         type uint32;
         description "GTPv0 sgsn context response message packet";
       }
       leaf v0-sgsn-context-rsp-fwd {
         type uint32;
         description "GTPv0 sgsn context response message packet";
       }
       leaf v0-sgsn-context-rsp-drp {
         type uint32;
         description "GTPv0 sgsn context response message packet";
       }
       leaf v0-sgsn-context-ack-rcv {
         type uint32;
         description "GTPv0 sgsn context acknowledge message packet";
       }
       leaf v0-sgsn-context-ack-fwd {
         type uint32;
         description "GTPv0 sgsn context acknowledge message packet";
       }
       leaf v0-sgsn-context-ack-drp {
         type uint32;
         description "GTPv0 sgsn context acknowledge message packet";
       }
       leaf v0-others-rcv {
         type uint32;
         description "GTPv0 others message packet";
       }
       leaf v0-others-fwd {
         type uint32;
         description "GTPv0 others message packet";
       }
       leaf v0-others-drp {
         type uint32;
         description "GTPv0 others message packet";
       }
       leaf v1-create-req-rcv {
         type uint32;
         description "GTPv1 create PDP request message packet";
       }
       leaf v1-create-req-fwd {
         type uint32;
         description "GTPv1 create PDP request message packet";
       }
       leaf v1-create-req-drp {
         type uint32;
         description "GTPv1 create PDP request message packet";
       }
       leaf v1-create-rsp-rcv {
         type uint32;
         description "GTPv1 create PDP response message packet";
       }
       leaf v1-create-rsp-fwd {
         type uint32;
         description "GTPv1 create PDP response message packet";
       }
       leaf v1-create-rsp-drp {
         type uint32;
         description "GTPv1 create PDP response message packet";
       }
       leaf v1-update-req-rcv {
         type uint32;
         description "GTPv1 update PDP request message packet";
       }
       leaf v1-update-req-fwd {
         type uint32;
         description "GTPv1 update PDP request message packet";
       }
       leaf v1-update-req-drp {
         type uint32;
         description "GTPv1 update PDP request message packet";
       }
       leaf v1-update-rsp-rcv {
         type uint32;
         description "GTPv1 update PDP response message packet";
       }
       leaf v1-update-rsp-fwd {
         type uint32;
         description "GTPv1 update PDP response message packet";
       }
       leaf v1-update-rsp-drp {
         type uint32;
         description "GTPv1 update PDP response message packet";
       }
       leaf v1-delete-req-rcv {
         type uint32;
         description "GTPv1 delete PDP request message packet";
       }
       leaf v1-delete-req-fwd {
         type uint32;
         description "GTPv1 delete PDP request message packet";
       }
       leaf v1-delete-req-drp {
         type uint32;
         description "GTPv1 delete PDP request message packet";
       }
       leaf v1-delete-rsp-rcv {
         type uint32;
         description "GTPv1 delete PDP response message packet";
       }
       leaf v1-delete-rsp-fwd {
         type uint32;
         description "GTPv1 delete PDP response message packet";
       }
       leaf v1-delete-rsp-drp {
         type uint32;
         description "GTPv1 delete PDP response message packet";
       }
       leaf v1-sgsn-context-req-rcv {
         type uint32;
         description "GTPv1 sgsn context request message packet";
       }
       leaf v1-sgsn-context-req-fwd {
         type uint32;
         description "GTPv1 sgsn context request message packet";
       }
       leaf v1-sgsn-context-req-drp {
         type uint32;
         description "GTPv1 sgsn context request message packet";
       }
       leaf v1-sgsn-context-rsp-rcv {
         type uint32;
         description "GTPv1 sgsn context response message packet";
       }
       leaf v1-sgsn-context-rsp-fwd {
         type uint32;
         description "GTPv1 sgsn context response message packet";
       }
       leaf v1-sgsn-context-rsp-drp {
         type uint32;
         description "GTPv1 sgsn context response message packet";
       }
       leaf v1-sgsn-context-ack-rcv {
         type uint32;
         description "GTPv1 sgsn context acknowledge message packet";
       }
       leaf v1-sgsn-context-ack-fwd {
         type uint32;
         description "GTPv1 sgsn context acknowledge message packet";
       }
       leaf v1-sgsn-context-ack-drp {
         type uint32;
         description "GTPv1 sgsn context acknowledge message packet";
       }
       leaf v1-forward-reloc-req-rcv {
         type uint32;
         description "GTPv1 forward relocation request message packet";
       }
       leaf v1-forward-reloc-req-fwd {
         type uint32;
         description "GTPv1 forward relocation request message packet";
       }
       leaf v1-forward-reloc-req-drp {
         type uint32;
         description "GTPv1 forward relocation request message packet";
       }
       leaf v1-forward-reloc-rsp-rcv {
         type uint32;
         description "GTPv1 forward relocation response message packet";
       }
       leaf v1-forward-reloc-rsp-fwd {
         type uint32;
         description "GTPv1 forward relocation response message packet";
       }
       leaf v1-forward-reloc-rsp-drp {
         type uint32;
         description "GTPv1 forward relocation response message packet";
       }
       leaf v1-others-rcv {
         type uint32;
         description "GTPv1 others message packet";
       }
       leaf v1-others-fwd {
         type uint32;
         description "GTPv1 others message packet";
       }
       leaf v1-others-drp {
         type uint32;
         description "GTPv1 others message packet";
       }
       leaf v2-create-session-req-rcv {
         type uint32;
         description "GTPv2 create session request message packet";
       }
       leaf v2-create-session-req-fwd {
         type uint32;
         description "GTPv2 create session request message packet";
       }
       leaf v2-create-session-req-drp {
         type uint32;
         description "GTPv2 create session request message packet";
       }
       leaf v2-create-session-rsp-rcv {
         type uint32;
         description "GTPv2 create session response message packet";
       }
       leaf v2-create-session-rsp-fwd {
         type uint32;
         description "GTPv2 create session response message packet";
       }
       leaf v2-create-session-rsp-drp {
         type uint32;
         description "GTPv2 create session response message packet";
       }
       leaf v2-delete-session-req-rcv {
         type uint32;
         description "GTPv2 delete session request message packet";
       }
       leaf v2-delete-session-req-fwd {
         type uint32;
         description "GTPv2 delete session request message packet";
       }
       leaf v2-delete-session-req-drp {
         type uint32;
         description "GTPv2 delete session request message packet";
       }
       leaf v2-delete-session-rsp-rcv {
         type uint32;
         description "GTPv2 delete session response message packet";
       }
       leaf v2-delete-session-rsp-fwd {
         type uint32;
         description "GTPv2 delete session response message packet";
       }
       leaf v2-delete-session-rsp-drp {
         type uint32;
         description "GTPv2 delete session response message packet";
       }
       leaf v2-create-bearer-req-rcv {
         type uint32;
         description "GTPv2 create bearer request message packet";
       }
       leaf v2-create-bearer-req-fwd {
         type uint32;
         description "GTPv2 create bearer request message packet";
       }
       leaf v2-create-bearer-req-drp {
         type uint32;
         description "GTPv2 create bearer request message packet";
       }
       leaf v2-create-bearer-rsp-rcv {
         type uint32;
         description "GTPv2 create bearer response message packet";
       }
       leaf v2-create-bearer-rsp-fwd {
         type uint32;
         description "GTPv2 create bearer response message packet";
       }
       leaf v2-create-bearer-rsp-drp {
         type uint32;
         description "GTPv2 create bearer response message packet";
       }
       leaf v2-modify-bearer-req-rcv {
         type uint32;
         description "GTPv2 modify bearer request message packet";
       }
       leaf v2-modify-bearer-req-fwd {
         type uint32;
         description "GTPv2 modify bearer request message packet";
       }
       leaf v2-modify-bearer-req-drp {
         type uint32;
         description "GTPv2 modify bearer request message packet";
       }
       leaf v2-modify-bearer-rsp-rcv {
         type uint32;
         description "GTPv2 modify bearer response message packet";
       }
       leaf v2-modify-bearer-rsp-fwd {
         type uint32;
         description "GTPv2 modify bearer response message packet";
       }
       leaf v2-modify-bearer-rsp-drp {
         type uint32;
         description "GTPv2 modify bearer response message packet";
       }
       leaf v2-delete-bearer-req-rcv {
         type uint32;
         description "GTPv2 delete bearer request message packet";
       }
       leaf v2-delete-bearer-req-fwd {
         type uint32;
         description "GTPv2 delete bearer request message packet";
       }
       leaf v2-delete-bearer-req-drp {
         type uint32;
         description "GTPv2 delete bearer request message packet";
       }
       leaf v2-delete-bearer-rsp-rcv {
         type uint32;
         description "GTPv2 delete bearer response message packet";
       }
       leaf v2-delete-bearer-rsp-fwd {
         type uint32;
         description "GTPv2 delete bearer response message packet";
       }
       leaf v2-delete-bearer-rsp-drp {
         type uint32;
         description "GTPv2 delete bearer response message packet";
       }
       leaf v2-context-req-rcv {
         type uint32;
         description "GTPv2 context request message packet";
       }
       leaf v2-context-req-fwd {
         type uint32;
         description "GTPv2 context request message packet";
       }
       leaf v2-context-req-drp {
         type uint32;
         description "GTPv2 context request message packet";
       }
       leaf v2-context-rsp-rcv {
         type uint32;
         description "GTPv2 context response message packet";
       }
       leaf v2-context-rsp-fwd {
         type uint32;
         description "GTPv2 context response message packet";
       }
       leaf v2-context-rsp-drp {
         type uint32;
         description "GTPv2 context response message packet";
       }
       leaf v2-context-ack-rcv {
         type uint32;
         description "GTPv2 context acknowledge message packet";
       }
       leaf v2-context-ack-fwd {
         type uint32;
         description "GTPv2 context acknowledge message packet";
       }
       leaf v2-context-ack-drp {
         type uint32;
         description "GTPv2 context acknowledge message packet";
       }
       leaf v2-forward-reloc-req-rcv {
         type uint32;
         description "GTPv2 forward relocation request message packet";
       }
       leaf v2-forward-reloc-req-fwd {
         type uint32;
         description "GTPv2 forward relocation request message packet";
       }
       leaf v2-forward-reloc-req-drp {
         type uint32;
         description "GTPv2 forward relocation request message packet";
       }
       leaf v2-forward-reloc-rsp-rcv {
         type uint32;
         description "GTPv2 forward relocation response message packet";
       }
       leaf v2-forward-reloc-rsp-fwd {
         type uint32;
         description "GTPv2 forward relocation response message packet";
       }
       leaf v2-forward-reloc-rsp-drp {
         type uint32;
         description "GTPv2 forward relocation response message packet";
       }
       leaf v2-create-indir-fwd-tnl-req-rcv {
         type uint32;
         description "GTPv2 create indirect data forwarding tunnel request message packet";
       }
       leaf v2-create-indir-fwd-tnl-req-fwd {
         type uint32;
         description "GTPv2 create indirect data forwarding tunnel request message packet";
       }
       leaf v2-create-indir-fwd-tnl-req-drp {
         type uint32;
         description "GTPv2 create indirect data forwarding tunnel request message packet";
       }
       leaf v2-create-indir-fwd-tnl-rsp-rcv {
         type uint32;
         description "GTPv2 create indirect data forwarding tunnel response message packet";
       }
       leaf v2-create-indir-fwd-tnl-rsp-fwd {
         type uint32;
         description "GTPv2 create indirect data forwarding tunnel response message packet";
       }
       leaf v2-create-indir-fwd-tnl-rsp-drp {
         type uint32;
         description "GTPv2 create indirect data forwarding tunnel response message packet";
       }
       leaf v2-others-rcv {
         type uint32;
         description "GTPv2 others message packet";
       }
       leaf v2-others-fwd {
         type uint32;
         description "GTPv2 others message packet";
       }
       leaf v2-others-drp {
         type uint32;
         description "GTPv2 others message packet";
       }
     }
   }
   grouping gtp-show-statistics-all-block {
     leaf fpc-id {
       type uint32;
       description "FPC slot ID";
     }
     leaf pic-id {
       type uint32;
       description "PIC slot ID";
     }
     leaf active-gsn {
       type uint32;
       description "Total number of active GSNs";
     }
     leaf obsolete-gsn {
       type uint32;
       description "Total number of obsolete GSNs";
     }
     leaf use-rate {
       type uint32;
       description "Use rate of GSN table";
     }
   }
   grouping gtp-show-handover-group-block {
     leaf handover-group-name {
       type string;
       description "Handover group name";
     }
     leaf ho-address-book {
       type string;
       description "Address book name";
     }
     leaf ho-address-set {
       type string;
       description "Address set name";
     }
   }
   grouping gtp-show-ip-group-block {
     leaf ip-group-name {
       type string;
       description "IP group name";
     }
     leaf ig-address-book {
       type string;
       description "Address book name";
     }
     leaf ig-address-set {
       type string;
       description "Address set name";
     }
   }
   grouping gtp-show-msgie-prof-v1-block {
     container gtp-show-prof-summary {
       leaf gtp-prof-list {
         type string;
         description "GTP profile list";
       }
     }
     container msgie-prof-v1-detail {
       leaf msgie-prof-v1-name {
         type string;
         description " GTPv1 message-ie profile name";
       }
       leaf msgie-prof-v1-uid {
         type string;
         description " GTPv1 message-ie profile uid";
       }
       leaf msgie-prof-v1-msg-number {
         type string;
         description " GTPv1 message number";
       }
       leaf msgie-prof-v1-msg-ie-bitmap {
         type string;
         description " GTPv1 message IE bitmap";
       }
     }
   }
   grouping gtp-show-msgie-prof-v2-block {
     container gtp-show-prof-summary {
       leaf gtp-prof-list {
         type string;
         description "GTP profile list";
       }
     }
     container msgie-prof-v2-detail {
       leaf msgie-prof-v2-name {
         type string;
         description " GTPv2 message-ie profile name";
       }
       leaf msgie-prof-v2-uid {
         type string;
         description " GTPv2 message-ie profile uid";
       }
       leaf msgie-prof-v2-msg-number {
         type string;
         description " GTPv2 message number";
       }
       leaf msgie-prof-v2-msg-ie {
         type string;
         description " GTPv2 message IE";
       }
       leaf msgie-prof-v2-msg-ie-ins-number {
         type string;
         description " GTPv2 message IE instance number ";
       }
     }
   }
   grouping gtp-show-grpie-prof-block {
     container gtp-show-prof-summary {
       leaf gtp-prof-list {
         type string;
         description "GTP profile list";
       }
     }
     container grpie-prof-detail {
       leaf grpie-prof-name {
         type string;
         description " GTP grouped-ie profile name";
       }
       leaf grpie-prof-uid {
         type string;
         description " GTP grouped-ie profile uid";
       }
       leaf grpie-prof-ie-number {
         type string;
         description " GTP IE number of the grouped-ie";
       }
       leaf grpie-prof-ies {
         type string;
         description " GTP IE number in the profile";
       }
       leaf grpie-prof-ies-ins-number {
         type string;
         description " GTP IE instance number ";
       }
     }
   }
   grouping gtp-show-gtp-prof-ie-set-block {
     container gtp-show-prof-summary {
       leaf gtp-prof-list {
         type string;
         description "GTP profile list";
       }
     }
     container gtp-prof-ie-set-detail {
       leaf gtp-prof-ie-set-name {
         type string;
         description "IE set name";
       }
       leaf gtp-prof-ie-set-uid {
         type uint32;
         description "IE set uid";
       }
       leaf gtp-prof-ie-set-bitmap {
         type string;
         description "IE bitmap in IE set";
       }
     }
   }
   grouping gtp-show-gtp-msg-list-block {
     container gtp-show-prof-summary {
       leaf gtp-prof-list {
         type string;
         description "GTP profile list";
       }
     }
     container gtp-msg-list-detail {
       leaf gtp-msg-list-name {
         type string;
         description "Message list name";
       }
       leaf gtp-msg-list-uid {
         type uint32;
         description "Message list uid";
       }
       leaf gtp-msg-list-msg-number {
         type string;
         description "Message in message list";
       }
     }
   }
   grouping gtp-show-apn-control-block {
     container gtp-show-prof-summary {
       leaf gtp-prof-list {
         type string;
         description "GTP profile list";
       }
     }
     container gtp-apnc-detail {
       leaf apn-string {
         type string;
         description "APN control profile name";
       }
       leaf apnc-uid {
         type uint32;
         description "APN control profile uid";
       }
       leaf arl-alarm-threshold {
         type string;
         description " GTP APN controlled rate-limit alarm threshold";
       }
       leaf arl-drop-threshold {
         type string;
         description " GTP APN controlled rate-limit drop threshold";
       }
       leaf arl-v0-msg-list {
         type string;
         description " GTPv0 message number";
       }
       leaf arl-v1-msg-list {
         type string;
         description " GTPv1 message number";
       }
       leaf arl-v2-msg-list {
         type string;
         description " GTPv2 message number";
       }
     }
   }
   grouping gtp-show-apn-control-group-block {
     container gtp-show-prof-summary {
       leaf gtp-prof-list {
         type string;
         description "GTP profile list";
       }
     }
     container gtp-apnc-grp-detail {
       leaf apnc-grp-name {
         type string;
         description "APN control group name";
       }
       leaf apnc-grp-uid {
         type uint32;
         description "APN control profile group uid";
       }
     }
     container gtp-show-apn-control {
       container gtp-show-prof-summary {
         leaf gtp-prof-list {
           type string;
           description "GTP profile list";
         }
       }
       container gtp-apnc-detail {
         leaf apn-string {
           type string;
           description "APN control profile name";
         }
         leaf apnc-uid {
           type uint32;
           description "APN control profile uid";
         }
         leaf arl-alarm-threshold {
           type string;
           description " GTP APN controlled rate-limit alarm threshold";
         }
         leaf arl-drop-threshold {
           type string;
           description " GTP APN controlled rate-limit drop threshold";
         }
         leaf arl-v0-msg-list {
           type string;
           description " GTPv0 message number";
         }
         leaf arl-v1-msg-list {
           type string;
           description " GTPv1 message number";
         }
         leaf arl-v2-msg-list {
           type string;
           description " GTPv2 message number";
         }
       }
     }
   }
   grouping sctp-show-counters-block {
     container show-counters-slot {
       leaf fpc-slot {
         type uint32;
         description "FPC slot number";
       }
       leaf pic-slot {
         type uint32;
         description "PIC slot number";
       }
     }
     container show-counter-association-num {
       leaf counter-assoc-name {
         type string;
         description "Association number name when show counter";
       }
       leaf counter-assoc-number {
         type uint32;
         description "Association number when show counter";
       }
     }
     container dbg-records {
       leaf pak-without-profile {
         type uint32;
         description "SCTP packet without profile";
       }
       leaf pak-nat-only {
         type uint32;
         description "SCTP nat only";
       }
       leaf pak-inspection {
         type uint32;
         description "SCTP packet for inspection";
       }
       leaf drop-at-clearing-all {
         type uint32;
         description "SCTP drop for clearing all";
       }
       leaf src-pnat {
         type uint32;
         description "SCTP source port nat";
       }
       leaf dst-pnat {
         type uint32;
         description "SCTP destination port nat";
       }
       leaf hostname {
         type uint32;
         description "SCTP hostname";
       }
       leaf dup-init {
         type uint32;
         description "SCTP duplicated init";
       }
       leaf dup-initack {
         type uint32;
         description "SCTP duplicated init ack";
       }
       leaf tag-null-abort {
         type uint32;
         description "SCTP tag null abort";
       }
       leaf error-chunk {
         type uint32;
         description "SCTP error trunk";
       }
       leaf bad-interest {
         type uint32;
         description "SCTP bad interest";
       }
       leaf wing-attach {
         type uint32;
         description "SCTP attach wing";
       }
       leaf wing-detach {
         type uint32;
         description "SCTP detach wing";
       }
       leaf wrap-with-assoc {
         type uint32;
         description "SCTP wrap with association";
       }
       leaf unwrap-from-assoc {
         type uint32;
         description "SCTP unwrap from association";
       }
       leaf conflict-assoc {
         type uint32;
         description "SCTP conflict with association";
       }
       leaf conflict-redr {
         type uint32;
         description "SCTP conflict with redr association";
       }
       leaf wrong-distribution {
         type uint32;
         description "SCTP wrong distribution by NP";
       }
     }
     container packet-error {
       leaf chunk-unsupport {
         type uint32;
         description "SCTP unsupported chunk";
       }
       leaf cookie-invalid {
         type uint32;
         description "SCTP invalid cookie";
       }
       leaf pkt-len {
         type uint32;
         description "SCTP packet len";
       }
       leaf chunk-len {
         type uint32;
         description "SCTP chunk len";
       }
       leaf tag-error {
         type uint32;
         description "SCTP initial/verification tag error";
       }
       leaf bad-len {
         type uint32;
         description "SCTP bad len";
       }
       leaf bad-chk-hdr {
         type uint32;
         description "SCTP bad chunk header";
       }
     }
     container assoc-match-error {
       leaf ha-assoc {
         type uint32;
         description "SCTP HA association";
       }
       leaf data-assoc {
         type uint32;
         description "SCTP data association";
       }
       leaf initack-assoc {
         type uint32;
         description "SCTP INIT ACK association";
       }
       leaf sack-assoc {
         type uint32;
         description "SCTP SACK association";
       }
       leaf hb-assoc {
         type uint32;
         description "SCTP HB association";
       }
       leaf hb-ack-assoc {
         type uint32;
         description "SCTP HB ACK association";
       }
       leaf abort-assoc {
         type uint32;
         description "SCTP ABORT association";
       }
       leaf shutdown-assoc {
         type uint32;
         description "SCTP SHUNTDOWN association";
       }
       leaf shutdown-ack-assoc {
         type uint32;
         description "SCTP SHUNTDOWN ACK association";
       }
       leaf err-assoc {
         type uint32;
         description "SCTP ERROR association";
       }
       leaf cookie-echo-assoc {
         type uint32;
         description "SCTP COOKIE ECHO association";
       }
       leaf cookie-ack-assoc {
         type uint32;
         description "SCTP COOKIE ACK association";
       }
       leaf shutdown-complete-assoc {
         type uint32;
         description "SCTP SHUNTDOWN COMPLETE association";
       }
       leaf lookup-no-assoc {
         type uint32;
         description "SCTP cannot find association when lookup";
       }
       leaf dup-init-diff-ip-list {
         type uint32;
         description "SCTP duplicated INIT with different IP list";
       }
       leaf dup-init-diff-dst-ip {
         type uint32;
         description "SCTP duplicated INIT with different dst IP";
       }
       leaf dup-initack-src-ip-invalid {
         type uint32;
         description "SCTP duplicated INIT ACK with invalid IP";
       }
       leaf dup-initack-diff-ip-list {
         type uint32;
         description "SCTP duplicated INIT ACK with different IP list";
       }
     }
     container assoc-state-error {
       leaf data-state {
         type uint32;
         description "SCTP data state";
       }
       leaf init-state {
         type uint32;
         description "SCTP INIT state";
       }
       leaf initack-state {
         type uint32;
         description "SCTP INIT ACK state";
       }
       leaf sack-state {
         type uint32;
         description "SCTP SACK state";
       }
       leaf shutdown-state {
         type uint32;
         description "SCTP SHUNTDOWN state";
       }
       leaf shutdown-ack-state {
         type uint32;
         description "SCTP SHUNTDOWN ACK state";
       }
       leaf cookie-echo-state {
         type uint32;
         description "SCTP COOKIE ECHO state";
       }
       leaf cookie-ack-state {
         type uint32;
         description "SCTP COOKIE ACK state";
       }
       leaf shutdown-complete-state {
         type uint32;
         description "SCTP SHUNTDOWN COMPLETE state";
       }
       leaf cookie-echo-retrans-timeout {
         type uint32;
         description "SCTP COOKIE ECHO retransmit time out";
       }
       leaf cookie-ack-retrans-timeout {
         type uint32;
         description "SCTP COOKIE ACK retransmit time out";
       }
     }
     container assoc-loadbalance-counter {
       leaf redirect-assoc-request-send {
         type uint32;
         description "SCTP redirect-assoc request send";
       }
       leaf redirect-assoc-request-ack-recv {
         type uint32;
         description "SCTP redirect-assoc request ack receive";
       }
       leaf redirect-assoc-request-nack-recv {
         type uint32;
         description "SCTP redirect-assoc request nack receive";
       }
       leaf redirect-assoc-request-ack-timeout {
         type uint32;
         description "SCTP redirect-assoc request ack timeout";
       }
       leaf redirect-assoc-request-recv {
         type uint32;
         description "SCTP redirect-assoc request receive";
       }
       leaf redirect-assoc-request-ack-send {
         type uint32;
         description "SCTP redirect-assoc request ack send";
       }
       leaf redirect-assoc-request-nack-send {
         type uint32;
         description "SCTP redirect-assoc request nack send";
       }
     }
     container over-rate-drop {
       leaf sccp {
         type uint32;
         description "SCTP sccp over rate drop";
       }
       leaf ssp {
         type uint32;
         description "SCTP ssp over rate drop";
       }
       leaf sst {
         type uint32;
         description "SCTP sst over rate drop";
       }
     }
     container memory-counters {
       leaf alloc-assoc {
         type uint32;
         description "SCTP allocated association";
       }
       leaf free-assoc {
         type uint32;
         description "SCTP free association";
       }
       leaf alloc-redr {
         type uint32;
         description "SCTP allocated redr association";
       }
       leaf free-redr {
         type uint32;
         description "SCTP free redr association";
       }
       leaf alloc-assoc-wrap {
         type uint32;
         description "SCTP allocated association wrap";
       }
       leaf free-assoc-wrap {
         type uint32;
         description "SCTP free association wrap";
       }
       leaf alloc-cookie {
         type uint32;
         description "SCTP allocated cookie";
       }
       leaf free-cookie {
         type uint32;
         description "SCTP free cookie";
       }
       leaf alloc-addr {
         type uint32;
         description "SCTP allocated addr";
       }
       leaf free-addr {
         type uint32;
         description "SCTP free addr";
       }
     }
     container ha-counters {
       leaf invalid-type {
         type uint32;
         description "SCTP HA invalid type";
       }
       leaf bad-msg {
         type uint32;
         description "SCTP HA bad message";
       }
       leaf no-assoc-info {
         type uint32;
         description "SCTP HA no association information";
       }
       leaf send-fail {
         type uint32;
         description "SCTP HA send fail";
       }
       leaf dup-create {
         type uint32;
         description "SCTP HA duplicated create";
       }
       leaf no-policy {
         type uint32;
         description "SCTP HA no policy";
       }
       leaf no-profile {
         type uint32;
         description "SCTP HA no profile";
       }
       leaf alloc-fail {
         type uint32;
         description "SCTP HA alloc fail";
       }
       leaf non-established-issu {
         type uint32;
         description "SCTP HA non-established ISSU";
       }
     }
     container other-error {
       leaf over-max {
         type uint32;
         description "SCTP reach MAX number";
       }
       leaf over-min {
         type uint32;
         description "SCTP reach MIN number";
       }
       leaf del-error {
         type uint32;
         description "SCTP error when delete";
       }
       leaf sess-cookie-set-fail {
         type uint32;
         description "SCTP fail when set session cookie";
       }
       leaf sess-cookie-get-fail {
         type uint32;
         description "SCTP fail when get session cookie";
       }
       leaf no-assoc-install-redr-cb {
         type uint32;
         description "SCTP cannot find assoc in install redr assoc callback";
       }
       leaf wrap-alloced-failure {
         type uint32;
         description "SCTP fail when alloc wrap";
       }
       leaf wrap-null-assocp {
         type uint32;
         description "SCTP wrap with null association pointer";
       }
       leaf assoc-alloced-failure {
         type uint32;
         description "SCTP fail when alloc assoc";
       }
       leaf redr-assoc-alloced-failure {
         type uint32;
         description "SCTP fail when alloc redr assoc";
       }
       leaf invalid-pkt-pointer {
         type uint32;
         description "SCTP invalid packet pointer";
       }
       leaf nat-jbuf-alloc-fail {
         type uint32;
         description "SCTP fail when alloc nat jbuf";
       }
       leaf evt-cookie-alloc-fail {
         type uint32;
         description "SCTP fail when alloc evt cookie";
       }
     }
     container show-counters-recvdrop {
       leaf recvdrop-name {
         type string;
         description "Counter name";
       }
       leaf received {
         type uint32;
         description "Received packet";
       }
       leaf drop {
         type uint32;
         description "Dropped packet";
       }
       leaf over-rate {
         type uint32;
         description "Over rate packet";
       }
     }
     container show-counters-m3ua {
       leaf m3ua-recvdrop-name {
         type uint32;
         description "M3UA counter name";
       }
       leaf m3ua-received {
         type uint32;
         description "M3UA received packet";
       }
       leaf m3ua-drop {
         type uint32;
         description "M3UA dropped packet";
       }
     }
     container show-counters-errdrop {
       leaf errdrop-name {
         type uint32;
         description "Error/Drop counter name";
       }
       leaf errdrop {
         type uint32;
         description "Error/Drop packet";
       }
     }
   }
   grouping metric-collect-information-block {
     leaf success {
       type uint32;
       description "Metric post success counter";
     }
     leaf failure {
       type uint32;
       description "Metric post error counter";
     }
     leaf last-post-datetime {
       type string;
       description "Last time when metric posted to CloudWatch";
     }
   }
   grouping log-collect-information-block {
     list log-file {
       description "Collected log file";
       leaf name {
         type string;
         description "Log file name";
       }
       leaf posted {
         type uint32;
         description "Log number posted to CloudWatch";
       }
       leaf exception {
         type uint32;
         description "Exception number when post log to CloudWatch";
       }
       leaf security-hub-imported {
         type uint32;
         description "Log number imported to security hub";
       }
     }
   }
   grouping cloud-ha-information-block {
     leaf cloud-type {
       type string;
       description "Cloud platform type";
     }
     leaf cloud-service-type {
       type string;
       description "Cloud service type";
     }
     leaf cloud-service-status {
       type string;
       description "Cloud service status";
     }
   }
   grouping hakr-keychain-information-block {
     list hakr-keychain {
       leaf hakr-keychain-name {
         type string;
         description "Keychain name";
       }
       leaf hakr-keychain-active-send-key {
         type int32;
         description "Transmit key ID";
       }
       leaf hakr-keychain-active-receive-key {
         type int32;
         description "Receive key ID";
       }
       leaf hakr-keychain-next-send-key {
         type string;
         description "Next transmit key";
       }
       leaf hakr-keychain-next-receive-key {
         type string;
         description "Next receive key";
       }
       leaf hakr-keychain-next-key-time {
         type string;
         description "Key transition time";
       }
       leaf hakr-keychain-tolerance {
         type int32;
         description "Clock skew tolerance";
       }
       list hakr-keys {
         leaf hakr-key-id {
           type string;
           description "Authentication element identifier";
         }
         leaf hakr-key-algorithm {
           type string;
           description "Authentication algorithm";
         }
         leaf hakr-key-fallback-algorithm {
           type string;
           description "Fallback Authentication algorithm";
         }
         leaf hakr-key-state {
           type string;
           description "Authentication key operational state";
         }
         leaf hakr-key-options {
           type string;
           description "Authentication key options";
         }
         leaf hakr-key-start-time {
           type string;
           description "Time since the current session began (hours:minutes:seconds)";
         }
         leaf hakr-key-mode {
           type string;
           description "Authentication key mode";
         }
         leaf hakr-key-secret {
           type string;
           description "Authentication key";
         }
       }
       leaf-list hakr-sa-clients {
         type string;
         description "Keychain clients ";
       }
     }
     list hakr-keys {
       leaf hakr-key-secret {
         type string;
         description "Authentication key";
       }
       leaf hakr-key-id {
         type string;
         description "Authentication element identifier";
       }
       leaf hakr-key-algorithm {
         type string;
         description "Authentication algorithm";
       }
       leaf hakr-key-fallback-algorithm {
         type string;
         description "Fallback Authentication algorithm";
       }
       leaf hakr-key-state {
         type string;
         description "Authentication key operational state";
       }
       leaf hakr-key-options {
         type string;
         description "Authentication key options";
       }
       leaf hakr-key-start-time {
         type string;
         description "Time since the current session began (hours:minutes:seconds)";
       }
       leaf hakr-key-mode {
         type string;
         description "Authentication key mode";
       }
     }
   }
   grouping mka-session-information-block {
     leaf interface-name {
       type string;
     }
   }
   grouping mka-statistics-block {
     container mka-interface-statistics {
       leaf interface-name {
         type string;
       }
       leaf received-packets {
         type uint32;
         description "Number of MKA packets received";
       }
       leaf sent-packets {
         type uint32;
         description "Number of MKA packets sent";
       }
       leaf version-error {
         type uint32;
         description "Number of MKA packets with version mismatch";
       }
       leaf cak-error {
         type uint32;
         description "Number of MKA packets with CAK invalid or mismatch";
       }
       leaf integrity-check-value-mismatch {
         type uint32;
         description "Number of MKA packets with integrity check value mismatch";
       }
       leaf duplicate-message-identifier {
         type uint32;
         description "Number of MKA packets with duplicate message identifier";
       }
       leaf duplicate-message-number {
         type uint32;
         description "Number of MKA packets with duplicate message number";
       }
       leaf duplicate-address {
         type uint32;
         description "Number of MKA packets with duplicate address";
       }
       leaf invalid-destination {
         type uint32;
         description "Number of MKA packets with invalid destination";
       }
       leaf format-error {
         type uint32;
         description "Number of MKA packets with format errors";
       }
       leaf old-message-number {
         type uint32;
         description "Number of MKA packets with old or replayed message number";
       }
     }
   }
   grouping macsec-connection-information-block {
     leaf interface-name {
       type string;
     }
     leaf connectivity-association-name {
       type string;
       description "Connectivity association name";
     }
     leaf cipher-suite {
       type string;
       description "Cipher suite name";
     }
     leaf encryption {
       type string;
       description "MAC security encryption status";
     }
     leaf offset {
       type uint32;
       description "MAC security offset";
     }
     leaf include-sci {
       type string;
       description "MAC security SCI inclusion status";
     }
     leaf-list replay-protect {
       type string;
       description "MAC replay protect status";
     }
     leaf replay-protect-window {
       type uint32;
       description "MAC security replay protect window size";
     }
     leaf sci {
       type string;
       description "MKA outbound secure channel identifier";
     }
     leaf outgoing-packet-number {
       type uint64;
       description "MAC security outgoing packet number";
     }
     leaf lowest-accepted-packet-number {
       type uint32;
       description "MAC security lowest accepted packet number";
     }
     leaf association-number {
       type uint32;
       description "MAC security association number";
     }
     leaf member-identifier {
       type string;
       description "MKA member identifier";
     }
     leaf key-number {
       type uint32;
       description "MKA key number being used";
     }
     leaf association-number-status {
       type string;
       description "MAC security association number status";
     }
     leaf start-time {
       type string;
       description "MAC security association number using start time";
     }
     list macsec-interface-common-information {
       leaf interface-name {
         type string;
       }
       leaf connectivity-association-name {
         type string;
         description "Connectivity association name";
       }
       leaf cipher-suite {
         type string;
         description "Cipher suite name";
       }
       leaf encryption {
         type string;
         description "MAC security encryption status";
       }
       leaf offset {
         type uint32;
         description "MAC security offset";
       }
       leaf include-sci {
         type string;
         description "MAC security SCI inclusion status";
       }
       leaf-list replay-protect {
         type string;
         description "MAC replay protect status";
       }
       leaf replay-protect-window {
         type uint32;
         description "MAC security replay protect window size";
       }
     }
     list outbound-secure-channel {
       leaf sci {
         type string;
         description "MKA outbound secure channel identifier";
       }
       leaf outgoing-packet-number {
         type uint64;
         description "MAC security outgoing packet number";
       }
       list outbound-secure-association {
         leaf association-number {
           type uint32;
           description "MAC security association number";
         }
         leaf association-number-status {
           type string;
           description "MAC security association number status";
         }
         leaf create-time {
           type string;
           description "MAC security association number creation time";
         }
         leaf member-identifier {
           type string;
           description "MKA member identifier";
         }
         leaf key-number {
           type uint32;
           description "MKA key number being used";
         }
         leaf start-time {
           type string;
           description "MAC security association number using start time";
         }
       }
     }
     list inbound-secure-channel {
       leaf sci {
         type string;
         description "MKA outbound secure channel identifier";
       }
       leaf lowest-accepted-packet-number {
         type uint32;
         description "MAC security lowest accepted packet number";
       }
       list inbound-secure-association {
         leaf association-number {
           type uint32;
           description "MAC security association number";
         }
         leaf association-number-status {
           type string;
           description "MAC security association number status";
         }
         leaf create-time {
           type string;
           description "MAC security association number creation time";
         }
         leaf member-identifier {
           type string;
           description "MKA member identifier";
         }
         leaf key-number {
           type uint32;
           description "MKA key number being used";
         }
         leaf start-time {
           type string;
           description "MAC security association number using start time";
         }
       }
     }
   }
   grouping macsec-statistics-block {
     leaf macsec-tx-sc-protected {
       type int32;
       description "Protected Secure Channel MACSec packets transmitted";
     }
     leaf macsec-tx-sc-encrypted {
       type int32;
       description "Encrypted Secure Channel MACSec packets transmitted";
     }
     leaf macsec-tx-sc-protectedbytes {
       type int32;
       description "Protected Secure Channel MACSec bytes transmitted";
     }
     leaf macsec-tx-sc-encryptedbytes {
       type int32;
       description "Encrypted Secure Channel MACSec bytes transmitted";
     }
     leaf macsec-rx-sc-ok {
       type int32;
       description "OK Secure Association MACSec packets received";
     }
     leaf macsec-rx-sc-validatedbytes {
       type int32;
       description "Validated Secure Association MACSec bytes received";
     }
     leaf macsec-rx-sc-decryptedbytes {
       type int32;
       description "Validated Secure Association MACSec bytes received";
     }
     leaf interface-name {
       type string;
     }
     leaf encrypted-packets {
       type uint64;
       description "Macsec encrypted packets sent";
     }
     leaf encrypted-bytes {
       type uint64;
       description "Macsec encrypted bytes sent";
     }
     leaf protected-packets {
       type uint64;
       description "Macsec packets sent with only integrity protection";
     }
     leaf protected-bytes {
       type uint64;
       description "Macsec bytes sent with only integrity protection";
     }
     leaf ok-packets {
       type uint64;
       description "Macsec packets accepted";
     }
     leaf decrypted-bytes {
       type uint64;
       description "Macsec received bytes decrypted";
     }
     leaf decrypted-packets {
       type uint64;
       description "Macsec received packets decrypted";
     }
     leaf validated-packets {
       type uint64;
       description "Macsec received packets validated";
     }
     leaf validated-bytes {
       type uint64;
       description "Macsec received bytes validated";
     }
     leaf untagged-packets {
       type uint64;
       description "Macsec untagged packets";
     }
     leaf toolong-packets {
       type uint64;
       description "Macsec too long packets transmitted on a secure channel";
     }
     leaf control-packets {
       type uint64;
       description "Macsec control packets received on a secure channel";
     }
     leaf tagged-miss-packets {
       type uint64;
       description "Macsec tagged miss packets received on a secure channel";
     }
     leaf untagged-hit-packets {
       type uint64;
       description "Macsec untagged hit packets received on a secure channel";
     }
     leaf notag-packets {
       type uint64;
       description "Macsec no tag packets received on a secure channel";
     }
     leaf badtag-packets {
       type uint64;
       description "Macsec bad tag packets received on a secure channel";
     }
     leaf unknown-sci-packets {
       type uint64;
       description "Macsec unknown sci packets received on a secure channel";
     }
     leaf no-sci-packets {
       type uint64;
       description "Macsec no sci packets received on a secure channel";
     }
     leaf control-pass-packets {
       type uint64;
       description "Macsec allowed control packets received on a secure channel";
     }
     leaf uncontrol-pass-packets {
       type uint64;
       description "Macsec allowed uncontrol packets received on a secure channel";
     }
     leaf control-fail-packets {
       type uint64;
       description "Macsec dropped control packets received on a secure channel";
     }
     leaf uncontrol-fail-packets {
       type uint64;
       description "Macsec dropped uncontrol packets received on a secure channel";
     }
     leaf hit-dropped-packets {
       type uint64;
       description "Macsec hit dropped packets received on a security channel";
     }
     leaf notusing-sa-packets {
       type uint64;
       description "Macsec not using sa packets received on a security channel";
     }
     leaf unused-sa-packets {
       type uint64;
       description "Macsec unused sa packets received on a security channel";
     }
     leaf late-packets {
       type uint64;
       description "Macsec late packets dropped on a security channel";
     }
     leaf delayed-packets {
       type uint64;
       description "Macsec delayed packets accepted on a security channel";
     }
     leaf unchecked-packets {
       type uint64;
       description "Macsec unchecked packets accepted on a security channel";
     }
     leaf notvalid-packets {
       type uint64;
       description "Macsec not valid packets dropped on a security channel";
     }
     leaf invalid-packets {
       type uint64;
       description "Macsec invalid packets accepted on a security channel";
     }
     list secure-channel-sent {
       leaf encrypted-packets {
         type uint64;
         description "Macsec encrypted packets sent";
       }
       leaf encrypted-bytes {
         type uint64;
         description "Macsec encrypted bytes sent";
       }
       leaf protected-packets {
         type uint64;
         description "Macsec packets sent with only integrity protection";
       }
       leaf protected-bytes {
         type uint64;
         description "Macsec bytes sent with only integrity protection";
       }
     }
     list secure-association-sent {
       leaf encrypted-packets {
         type uint64;
         description "Macsec encrypted packets sent";
       }
       leaf encrypted-bytes {
         type uint64;
         description "Macsec encrypted bytes sent";
       }
       leaf protected-packets {
         type uint64;
         description "Macsec packets sent with only integrity protection";
       }
       leaf protected-bytes {
         type uint64;
         description "Macsec bytes sent with only integrity protection";
       }
     }
     list secure-channel-received {
       leaf ok-packets {
         type uint64;
         description "Macsec packets accepted";
       }
       leaf decrypted-packets {
         type uint64;
         description "Macsec received packets decrypted";
       }
       leaf decrypted-bytes {
         type uint64;
         description "Macsec received bytes decrypted";
       }
       leaf validated-packets {
         type uint64;
         description "Macsec received packets validated";
       }
       leaf validated-bytes {
         type uint64;
         description "Macsec received bytes validated";
       }
     }
     list secure-association-received {
       leaf ok-packets {
         type uint64;
         description "Macsec packets accepted";
       }
       leaf decrypted-packets {
         type uint64;
         description "Macsec received packets decrypted";
       }
       leaf decrypted-bytes {
         type uint64;
         description "Macsec received bytes decrypted";
       }
       leaf validated-packets {
         type uint64;
         description "Macsec received packets validated";
       }
       leaf validated-bytes {
         type uint64;
         description "Macsec received bytes validated";
       }
     }
     list macsec-error-information {
       list secure-channel-sent-errors {
         leaf untagged-packets {
           type uint64;
           description "Macsec untagged packets";
         }
         leaf toolong-packets {
           type uint64;
           description "Macsec too long packets transmitted on a secure channel";
         }
       }
       list secure-channel-received-errors {
         leaf control-packets {
           type uint64;
           description "Macsec control packets received on a secure channel";
         }
         leaf tagged-miss-packets {
           type uint64;
           description "Macsec tagged miss packets received on a secure channel";
         }
         leaf untagged-hit-packets {
           type uint64;
           description "Macsec untagged hit packets received on a secure channel";
         }
         leaf untagged-packets {
           type uint64;
           description "Macsec untagged packets";
         }
         leaf notag-packets {
           type uint64;
           description "Macsec no tag packets received on a secure channel";
         }
         leaf badtag-packets {
           type uint64;
           description "Macsec bad tag packets received on a secure channel";
         }
         leaf unknown-sci-packets {
           type uint64;
           description "Macsec unknown sci packets received on a secure channel";
         }
         leaf no-sci-packets {
           type uint64;
           description "Macsec no sci packets received on a secure channel";
         }
         leaf control-pass-packets {
           type uint64;
           description "Macsec allowed control packets received on a secure channel";
         }
         leaf control-fail-packets {
           type uint64;
           description "Macsec dropped control packets received on a secure channel";
         }
         leaf uncontrol-pass-packets {
           type uint64;
           description "Macsec allowed uncontrol packets received on a secure channel";
         }
         leaf uncontrol-fail-packets {
           type uint64;
           description "Macsec dropped uncontrol packets received on a secure channel";
         }
       }
       list secure-channel-received-extended {
         leaf hit-dropped-packets {
           type uint64;
           description "Macsec hit dropped packets received on a security channel";
         }
         leaf invalid-packets {
           type uint64;
           description "Macsec invalid packets accepted on a security channel";
         }
         leaf late-packets {
           type uint64;
           description "Macsec late packets dropped on a security channel";
         }
         leaf delayed-packets {
           type uint64;
           description "Macsec delayed packets accepted on a security channel";
         }
         leaf unchecked-packets {
           type uint64;
           description "Macsec unchecked packets accepted on a security channel";
         }
         leaf notvalid-packets {
           type uint64;
           description "Macsec not valid packets dropped on a security channel";
         }
         leaf notusing-sa-packets {
           type uint64;
           description "Macsec not using sa packets received on a security channel";
         }
         leaf unused-sa-packets {
           type uint64;
           description "Macsec unused sa packets received on a security channel";
         }
         leaf untagged-hit-packets {
           type uint64;
           description "Macsec untagged hit packets received on a secure channel";
         }
       }
     }
   }
   grouping macsec-crypto-algorithms-block {
     leaf fips-validated-algorithms {
       type string;
       description "Fips validated algorithms used by MACsec module";
     }
   }
   grouping macsec-crypto-version-block {
     leaf crypto-version {
       type string;
       description "Version of crypto library used by MACsec module";
     }
   }
 }
