module junos-genstate-commit-information {
   namespace "http://yang.juniper.net/junos/genstate/commit-information";
   prefix jgci;

   import junos-genstate {
     prefix jgs;
     revision-date 2024-01-01;
   }

   import junos-common-types {
     prefix jt;
     revision-date 2024-01-01;
   }

   organization
     "Juniper Networks, Inc.";

   contact
     "Juniper Networks, Inc.

      1133 Innovation Way
      Sunnyvale, CA

      +1 888 314-5822

      E-mail: yang-support@juniper.net";

   description "Junos genstate data model for commit-information";

   revision 2024-01-01 {
     description "Junos: 24.2R1.18-EVO";
   }

   grouping commit-information-top {
     description "Top-level grouping";
     container commit-information {
       config false;
       description "Top-level container";
       container pending-commit {
         leaf user {
           type string;
           description "User name executing this script";
         }
         leaf client {
           type string;
           description "This client application performed the commit";
         }
         leaf date-time {
           type string;
         }
         leaf log {
           type string;
           description "Log message for this commit";
         }
       }
       container prepared-commit {
         leaf user {
           type string;
           description "User name executing this script";
         }
         leaf client {
           type string;
           description "This client application performed the commit";
         }
         leaf log {
           type string;
           description "Log message for this commit";
         }
       }
       list commit-history {
         leaf sequence-number {
           type int32;
           description "Commit sequence number, 0 being the most recent";
         }
         leaf date-time {
           type string;
         }
         leaf user {
           type string;
           description "User name executing this script";
         }
         leaf client {
           type string;
           description "This client application performed the commit";
         }
         leaf comment {
           type string;
         }
         leaf configuration-revision {
           type string;
           description "Configuration revision information";
         }
         leaf log {
           type string;
           description "Log message for this commit";
         }
         leaf commit-confirmed {
           type string;
           description "Commit confirmed rollback state";
         }
       }
       container rescue-configuration {
         leaf date-time {
           type string;
         }
         leaf user {
           type string;
           description "User name executing this script";
         }
         leaf client {
           type string;
           description "This client application performed the commit";
         }
         leaf comment {
           type string;
         }
         leaf log {
           type string;
           description "Log message for this commit";
         }
       }
     }
   }
   augment "/jgs:genstate" {
     description "Adds commit-information to top-level genstate";
     uses commit-information-top;
   }
 }
