/*
 * Copyright (c) 2024 Juniper Networks, Inc.
 * All rights reserved.
 */
 module junos-conf-services {
   namespace "http://yang.juniper.net/junos/conf/services";

   prefix jc-services;

   import junos-common-types {
     prefix jt;
     revision-date 2024-01-01;
   }

   import junos-conf-root {
     prefix jc;
     revision-date 2024-01-01;
   }

   organization "Juniper Networks, Inc.";

   contact "yang-support@juniper.net";

   description "Junos services configuration module";

   revision 2024-01-01 {
     description "Junos: 24.2R1.18-EVO";
   }

   augment /jc:configuration {
     uses services-group;
   }
   augment /jc:configuration/jc:groups {
     uses services-group;
   }
   grouping services-group {
     container services {
       description "System services";
       uses apply-advanced;
       container jinsightd {
         presence "enable jinsightd";
         description "Health Monitoring services";
         uses apply-advanced;
         container traceoptions {
           description "Jinsight trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             description "Tracing parameters";
             leaf name {
               type enumeration {
                 enum "all" {
                   description "Trace all events";
                 }
                 enum "rule-engine" {
                   description "Log configuration rule engine";
                 }
                 enum "core" {
                   description "Trace core message events";
                 }
                 enum "database" {
                   description "Trace database events";
                 }
                 enum "timer" {
                   description "Trace timer events";
                 }
               }
             }
           }
         }
         container subscribe {
           presence "enable subscribe";
           description "Subscription";
           uses apply-advanced;
           leaf health-monitor {
             description "Health-monitor parameters";
             type empty;
           }
         }
       }
       container fixed-wireless-access {
         description "Configuration for fixed wireless access service";
         uses apply-advanced;
         list control-plane {
           key name;
           ordered-by user;
           description "S11 configuration";
           max-elements 16;
           leaf name {
             description "S11 connection name";
             type string {
               length "1 .. 63";
             }
           }
           uses apply-advanced;
           container s11 {
             description "S11 IP address";
             uses apply-advanced;
             leaf v4-address {
               description "IPv4 address configured on interface";
               type jt:ipv4addr;
             }
             leaf path-management {
               description "Enable/disable path management";
               default "enable";
               type enumeration {
                 enum "enable" {
                   description "Enable parameter";
                 }
                 enum "disable" {
                   description "Disable parameter";
                 }
               }
             }
           }
         }
         list apn {
           key name;
           ordered-by user;
           description "Configure access point names for fixed wireless connections";
           leaf name {
             description "Access point name";
             type string {
             }
           }
           uses apply-advanced;
           leaf description {
             description "Text description of APN";
             type string {
             }
           }
           leaf apn-data-type {
             description "Specify APN data type";
             default "ipv4";
             type enumeration {
               enum "ipv4" {
                 description "IPv4 Data type";
               }
             }
           }
           leaf aaa-profile {
             description "Specify AAA profile for Authorization and Accounting";
             type string {
               length "1 .. 80";
             }
           }
           leaf dynamic-profile {
             description "Dynamic profile for the apn";
             type string {
               length "1 .. 80";
             }
           }
           leaf ipv4-address-pool {
             description "IPv4 address pool for the apn";
             type string {
               length "1 .. 80";
             }
           }
           leaf routing-instance {
             description "Routing instance used for redirect";
             type union {
               type string {
                 pattern "default";
               }
               type string {
               }
             }
           }
           container authentication {
             description "FWA tunnel authentication";
             uses fwa-authentication-type;
           }
         }
         list data-plane {
           key name;
           ordered-by user;
           description "S1-U configuration";
           max-elements 1;
           leaf name {
             description "S1-U connection name";
             type string {
               length "1 .. 63";
             }
           }
           uses apply-advanced;
           container s1-u {
             description "S1-U IP address";
             uses apply-advanced;
             leaf v4-address {
               description "IPv4 address configured on interface";
               type jt:ipv4addr;
             }
           }
         }
         leaf-list anchor-point {
           ordered-by user;
           description "Interface used for GTP-U tunnel termination";
           type string {
             length "1 .. 64";
           }
         }
         container traceoptions {
           description "Fixed wirelss access service trace options";
           uses bbefwa-trace-options-type;
         }
       }
       container captive-portal-content-delivery {
         description "Configuration for captive portal and content delivery service";
         uses apply-advanced;
         leaf auto-deactivate {
           description "Deactivate content delivery service";
           type string;
         }
         list rule {
           key name;
           ordered-by user;
           description "Define a captive portal content delivery rule";
           uses cpcd-rule-object-type;
         }
         list rule-set {
           key name;
           ordered-by user;
           description "Define a set of captive portal content delivery rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list profile {
           key name;
           ordered-by user;
           description "One or more rule/rule set in the profile";
           leaf name {
             description "Profile name";
             type string {
               length "1 .. 63";
             }
           }
           uses apply-advanced;
           choice cpcd_rules_choice {
             case case_1 {
               leaf dynamic {
                 description "Dynamic profile flag";
                 type empty;
               }
             }
             case case_2 {
               list cpcd-rules {
                 key name;
                 ordered-by user;
                 description "List of captive portal content delivery rules";
                 leaf name {
                   type string {
                     length "1 .. 63";
                   }
                 }
                 uses apply-advanced;
               }
             }
             case case_3 {
               list cpcd-rule-sets {
                 key name;
                 ordered-by user;
                 description "List of captive portal content delivery rule sets";
                 leaf name {
                   type string {
                     length "1 .. 63";
                   }
                 }
                 uses apply-advanced;
               }
             }
           }
           container ipda-rewrite-options {
             description "Ipda rewrite options";
             uses apply-advanced;
             leaf destination-address {
               description "Default ipda rewrite IP address";
               type jt:ipaddr;
             }
             leaf destination-port {
               description "Default ipda rewrite port";
               type union {
                 type string {
                   pattern "<.*>|$.*";
                 }
                 type uint16 {
                   range "1 .. 65535";
                 }
               }
             }
           }
           container http-redirect-options {
             description "Http redirect options";
             uses apply-advanced;
             leaf url {
               description "URL of the captive portal file";
               type string {
               }
             }
           }
           leaf auto-deactivate {
             description "Deactivate content delivery service";
             type enumeration {
               enum "never" {
                 description "Deactivate never";
               }
               enum "initial-get" {
                 description "Deactivate on initial http-get";
               }
             }
           }
         }
         container traceoptions {
           description "Captive portal and content delivery trace options";
           uses cpcd-trace-options-type;
         }
       }
       container dynamic-flow-capture {
         description "Configure Dynamic Flow Capture parameters";
         uses apply-advanced;
         leaf g-max-duplicates {
           description "Maximum content destinations for the capture group";
           default "3";
           type union {
             type string {
               pattern "<.*>|$.*";
             }
             type uint32 {
               range "1 .. 64";
             }
           }
         }
         leaf g-duplicates-dropped-periodicity {
           description "Periodicity of DuplicatesDropped notification in secs";
           default "30";
           type union {
             type string {
               pattern "<.*>|$.*";
             }
             type uint32 {
               range "1 .. 255";
             }
           }
         }
         list capture-group {
           key name;
           ordered-by user;
           description "Configure DFC group parameters";
           max-elements 16;
           uses dfc_group_type;
         }
         container traceoptions {
           presence "enable traceoptions";
           description "Trace options for dynamic-flow-capture service";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
       }
       container flow-tap {
         description "Configure flow-tap parameters";
         uses apply-advanced;
         container family {
           description "Address family of packets to tap";
           uses apply-advanced;
           leaf inet {
             description "IPv4 family";
             type empty;
           }
           leaf inet6 {
             description "IPv4 family";
             type empty;
           }
           leaf ccc {
             description "CCC family";
             type empty;
           }
         }
         leaf interface {
           description "Service interface on which to configure flow-tap service";
           type union {
             type jt:interface-name;
             type string {
               pattern "<.*>|$.*";
             }
           }
         }
         leaf tunnel-interface {
           description "Tunnel interface through which flow-tap would communicate with MD";
           type union {
             type jt:interface-name;
             type string {
               pattern "<.*>|$.*";
             }
           }
         }
       }
       container radius-flow-tap {
         description "Configure radius triggered flow-tap parameters";
         uses apply-advanced;
         leaf forwarding-class {
           description "Forwarding class assigned to intercepted packets";
           type string {
           }
         }
         leaf source-ipv4-address {
           description "IP Address to use as source address in IPv4 header appended to intercepted packets";
           type jt:ipv4addr;
         }
         leaf multicast-interception {
           description "Enable Multicast Tapping";
           type empty;
         }
         container interfaces {
           description "Tunnel Interfaces";
           uses apply-advanced;
           list tunnel-interface {
             key name;
             uses tunnel_interface_type;
           }
         }
         choice ri_or_ls {
           case case_1 {
             leaf routing-instance {
               description "Routing instance to be used for radius flow tap";
               type string;
             }
           }
           case case_2 {
             list logical-system {
               key name;
               ordered-by user;
               description "Logical system to be used for radius flow tap";
               max-elements 1;
               leaf name {
                 description "Logical system name";
                 type string;
               }
               uses apply-advanced;
               leaf routing-instance {
                 description "Routing instance to be used for radius flow tap";
                 type string;
               }
             }
           }
         }
         list policy {
           key name;
           ordered-by user;
           description "Policy";
           leaf name {
             description "Policy Name";
             type string {
             }
           }
           uses apply-advanced;
           container inet {
             description "Protocol family IPv4 drop policy terms";
             uses apply-advanced;
             list drop-policy {
               key name;
               ordered-by user;
               description "Define an IPv4 drop policy";
               uses drop-policy-term;
             }
           }
           container inet6 {
             description "Protocol family IPv6 drop policy terms";
             uses apply-advanced;
             list drop-policy {
               key name;
               ordered-by user;
               description "Define an IPv6 drop policy";
               uses drop-policy6-term;
             }
           }
         }
         container snmp {
           description "SNMP options for radius flow tap";
           uses apply-advanced;
           list notify-targets {
             key name;
             ordered-by user;
             description "Target list for packet mirror SNMP notifications";
             leaf name {
               description "Target IP address";
               type jt:ipaddr;
             }
             uses apply-advanced;
           }
         }
       }
       container mobile-flow-tap {
         description "Configure mobile triggered flow-tap parameters";
         uses apply-advanced;
         container source-interface {
           presence "enable source-interface";
           description "Source interface from which IRI packets will be sent";
           leaf interface-name {
             description "Interface name";
             type union {
               type jt:interface-name;
               type string {
                 pattern "<.*>|$.*";
               }
             }
           }
           leaf ipv4-address {
             description "Source IPv4 address to be used";
             type jt:ipv4addr;
           }
         }
       }
       container flow-monitoring {
         presence "enable flow-monitoring";
         description "Configure flow monitoring";
         uses apply-advanced;
         container version9 {
           description "Version 9 configuration";
           uses apply-advanced;
           list template {
             key name;
             ordered-by user;
             description "One or more version 9 templates";
             max-elements 10;
             uses version9-template;
           }
         }
         container version-ipfix {
           description "Version IP-Fix configuration";
           uses apply-advanced;
           list template {
             key name;
             ordered-by user;
             description "One or more version ip-fix templates";
             max-elements 10;
             uses version-ipfix-template;
           }
         }
       }
       container jdaf {
         description "Juniper distributed application framework (JDAF)";
         uses apply-advanced;
         leaf-list routing-instances {
           ordered-by user;
           description "List of routing-instance name for JDAF clients";
           type string {
             length "1 .. 128";
           }
         }
       }
       container inline-monitoring {
         presence "enable inline-monitoring";
         description "Inline packet monitoring service";
         uses apply-advanced;
         container traceoptions {
           description "Trace options for IMOND";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         list counter-profile {
           key name;
           ordered-by user;
           description "Custom counter profiles for Inline packet monitoring";
           max-elements 8;
           leaf name {
             description "Name of counter-profile";
             type string {
               length "1 .. 32";
             }
           }
           uses apply-advanced;
           list counter {
             key name;
             ordered-by user;
             description "Inline monitoring counter";
             max-elements 6;
             leaf name {
               description "Name of counter";
               type string {
                 length "1 .. 32";
               }
             }
             uses apply-advanced;
             leaf max-value {
               description "Non-overlapping min/max range for counter-type, not exceeding packet contruct";
               type union {
                 type string {
                   pattern "<.*>|$.*";
                 }
                 type uint32 {
                   range "0 .. 65535";
                 }
               }
             }
             leaf min-value {
               description "Non-overlapping min/max range for counter-type, not exceeding packet contruct";
               type union {
                 type string {
                   pattern "<.*>|$.*";
                 }
                 type uint32 {
                   range "0 .. 65535";
                 }
               }
             }
             leaf counter-type {
               description "Counter type";
               type enumeration {
                 enum "packet-range" {
                   description "Packet range 64-9000 bytes";
                 }
                 enum "ttl-range" {
                   description "TTL range 0-255";
                 }
                 enum "tcp-window-range" {
                   description "TCP window range 0-65535";
                 }
                 enum "dos-attack" {
                   description "DoS attack counter, min/max is not required";
                 }
               }
             }
           }
         }
         list feature-profile {
           key name;
           ordered-by user;
           description "Feature profile for Inline packet monitoring";
           max-elements 1;
           leaf name {
             description "Name of feature-profile";
             type string {
               length "1 .. 32";
             }
           }
           uses apply-advanced;
           leaf-list features {
             ordered-by user;
             description "Features list";
             type enumeration {
               enum "inter-arrival-time" {
                 description "Inter arrival time";
               }
               enum "inter-departure-time" {
                 description "Inter departure time";
               }
               enum "chip-delay" {
                 description "Chip delay";
               }
               enum "shared-pool-congestion" {
                 description "Shared pool congestion level";
               }
               enum "queue-congestion-level" {
                 description "Queue congestion level";
               }
               enum "ingress-drop-reason" {
                 description "Ingress drop reason";
               }
               enum "egress-drop-reason" {
                 description "Egress drop reason";
               }
               enum "aggregate-intf-member-id" {
                 description "Aggregate interface member id";
               }
               enum "flow-start-end-time" {
                 description "Flow start and end time";
               }
               enum "security-enable" {
                 description "Enable DOS attack detection on monitored flows";
               }
             }
           }
         }
         list template {
           key name;
           ordered-by user;
           description "Templates for Inline packet monitoring";
           max-elements 16;
           leaf name {
             description "Name of template";
             type string {
               length "1 .. 32";
             }
           }
           uses apply-advanced;
           leaf template-refresh-rate {
             description "Refresh rate in seconds";
             default "600";
             type union {
               type string {
                 pattern "<.*>|$.*";
               }
               type uint16 {
                 range "10 .. 600";
               }
             }
           }
           leaf option-template-refresh-rate {
             description "Option refresh rate in seconds";
             default "600";
             type union {
               type string {
                 pattern "<.*>|$.*";
               }
               type uint16 {
                 range "10 .. 600";
               }
             }
           }
           leaf observation-domain-id {
             description "Observation domain ID";
             default "0";
             type union {
               type string {
                 pattern "<.*>|$.*";
               }
               type uint8 {
                 range "0 .. 255";
               }
             }
           }
           leaf template-id {
             description "Template ID";
             type union {
               type string {
                 pattern "<.*>|$.*";
               }
               type uint16;
             }
           }
           leaf option-template-id {
             description "Option template ID";
             type union {
               type string {
                 pattern "<.*>|$.*";
               }
               type uint16 {
                 range "1024 .. 65535";
               }
             }
           }
           leaf flow-active-timeout {
             description "Interval after which active flow is exported in seconds";
             default "60";
             type union {
               type string {
                 pattern "<.*>|$.*";
               }
               type uint16 {
                 range "10 .. 600";
               }
             }
           }
           leaf flow-inactive-timeout {
             description "Period of inactivity that marks a flow inactive in seconds";
             default "60";
             type union {
               type string {
                 pattern "<.*>|$.*";
               }
               type uint16 {
                 range "10 .. 600";
               }
             }
           }
           leaf template-type {
             description "Template IP version";
             default "ipv4-template";
             type enumeration {
               enum "ipv4-template" {
                 description "IPv4 template configuration";
               }
               enum "ipv6-template" {
                 description "IPv6 template configuration";
               }
             }
           }
           container flow-monitoring {
             presence "enable flow-monitoring";
             uses apply-advanced;
             leaf sampling-profile {
               description "Supported sampling profiles";
               type enumeration {
                 enum "first-N-Packets" {
                   description "Initial first 'N' packet samples are exported to collector";
                 }
                 enum "deterministic" {
                   description "Deterministically 'N'th packet is sampled";
                 }
                 enum "random" {
                   description "Random packets are sampled and exported";
                 }
                 enum "combo-1" {
                   description "Initial first 'N' packets followed by random packet sampling";
                 }
                 enum "combo-2" {
                   description "Initial first 'N' packets followed by deterministic sampling";
                 }
               }
             }
             leaf packet-count {
               description "Packet count for first-N-Packets/combo-1/combo-2 sampling profiles";
               default "10";
               type union {
                 type string {
                   pattern "<.*>|$.*";
                 }
                 type uint16 {
                   range "1 .. 1023";
                 }
               }
             }
             leaf sampling-rate {
               description "Sampling rate";
               default "10000";
               type union {
                 type string {
                   pattern "<.*>|$.*";
                 }
                 type uint32 {
                   range "1 .. 65535";
                 }
               }
             }
             leaf security-enable {
               description "Enable DOS attack detection on monitored flows";
               type empty;
             }
             leaf flow-rate {
               description "Flow meter rate in kbps";
               type union {
                 type string {
                   pattern "<.*>|$.*";
                 }
                 type uint32 {
                   range "8 .. 10000000";
                 }
               }
             }
             leaf burst-size {
               description "Burst size in bytes";
               type union {
                 type string {
                   pattern "<.*>|$.*";
                 }
                 type uint32 {
                   range "512 .. 256000000";
                 }
               }
             }
             leaf flow-limit {
               description "Maximum number of flows allowed";
               default "32000";
               type union {
                 type string {
                   pattern "<.*>|$.*";
                 }
                 type uint16;
               }
             }
             leaf counter-profile {
               description "Counter profiles per-flow-4-counters, per-flow-6-counters or custom profile";
               type string {
                 length "1 .. 32";
               }
             }
             leaf feature-profile {
               description "Feature profile";
               type string {
                 length "1 .. 32";
               }
             }
           }
           list primary-data-record-fields {
             key name;
             ordered-by user;
             description "Primary data record fields";
             leaf name {
               description "IPFIX Information Elements";
               type enumeration {
                 enum "datalink-frame-size" {
                   description "Datalink Frame Size";
                 }
                 enum "direction" {
                   description "Direction";
                 }
                 enum "egress-interface-snmp-id" {
                   description "Egress Interface SNMP ID";
                 }
                 enum "ingress-interface-snmp-id" {
                   description "Ingress Interface SNMP ID";
                 }
                 enum "cpid-ingress-interface-index" {
                   description "CPID Ingress Interface Index";
                 }
                 enum "cpid-underlying-ingress-interface-index" {
                   description "CPID Underlying Ingress Interface Index";
                 }
                 enum "cpid-egress-interface-index" {
                   description "CPID Egress Interface Index";
                 }
                 enum "cpid-forwarding-nexthop-id" {
                   description "CPID Forwarding Nexthop Id";
                 }
                 enum "cpid-forwarding-exception-code" {
                   description "CPID Forwarding Exception Code";
                 }
                 enum "cpid-forwarding-class-drop-priority" {
                   description "CPID Forwarding Class Drop Priority";
                 }
               }
             }
           }
         }
         list instance {
           key name;
           ordered-by user;
           description "Inline monitoring instance";
           max-elements 7;
           leaf name {
             description "Name of instance";
             type string {
               length "1 .. 32";
             }
           }
           uses apply-advanced;
           leaf template-name {
             description "Template Name";
             type string {
               length "1 .. 32";
             }
           }
           leaf maximum-clip-length {
             description "Maximum packet length";
             type union {
               type string {
                 pattern "<.*>|$.*";
               }
               type uint16 {
                 range "64 .. 256";
               }
             }
           }
           leaf controller {
             description "Controller type";
             type enumeration {
               enum "p4" {
                 description "Controller P4";
               }
               enum "re" {
                 description "Send packet to RE";
               }
             }
           }
           leaf export-by-asic {
             description "Export IPFIX packets via ASIC";
             type empty;
           }
           leaf sampling-rate {
             description "Sampling rate";
             type union {
               type string {
                 pattern "<.*>|$.*";
               }
               type uint32 {
                 range "1 .. 32000000";
               }
             }
           }
           list collector {
             key name;
             ordered-by user;
             description "Inline monitoring collector";
             max-elements 4;
             leaf name {
               description "Name of collector";
               type string {
                 length "1 .. 32";
               }
             }
             uses apply-advanced;
             leaf source-address {
               description "Source address";
               type jt:ipaddr;
             }
             leaf destination-address {
               description "Destination address";
               type jt:ipaddr;
             }
             leaf dscp {
               description "DSCP Value";
               default "0";
               type union {
                 type string {
                   pattern "<.*>|$.*";
                 }
                 type uint8 {
                   range "0 .. 63";
                 }
               }
             }
             leaf destination-port {
               description "Destination port value";
               type union {
                 type string {
                   pattern "<.*>|$.*";
                 }
                 type uint16 {
                   range "1 .. 65535";
                 }
               }
             }
             leaf forwarding-class {
               description "Forwarding class for exported frames";
               type string {
                 length "1 .. 64";
               }
             }
             leaf sampling-rate {
               description "Sampling rate";
               type union {
                 type string {
                   pattern "<.*>|$.*";
                 }
                 type uint32 {
                   range "1 .. 16000000";
                 }
               }
             }
             leaf routing-instance {
               description "Name of routing instance";
               type string;
             }
           }
         }
         leaf observation-cloud-id {
           description "Observation cloud ID";
           type union {
             type string {
               pattern "<.*>|$.*";
             }
             type uint8 {
               range "1 .. 255";
             }
           }
         }
         leaf flow-export-timer {
           description "Flow export timer";
           default "10";
           units "seconds";
           type union {
             type string {
               pattern "<.*>|$.*";
             }
             type uint16 {
               range "1 .. 600";
             }
           }
         }
       }
       container app-engine {
         description "App-engine";
         uses apply-advanced;
         container security {
           presence "enable security";
           description "Enable app-engine security";
         }
         container monitor-cpu {
           description "Monitor node CPU usage";
           uses monitor-threshold;
         }
         container monitor-memory {
           description "Monitor node memory usage";
           uses monitor-threshold;
         }
         container monitor-storage {
           description "Monitor storage usage";
           uses monitor-threshold;
         }
         leaf default-compute-node-package {
           description "Default JunosV App Engine package for appliance";
           type string;
         }
         list compute-cluster {
           key name;
           ordered-by user;
           description "Configure compute cluster";
           leaf name {
             description "Compute cluster name";
             type string {
               length "1 .. 15";
             }
           }
           uses apply-advanced;
           container local-management {
             description "Management address connected to compute cluster";
             uses apply-advanced;
             list routing-instance {
               key routing-instance-name;
               ordered-by user;
               description "Packets are restriction to specified routing instance";
               max-elements 1;
               leaf routing-instance-name {
                 description "Name of routing instance";
                 type string {
                 }
               }
               uses apply-advanced;
               container family {
                 description "Protocol family";
                 container inet {
                   description "IPv4 parameters";
                   uses apply-advanced;
                   leaf address {
                     description "Interface address";
                     type jt:ipv4addr;
                   }
                 }
               }
             }
             container family {
               description "Protocol family";
               container inet {
                 description "IPv4 parameters";
                 uses apply-advanced;
                 leaf address {
                   description "Interface address";
                   type jt:ipv4addr;
                 }
               }
             }
           }
           container monitor-cpu {
             description "Monitor node CPU usage";
             uses monitor-threshold;
           }
           container monitor-memory {
             description "Monitor node memory usage";
             uses monitor-threshold;
           }
           container monitor-storage {
             description "Monitor storage usage";
             uses monitor-threshold;
           }
           list compute-node {
             key name;
             ordered-by user;
             description "Compute node name";
             max-elements 1;
             leaf name {
               description "Compute node name";
               type string {
                 length "1 .. 15";
               }
             }
             uses apply-advanced;
             container monitor-cpu {
               description "Monitor node CPU usage";
               uses monitor-threshold;
             }
             container monitor-memory {
               description "Monitor node memory usage";
               uses monitor-threshold;
             }
             container monitor-storage {
               description "Monitor storage usage";
               uses monitor-threshold;
             }
             choice compute-node-identifier {
               case case_1 {
                 leaf mac-address {
                   description "MAC address of the network boot interface";
                   type jt:mac-addr;
                 }
               }
               case case_2 {
                 leaf fpc {
                   description "FPC slot number";
                   type union {
                     type string {
                       pattern "<.*>|$.*";
                     }
                     type uint32;
                   }
                 }
               }
               case case_3 {
                 leaf hypervisor {
                   description "Compute node is hypervisor";
                   type empty;
                 }
               }
             }
             leaf package {
               description "JunosV App Engine package";
               type string;
             }
             container routing-options {
               description "Route configuration for compute node";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             container interfaces {
               description "Network interfaces configuration";
               uses apply-advanced;
               list ethernet {
                 key name;
                 ordered-by user;
                 description "Interface configuration";
                 leaf name {
                   description "Interface name";
                   type string {
                     length "1 .. 15";
                   }
                 }
                 uses apply-advanced;
                 leaf management {
                   description "Use this as management interface";
                   type empty;
                 }
                 container family {
                   description "Protocol family";
                   uses family;
                 }
                 leaf enable-passthrough {
                   description "Enable passthrough on this interface";
                   type empty;
                 }
                 leaf mtu {
                   description "Maximum transmit packet size";
                   type union {
                     type string {
                       pattern "<.*>|$.*";
                     }
                     type uint16 {
                       range "256 .. 9192";
                     }
                   }
                 }
                 container ether-options {
                   uses apply-advanced;
                   choice agg-intf {
                     case case_1 {
                       leaf ieee-802-3ad {
                         description "Aggregated interface name";
                         type string {
                           length "1 .. 15";
                         }
                       }
                     }
                   }
                 }
               }
               list bridge {
                 key name;
                 ordered-by user;
                 description "Bridge configuration";
                 leaf name {
                   description "Bridge name";
                   type string {
                     length "1 .. 15";
                   }
                 }
                 uses apply-advanced;
                 leaf management {
                   description "Use this as management bridge";
                   type empty;
                 }
                 container family {
                   description "Protocol family";
                   uses family;
                 }
                 leaf-list interface {
                   ordered-by user;
                   description "Bridge interface list";
                   type string {
                     length "1 .. 15";
                   }
                   max-elements 4;
                 }
                 leaf mtu {
                   description "Maximum transmit packet size";
                   type union {
                     type string {
                       pattern "<.*>|$.*";
                     }
                     type uint16 {
                       range "256 .. 9192";
                     }
                   }
                 }
               }
               list aggregate {
                 key name;
                 ordered-by user;
                 description "Aggregate interface configuration";
                 leaf name {
                   description "Aggregated interface name";
                   type string {
                     length "1 .. 15";
                   }
                 }
                 uses apply-advanced;
                 leaf management {
                   description "Use this as management aggregate";
                   type empty;
                 }
                 container family {
                   description "Protocol family";
                   uses family;
                 }
                 leaf mtu {
                   description "Maximum transmit packet size";
                   type union {
                     type string {
                       pattern "<.*>|$.*";
                     }
                     type uint16 {
                       range "256 .. 9192";
                     }
                   }
                 }
                 container aggregated-ether-options {
                   presence "enable aggregated-ether-options";
                   description "Link aggregation parameters";
                   uses apply-advanced;
                   leaf hash-policy {
                     default "layer-3-and-4";
                     type enumeration {
                       enum "layer-2" {
                         description "Uses mac address of both source and destination for hashing";
                       }
                       enum "layer-3-and-4" {
                         description "Uses port number and IP address of both source and destination for hashing";
                       }
                       enum "layer-2-and-3" {
                         description "Uses mac and IP address of both source and destination for hashing";
                       }
                     }
                   }
                   leaf miimon {
                     description "Link monitoring interval in milli-second";
                     type union {
                       type uint32;
                       type string {
                         pattern "<.*>|$.*";
                       }
                     }
                   }
                 }
               }
             }
             list syslog {
               key name;
               ordered-by user;
               description "System logging facility";
               leaf name {
                 description "Facility type";
                 type enumeration {
                   enum "any" {
                     description "All facilities";
                   }
                   enum "authorization" {
                     description "Authorization system";
                   }
                   enum "privileged" {
                     description "Privileged authorization events";
                   }
                   enum "cron" {
                     description "Cron daemon";
                   }
                   enum "daemon" {
                     description "Various system processes";
                   }
                   enum "kernel" {
                     description "Kernel";
                   }
                   enum "syslog" {
                     description "Syslog messages";
                   }
                   enum "user" {
                     description "User processes";
                   }
                   enum "uucp" {
                     description "UUCP system";
                   }
                   enum "local0" {
                     description "Local 0 messages";
                   }
                   enum "local1" {
                     description "Local 1 messages";
                   }
                   enum "local2" {
                     description "Local 2 messages";
                   }
                   enum "local3" {
                     description "Local 3 messages";
                   }
                   enum "local4" {
                     description "Local 4 messages";
                   }
                   enum "local5" {
                     description "Local 5 messages";
                   }
                   enum "local6" {
                     description "Local 6 messages";
                   }
                   enum "local7" {
                     description "Local 7 messages";
                   }
                 }
               }
               choice level {
                 case case_1 {
                   leaf any {
                     description "All levels";
                     type empty;
                   }
                 }
                 case case_2 {
                   leaf emergency {
                     description "Panic conditions";
                     type empty;
                   }
                 }
                 case case_3 {
                   leaf alert {
                     description "Conditions that should be corrected immediately";
                     type empty;
                   }
                 }
                 case case_4 {
                   leaf critical {
                     description "Critical conditions";
                     type empty;
                   }
                 }
                 case case_5 {
                   leaf error {
                     description "Error conditions";
                     type empty;
                   }
                 }
                 case case_6 {
                   leaf warning {
                     description "Warning messages";
                     type empty;
                   }
                 }
                 case case_7 {
                   leaf notice {
                     description "Conditions that should be handled specially";
                     type empty;
                   }
                 }
                 case case_8 {
                   leaf info {
                     description "Informational messages";
                     type empty;
                   }
                 }
                 case case_9 {
                   leaf debug {
                     description "Debug messages";
                     type empty;
                   }
                 }
               }
             }
           }
         }
         container virtual-machines {
           description "Virtual-machine management";
           uses apply-advanced;
           list instance {
             key name;
             ordered-by user;
             description "Virtual-machine instance";
             leaf name {
               description "Virtual-machine instance identifier";
               type string {
                 length "1 .. 39";
               }
             }
             uses apply-advanced;
             leaf cpu {
               description "Units of CPUs (default 1 cpu)";
               default "1";
               type union {
                 type string {
                   pattern "<.*>|$.*";
                 }
                 type uint32 {
                   range "1 .. 16";
                 }
               }
             }
             leaf memory {
               description "Memory for the virtual-machine (default 1 gigabytes)";
               default "1";
               units "gigabytes";
               type union {
                 type string {
                   pattern "<.*>|$.*";
                 }
                 type uint32 {
                   range "1 .. 32";
                 }
               }
             }
             leaf package {
               description "Virtual-machine package";
               type string {
                 length "1 .. 120";
               }
             }
             container local-management {
               description "Management address connected to virtual machine";
               uses apply-advanced;
               list routing-instance {
                 key routing-instance-name;
                 ordered-by user;
                 description "Packets are restriction to specified routing instance";
                 max-elements 1;
                 leaf routing-instance-name {
                   description "Name of routing instance";
                   type string {
                   }
                 }
                 uses apply-advanced;
                 container family {
                   description "Protocol family";
                   container inet {
                     description "IPv4 parameters";
                     uses apply-advanced;
                     leaf address {
                       description "Interface address";
                       type jt:ipv4addr;
                     }
                   }
                 }
               }
               container family {
                 description "Protocol family";
                 container inet {
                   description "IPv4 parameters";
                   uses apply-advanced;
                   leaf address {
                     description "Interface address";
                     type jt:ipv4addr;
                   }
                 }
               }
             }
             list compute-cluster {
               key name;
               ordered-by user;
               description "Compute cluster on which the virtual-machine runs";
               max-elements 1;
               leaf name {
                 description "Compute cluster name";
                 type string {
                   length "1 .. 15";
                 }
               }
               uses apply-advanced;
               leaf compute-node {
                 description "Compute node on which the virtual-machine runs";
                 type string {
                   length "1 .. 15";
                 }
               }
             }
             list interface {
               key name;
               ordered-by user;
               description "Virtual-machine interface configuration";
               leaf name {
                 description "Virtual-machine interface name";
                 type string {
                   length "1 .. 31";
                 }
               }
               uses apply-advanced;
               leaf hw-model {
                 description "Interface hardware model";
                 default "e1000g";
                 type enumeration {
                   enum "e1000g" {
                     description "Gigabit Ethernet e1000g driver";
                   }
                   enum "virtio" {
                     description "Para-virtualizing the interface";
                   }
                 }
               }
               leaf host-interface {
                 description "Passthrough host interface for virtual-machine";
                 type string {
                   length "1 .. 15";
                 }
               }
               leaf bridge {
                 description "Bridge that the interface connected to";
                 type string {
                   length "1 .. 15";
                 }
               }
               leaf mtu {
                 description "Maximum transmit packet size";
                 type union {
                   type string {
                     pattern "<.*>|$.*";
                   }
                   type uint16 {
                     range "256 .. 9192";
                   }
                 }
               }
               container family {
                 description "Interface address family";
                 container inet {
                   presence "enable inet";
                   description "IPv4 parameters";
                   uses apply-advanced;
                   list address {
                     key name;
                     ordered-by user;
                     description "Interface address/destination prefix";
                     leaf name {
                       description "Interface address/destination prefix";
                       type jt:ipv4prefix;
                     }
                     uses apply-advanced;
                     leaf primary {
                       description "Primary address on the interface";
                       type empty;
                     }
                   }
                 }
               }
             }
             container routing-options {
               description "Route configuration for virutal machine";
               uses apply-advanced;
               container static {
                 description "Static routes";
                 uses apply-advanced;
                 list route {
                   key name;
                   ordered-by user;
                   description "Static route";
                   leaf name {
                     description "Destination IP address or prefix";
                     type jt:ipv4prefix;
                   }
                   uses apply-advanced;
                   leaf next-hop {
                     description "Next hop to destination";
                     type jt:ipv4addr;
                   }
                 }
               }
               list rib {
                 key name;
                 ordered-by user;
                 description "Routing table options";
                 leaf name {
                   description "Routing table name";
                   type string {
                     length "1 .. 10";
                   }
                 }
                 uses apply-advanced;
                 container static {
                   description "Static routes";
                   uses apply-advanced;
                   list route {
                     key name;
                     ordered-by user;
                     description "Static route";
                     leaf name {
                       description "Destination IP address or prefix";
                       type jt:ipv4prefix;
                     }
                     uses apply-advanced;
                     leaf next-hop {
                       description "Next hop to destination";
                       type jt:ipv4addr;
                     }
                   }
                 }
               }
             }
             list secondary-disk {
               key name;
               ordered-by user;
               description "Virtual-machine disk";
               leaf name {
                 description "Virtual-machine disk name";
                 type enumeration {
                   enum "hdb" {
                     description "Disk name is hdb";
                   }
                   enum "hdc" {
                     description "Disk name is hdc";
                   }
                   enum "hdd" {
                     description "Disk name is hdd";
                   }
                 }
               }
               leaf size {
                 description "Virtual-machine secondary disk size";
                 units "gigabytes";
                 type union {
                   type string {
                     pattern "<.*>|$.*";
                   }
                   type uint32 {
                     range "1 .. 160";
                   }
                 }
               }
             }
           }
         }
       }
       container inband-flow-telemetry {
         presence "enable inband-flow-telemetry";
         description "Inband telemetry services";
         uses apply-advanced;
         container traceoptions {
           presence "enable traceoptions";
           description "Inband telemetry trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         container device-id {
           description "Inband telemetry global unique identifier";
           uses apply-advanced;
           choice device_id_choice {
             case case_1 {
               leaf auto {
                 description "Device router-id will be considered";
                 type empty;
               }
             }
             case case_2 {
               leaf id {
                 description "Specify unique device identifier";
                 type union {
                   type string {
                     pattern "<.*>|$.*";
                   }
                   type uint32 {
                     range "1 .. 1048575";
                   }
                 }
               }
             }
           }
         }
         leaf meta-data-stack-length {
           description "Maximum length for meta data";
           default "240";
           type union {
             type string {
               pattern "<.*>|$.*";
             }
             type uint32 {
               range "8 .. 255";
             }
           }
         }
         leaf hop-limit {
           description "Maximum hop limits allowed";
           default "250";
           type union {
             type string {
               pattern "<.*>|$.*";
             }
             type uint32 {
               range "1 .. 250";
             }
           }
         }
         leaf flow-type {
           description "Configure IFA traffic type";
           type enumeration {
             enum "l3" {
               description "L3 traffic type";
             }
             enum "vxlan" {
               description "Vxlan traffic type";
             }
           }
         }
         leaf no-ipv6-address-match {
           description "Configure if no ipv6 address match is used";
           type empty;
         }
         leaf clock-source {
           description "Configure clock source for timestamping";
           type enumeration {
             enum "ntp" {
               description "Use Network Time Protocol";
             }
             enum "ptp" {
               description "Use Precision Time Protocol";
             }
           }
         }
         list profile {
           key name;
           description "Profile options";
           max-elements 32;
           uses inband-telemetry-profile-type;
         }
       }
       container agf {
         description "Configuration for access gateway function";
         uses apply-advanced;
         leaf node-name {
           description "AGF node name";
           type string {
             length "1 .. 150";
           }
         }
         leaf node-id {
           description "AGF node identifier";
           type union {
             type string {
               pattern "<.*>|$.*";
             }
             type uint32 {
               range "0 .. 255";
             }
           }
         }
         leaf ip-address {
           description "AGF ip address";
           status deprecated;
           type jt:ipv4addr;
         }
         list fiveqi-map {
           key name;
           ordered-by user;
           uses fiveqi;
         }
         container n2-proxy {
           presence "enable n2-proxy";
           description "N2 proxy settings";
           status deprecated;
           uses apply-advanced;
           leaf ip-address {
             description "N2 proxy ip address";
             type jt:ipv4addr;
           }
           leaf port {
             description "N2 proxy port number";
             default "65454";
             type union {
               type string {
                 pattern "<.*>|$.*";
               }
               type uint16 {
                 range "0 .. 65535";
               }
             }
           }
         }
         list plmn {
           key name;
           ordered-by user;
           description "AGF public land mobile network";
           leaf name {
             description "Public land mobile network name";
             type string {
               length "1 .. 80";
             }
           }
           uses apply-advanced;
           leaf mcc {
             description "Mobile country code";
             type string {
             }
           }
           leaf mnc {
             description "Mobile network code";
             type string {
             }
           }
         }
         list tracking-area {
           key name;
           ordered-by user;
           description "Tracking area";
           leaf name {
             description "Tracking area code";
             type union {
               type string {
                 pattern "<.*>|$.*";
               }
               type uint32 {
                 range "0 .. 16777215";
               }
             }
           }
           uses apply-advanced;
           list plmn {
             key name;
             ordered-by user;
             description "Public land mobile network";
             max-elements 1;
             leaf name {
               description "Public land mobile network name";
               type string {
                 length "1 .. 80";
               }
             }
             uses apply-advanced;
             list s-nssai {
               key name;
               ordered-by user;
               description "Single network slice selection assistance information";
               leaf name {
                 description "Single network slice selection assistance information identifier";
                 type union {
                   type string {
                     pattern "<.*>|$.*";
                   }
                   type uint16 {
                     range "0 .. 128";
                   }
                 }
               }
               uses apply-advanced;
               leaf sst {
                 description "Slice service type";
                 type enumeration {
                   enum "embb" {
                     description "Enhanced mobile broadband slice";
                   }
                   enum "urllc" {
                     description "Ultra-reliable, low latency communications";
                   }
                   enum "miot" {
                     description "Massive IoT";
                   }
                   enum "v2x" {
                     description "V2X services";
                   }
                 }
               }
               leaf sd {
                 description "Selection differentiator";
                 default "0";
                 type union {
                   type string {
                     pattern "<.*>|$.*";
                   }
                   type uint32 {
                     range "0 .. 16777215";
                   }
                 }
               }
             }
           }
         }
         list amf {
           key name;
           ordered-by user;
           description "AGF access and mobility management function";
           max-elements 256;
           leaf name {
             description "AMF name";
             type string {
               length "1 .. 80";
             }
           }
           uses apply-advanced;
           leaf node-id {
             description "AMF node identifier";
             type union {
               type string {
                 pattern "<.*>|$.*";
               }
               type uint32 {
                 range "0 .. 255";
               }
             }
           }
           leaf ip-address {
             description "AMF ip address";
             type jt:ipv4addr;
           }
           leaf port {
             description "AMF port number";
             default "38412";
             type union {
               type string {
                 pattern "<.*>|$.*";
               }
               type uint16 {
                 range "0 .. 65535";
               }
             }
           }
           container local-endpoint {
             description "AMF local endpoint";
             uses apply-advanced;
             list ip-address {
               key name;
               ordered-by user;
               description "AMF local endpoint ip address";
               leaf name {
                 description "AMF local endpoint ip address";
                 type jt:ipv4addr;
               }
               uses apply-advanced;
             }
             leaf port {
               description "AMF local endpoint port number";
               type union {
                 type string {
                   pattern "<.*>|$.*";
                 }
                 type uint16 {
                   range "37100 .. 37164";
                 }
               }
             }
             leaf initial-tnla-weight-factor {
               description "The weight factor assigned to the initial SCTP association";
               default "128";
               type union {
                 type string {
                   pattern "<.*>|$.*";
                 }
                 type uint32 {
                   range "1 .. 255";
                 }
               }
             }
           }
           leaf routing-instance {
             description "Routing instance for AMF connectivity";
             type string {
             }
           }
           list tracking-area {
             key name;
             ordered-by user;
             description "AMF tracking areas";
             leaf name {
               description "Tracking area code";
               type union {
                 type uint32;
                 type string {
                   pattern "<.*>|$.*";
                 }
               }
             }
             uses apply-advanced;
           }
           leaf default-amf {
             description "Configure a default AMF";
             type empty;
           }
           leaf offline {
             description "Offline the AMF";
             type empty;
           }
         }
         list user-planes {
           key name;
           ordered-by user;
           uses user-plane-object;
         }
       }
       container flow-collector {
         description "Configure options to control flow collector";
         uses apply-advanced;
         leaf analyzer-address {
           description "Analyzer IP address field override value";
           type jt:ipv4addr;
         }
         leaf analyzer-id {
           description "Analyzer ID field override value";
           type string {
             length "1 .. 64";
           }
         }
         leaf retry {
           description "Transfer retry attempt count";
           default "0";
           type union {
             type string {
               pattern "<.*>|$.*";
             }
             type uint32 {
               range "0 .. 10";
             }
           }
         }
         leaf retry-delay {
           description "Delay between transfer retry attempts";
           default "0";
           units "seconds";
           type union {
             type string {
               pattern "<.*>|$.*";
             }
             type uint32 {
               range "0 .. 60";
             }
           }
         }
         list destinations {
           key name;
           ordered-by user;
           description "Configure destination for files";
           uses collector_destinations_type;
         }
         list file-specification {
           key name;
           description "File format specification";
           uses file_specification_type;
         }
         container interface-map {
           description "Input interface to Collector PIC mapping";
           presence "enable interface-map";
           uses interface_map_type;
         }
         container transfer-log-archive {
           description "Transfer log archive specification";
           presence "enable transfer-log-archive";
           uses collector_transfer_log_archive_type;
         }
       }
       container captive-portal {
         description "Captive Portal options";
         uses juniper-services-captive-portal;
       }
       container advanced-anti-malware {
         presence "enable advanced-anti-malware";
         uses apply-advanced;
       }
       container logging {
         description "Bulk logging configuration";
         uses juniper-pic-services-logging-options;
       }
       list service-set {
         key name;
         ordered-by user;
         description "Define a service set";
         leaf name {
           description "Service set name";
           type string {
             length "1 .. 63";
           }
         }
         uses apply-advanced;
         container syslog {
           description "Define system logging parameters";
           uses log-object;
         }
         leaf max-flows {
           description "Maximum number of flows allowed for a service set";
           type string;
         }
         leaf hosted-service-identifier {
           description "Service Set to Hosted service Map";
           type union {
             type string {
               pattern "<.*>|$.*";
             }
             type int32 {
               range "1 .. 63";
             }
           }
         }
         leaf max-session-setup-rate {
           description "Maximum number of session creations allowed per second";
           type string;
         }
         container max-drop-flows {
           description "Maximum number of drop flows allowed for a service-set";
           uses apply-advanced;
           leaf ingress {
             description "Maximum number of ingress drop flows allowed";
             type union {
               type string {
                 pattern "<.*>|$.*";
               }
               type int32 {
                 range "0 .. 8500000";
               }
             }
           }
           leaf egress {
             description "Maximum number of egress drop flows allowed";
             type union {
               type string {
                 pattern "<.*>|$.*";
               }
               type int32 {
                 range "0 .. 8500000";
               }
             }
           }
         }
         container snmp-trap-thresholds {
           presence "enable snmp-trap-thresholds";
           description "Define snmp traps for service sets";
           uses apply-advanced;
           container flow {
             presence "enable flow";
             description "Flow Threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
           container nat-address-port {
             presence "enable nat-address-port";
             description "Nat Address and port usage trap threshold range";
             leaf low {
               description "Lower limit of trap threshold";
               units "percent";
               type union {
                 type string {
                   pattern "<.*>|$.*";
                 }
                 type uint16 {
                   range "0 .. 100";
                 }
               }
             }
             leaf high {
               description "Upper limit of trap threshold";
               units "percent";
               type union {
                 type string {
                   pattern "<.*>|$.*";
                 }
                 type uint16 {
                   range "0 .. 100";
                 }
               }
             }
           }
           container session {
             presence "enable session";
             description "Session threshold range for a service set";
             leaf low {
               description "Lower limit of flow threshold";
               units "percent";
               type union {
                 type string {
                   pattern "<.*>|$.*";
                 }
                 type uint16 {
                   range "0 .. 100";
                 }
               }
             }
             leaf high {
               description "Upper limit of flow threshold";
               units "percent";
               type union {
                 type string {
                   pattern "<.*>|$.*";
                 }
                 type uint16 {
                   range "0 .. 100";
                 }
               }
             }
           }
         }
         leaf tcp-mss {
           description "Enable the limit on TCP Max. Seg. Size in SYN packets";
           type union {
             type string {
               pattern "<.*>|$.*";
             }
             type uint16 {
               range "536 .. 65535";
             }
           }
         }
         container cos-options {
           presence "enable cos-options";
           description "Options for COS service";
           uses apply-advanced;
           leaf match-rules-on-reverse-flow {
             description "If forward rules match fails, do it on reverse flow";
             type empty;
           }
         }
         container softwire-options {
           presence "enable softwire-options";
           description "Options for softwire";
           uses apply-advanced;
           leaf dslite-ipv6-prefix-length {
             description "The ipv6 prefix length for subscriber addresses";
             default "128";
             type enumeration {
               enum "56" {
                 description "The ipv6 prefix length of 56";
               }
               enum "64" {
                 description "The ipv6 prefix length of 64";
               }
               enum "96" {
                 description "The ipv6 prefix length of 96";
               }
               enum "128" {
                 description "The ipv6 prefix length of 128";
               }
             }
           }
         }
         container nat-options {
           description "Options for NAT";
           uses apply-advanced;
           container stateful-nat64 {
             description "Options for stateful NAT64";
             uses apply-advanced;
             leaf no-v6-frag-header {
               description "No fragmentation header in IPv6 header during IPv4 to IPv6 translation";
               type empty;
             }
             leaf clear-dont-fragment-bit {
               description "Clear DF bit in IPv4 header if IPv6 packet size is less than 1280 bytes";
               type empty;
             }
             leaf ipv6-mtu {
               description "Path MTU of IPv6 network";
               type union {
                 type string {
                   pattern "<.*>|$.*";
                 }
                 type uint16 {
                   range "1280 .. 9192";
                 }
               }
             }
             leaf disable-h323-ras {
               description "Disable H323 and RAS ALG for NAT64";
               type empty;
             }
           }
           container nptv6 {
             description "Options for NPTv6";
             uses apply-advanced;
             leaf icmpv6-error-messages {
               description "Send ICMP Error messages if NPTv6 address translation fails";
               type empty;
             }
           }
           leaf land-attack-check {
             description "Enable land attack checks";
             type enumeration {
               enum "ip-only" {
                 description "Land attack check is on IP address only";
               }
               enum "ip-port" {
                 description "Land attack check is on both IP and port";
               }
             }
           }
           leaf max-sessions-per-subscriber {
             description "Limit the number of sessions per subscriber";
             type union {
               type string {
                 pattern "<.*>|$.*";
               }
               type uint16 {
                 range "1 .. 32000";
               }
             }
           }
           leaf snmp-value-match-msmic {
             description "Match the MSMIC specific snmp values for the msdpc";
             type empty;
           }
         }
         container service-set-options {
           presence "enable service-set-options";
           description "Options for service set";
           uses apply-advanced;
           leaf tcp-non-syn {
             description "Deny session creation on receiving first non SYN pkt";
             type enumeration {
               enum "drop-flow" {
                 description "Drop tcp non SYN first packe";
               }
               enum "drop-flow-send-rst" {
                 description "Enable sending TCP RST on receiving first non SYN pkt";
               }
             }
           }
           leaf tcp-fast-open {
             description "Tcp-fast-Open enabled packets will be handled accordingly";
             type enumeration {
               enum "disabled" {
                 description "TFO option will be stripped and packet will be forwarded";
               }
               enum "drop" {
                 description "TFO enabled packets will be dropeed";
               }
             }
           }
           leaf bypass-traffic-on-pic-failure {
             description "Bypass traffic on service PIC failure";
             type empty;
           }
           leaf bypass-traffic-on-exceeding-flow-limits {
             description "Bypass traffic when exceeding the max flow limit";
             type empty;
           }
           leaf enable-asymmetric-traffic-processing {
             description "Enable service-processing for asymmetric traffic";
             type empty;
           }
           leaf subscriber-awareness {
             description "Enable subscriber awareness on the service chain";
             type empty;
           }
           leaf static-subscriber-application {
             description "Enable static subscriber on the service set";
             type empty;
           }
           container header-integrity-check {
             description "Enable/Disable header integrity checks";
             uses apply-advanced;
             leaf enable-all {
               description "Enable all header integrity checks";
               type empty;
             }
           }
           leaf enable-descriptive-session-syslog {
             description "This knob enables descriptive session syslogs for OPEN and CLOSE";
             type empty;
           }
           leaf enable-change-on-ams-redistribution {
             description "Allow NAT pool change on AMS redistribution";
             status deprecated;
             type empty;
           }
           leaf routing-engine-services {
             description "Enable service-processing at RE";
             type empty;
           }
           leaf inactivity-non-tcp-timeout {
             description "Inactivity timeout period for non-TCP established sessions";
             units "seconds";
             type union {
               type string {
                 pattern "<.*>|$.*";
               }
               type uint32 {
                 range "4 .. 86400";
               }
             }
           }
           leaf session-timeout {
             description "Session timeout period for established sessions";
             units "seconds";
             type union {
               type string {
                 pattern "<.*>|$.*";
               }
               type uint32 {
                 range "4 .. 86400";
               }
             }
           }
           container session-limit {
             presence "enable session-limit";
             description "Session limit";
             uses apply-advanced;
             leaf maximum {
               description "Maximum number of sessions allowed simultaneously";
               type string;
             }
           }
           leaf max-sessions-per-subscriber {
             description "Limit the number of sessions per subscriber";
             type union {
               type string {
                 pattern "<.*>|$.*";
               }
               type uint16 {
                 range "1 .. 32000";
               }
             }
           }
           container tcp-session {
             presence "enable tcp-session";
             description "Transmission Control Protocol session configuration";
             uses apply-advanced;
             leaf tcp-mss {
               description "Enable the limit on TCP Max. Seg. Size in SYN packets";
               type union {
                 type string {
                   pattern "<.*>|$.*";
                 }
                 type uint16 {
                   range "536 .. 65535";
                 }
               }
             }
             leaf tcp-tickles {
               description "Number of TCP keep-alive packets to be sent for bi-directional TCP flows";
               default "4";
               type union {
                 type string {
                   pattern "<.*>|$.*";
                 }
                 type uint8 {
                   range "0 .. 30";
                 }
               }
             }
             leaf open-timeout {
               description "Timeout period for TCP session establishment";
               units "seconds";
               type union {
                 type string {
                   pattern "<.*>|$.*";
                 }
                 type uint32 {
                   range "4 .. 300";
                 }
               }
             }
             leaf inactivity-tcp-timeout {
               description "Inactivity timeout period for TCP established sessions";
               units "seconds";
               type union {
                 type string {
                   pattern "<.*>|$.*";
                 }
                 type uint32 {
                   range "4 .. 86400";
                 }
               }
             }
             leaf inactivity-asymm-tcp-timeout {
               description "Inactivity timeout period for asymmetric TCP established sessions";
               units "seconds";
               type union {
                 type string {
                   pattern "<.*>|$.*";
                 }
                 type uint32 {
                   range "4 .. 86400";
                 }
               }
             }
             container ignore-errors {
               presence "enable ignore-errors";
               description "Ignore anomalies or errors";
               leaf tcp {
                 description "TCP protocol errors";
                 type empty;
               }
             }
             leaf close-timeout {
               description "Timeout period for TCP session tear-down";
               units "seconds";
               type union {
                 type string {
                   pattern "<.*>|$.*";
                 }
                 type uint32 {
                   range "2 .. 300";
                 }
               }
             }
             leaf tcp-non-syn {
               description "Deny session creation on receiving first non SYN pkt";
               type enumeration {
                 enum "drop-flow" {
                   description "Drop tcp non SYN first packe";
                 }
                 enum "drop-flow-send-rst" {
                   description "Enable sending TCP RST on receiving first non SYN pkt";
                 }
               }
             }
             leaf tcp-fast-open {
               description "Tcp-fast-Open enabled paclets will be handled accordingly";
               type enumeration {
                 enum "disabled" {
                   description "TFO option will be stripped and packet will be forwarded";
                 }
                 enum "drop" {
                   description "TFO enabled packets will be dropeed";
                 }
               }
             }
           }
           leaf enforce-global-timeout {
             description "Enforce global inactivity or session timeout";
             type empty;
           }
           leaf unidirectional-session-refreshing {
             description "Enable unidirectional session refreshing on this service-set";
             type enumeration {
               enum "input" {
                 description "Enable unidirectional session refreshing on input";
               }
               enum "output" {
                 description "Enable unidirectional session refreshing on output";
               }
             }
           }
         }
         container replicate-services {
           description "Define services that will be replicated to peer.";
           uses apply-advanced;
           leaf replication-threshold {
             description "Duration in seconds for which flow should remain active for replication. (Min 180s)";
             default "180";
             type union {
               type string {
                 pattern "<.*>|$.*";
               }
               type uint32 {
                 range "180 .. 86400";
               }
             }
           }
           leaf disable-replication-capability {
             description "Disable replication capability for this service-set";
             type empty;
           }
         }
         container allow-multicast {
           presence "enable allow-multicast";
           description "Allow multicast packets";
           uses apply-advanced;
         }
         choice softwire_choice {
           case case_1 {
             list softwire-rules {
               key name;
               ordered-by user;
               description "List of softwire rules";
               leaf name {
                 type string {
                   length "1 .. 63";
                 }
               }
               uses apply-advanced;
             }
           }
           case case_2 {
             list softwire-rule-sets {
               key name;
               ordered-by user;
               description "List of softwire rule sets";
               leaf name {
                 type string {
                   length "1 .. 63";
                 }
               }
               uses apply-advanced;
             }
           }
         }
         list softwires-rule-set {
           key name;
           ordered-by user;
           description "List of softwire rule sets";
           leaf name {
             type string {
               length "1 .. 63";
             }
           }
           uses apply-advanced;
         }
         choice stateful_firewall_rules_choice {
           case case_1 {
             list stateful-firewall-rules {
               key name;
               ordered-by user;
               description "List of stateful firewall rules";
               leaf name {
                 type string {
                   length "1 .. 63";
                 }
               }
               uses apply-advanced;
             }
           }
           case case_2 {
             list stateful-firewall-rule-sets {
               key name;
               ordered-by user;
               description "List of stateful firewall rule sets";
               leaf name {
                 type string {
                   length "1 .. 63";
                 }
               }
               uses apply-advanced;
             }
           }
         }
         choice ids-option-choice {
           case case_1 {
             list ids-option {
               key name;
               ordered-by user;
               description "List of ids-options";
               leaf name {
                 type string {
                   length "1 .. 31";
                 }
               }
               uses apply-advanced;
             }
           }
         }
         choice pcp_rules_choice {
           case case_1 {
             list pcp-rules {
               key name;
               ordered-by user;
               description "List of PCP rules";
               leaf name {
                 type string {
                   length "1 .. 63";
                 }
               }
               uses apply-advanced;
             }
           }
           case case_2 {
             list pcp-rule-sets {
               key name;
               ordered-by user;
               description "List of PCP rule sets";
               leaf name {
                 type string {
                   length "1 .. 63";
                 }
               }
               uses apply-advanced;
             }
           }
         }
         leaf appid-profile {
           description "Define AppID profile";
           type string {
             length "1 .. 63";
           }
         }
         choice nat_rules_choice {
           case case_1 {
             list nat-rules {
               key name;
               ordered-by user;
               description "List of NAT rules";
               leaf name {
                 type string {
                   length "1 .. 63";
                 }
               }
               uses apply-advanced;
             }
           }
           case case_2 {
             list nat-rule-sets {
               key name;
               ordered-by user;
               description "List of NAT rule sets";
               leaf name {
                 type string {
                   length "1 .. 63";
                 }
               }
               uses apply-advanced;
             }
           }
         }
         choice ip_reassembly_rules_choice {
           case case_1 {
             list ip-reassembly-rules {
               key name;
               ordered-by user;
               description "List of ip-reassembly rules";
               leaf name {
                 type string {
                   length "1 .. 63";
                 }
               }
               uses apply-advanced;
             }
           }
         }
         choice ids_rules_choice {
           case case_1 {
             list ids-rules {
               key name;
               ordered-by user;
               description "List of IDS rules";
               leaf name {
                 type string {
                   length "1 .. 63";
                 }
               }
               uses apply-advanced;
             }
           }
           case case_2 {
             list ids-rule-sets {
               key name;
               ordered-by user;
               description "List of IDS rule sets";
               leaf name {
                 type string {
                   length "1 .. 63";
                 }
               }
               uses apply-advanced;
             }
           }
         }
         choice cos_rules_choice {
           case case_1 {
             list cos-rules {
               key name;
               ordered-by user;
               description "One or more CoS rules";
               leaf name {
                 description "Rule name";
                 type string {
                   length "1 .. 63";
                 }
               }
               uses apply-advanced;
             }
           }
           case case_2 {
             list cos-rule-sets {
               key name;
               ordered-by user;
               description "One or more CoS rule sets";
               leaf name {
                 description "Name of rule set";
                 type string {
                   length "1 .. 63";
                 }
               }
               uses apply-advanced;
             }
           }
         }
         choice aacl_rules_choice {
           case case_1 {
             list aacl-rules {
               key name;
               ordered-by user;
               description "One or more AACL rules";
               leaf name {
                 description "Rule name";
                 type string {
                   length "1 .. 63";
                 }
               }
               uses apply-advanced;
             }
           }
           case case_2 {
             list aacl-rule-sets {
               key name;
               ordered-by user;
               description "One or more AACL rule sets";
               leaf name {
                 description "Name of rule set";
                 type string {
                   length "1 .. 63";
                 }
               }
               uses apply-advanced;
             }
           }
         }
         list aacl-dyn-rules {
           key name;
           ordered-by user;
           description "One or more AACL rule ";
           leaf name {
             description "Name of dynamic rule set";
             type string {
               length "1 .. 63";
             }
           }
           uses apply-advanced;
         }
         choice pgcp_rules_choice {
           case case_1 {
             list pgcp-rules {
               key name;
               ordered-by user;
               description "One or more PGCP rules";
               leaf name {
                 description "Rule name";
                 type string {
                   length "1 .. 63";
                 }
               }
               uses apply-advanced;
             }
           }
           case case_2 {
             list pgcp-rule-sets {
               key name;
               ordered-by user;
               description "One or more PGCP rule sets";
               leaf name {
                 description "Name of rule set";
                 type string {
                   length "1 .. 63";
                 }
               }
               uses apply-advanced;
             }
           }
         }
         container jflow-rules {
           presence "enable jflow-rules";
           description "One or more jflow rules";
           uses apply-advanced;
           container sampling {
             presence "enable sampling";
             uses apply-advanced;
             leaf instance {
               description "Name of the instance";
               type string {
                 length "1 .. 64";
               }
             }
           }
         }
         choice appid-choice {
           case case_1 {
             leaf application-identification-profile {
               description "Define Application Identification profile";
               type string {
                 length "1 .. 63";
               }
             }
           }
         }
         leaf pcef-profile {
           description "Define PCEF profile";
           type string {
             length "1 .. 63";
           }
         }
         leaf lrf-profile {
           description "Define logging and reporting profile";
           type string {
             length "1 .. 63";
           }
         }
         leaf hcm-profile {
           description "Define HCM profile";
           type string {
             length "1 .. 63";
           }
         }
         leaf web-filter-profile {
           description "Define WEB filtering profile";
           type string {
             length "1 .. 63";
           }
         }
         choice hcm_url_rules_choice {
           case case_1 {
             list hcm-url-rules {
               key name;
               ordered-by user;
               description "One or more HCM uri rules";
               leaf name {
                 description "Rule name";
                 type string {
                   length "1 .. 63";
                 }
               }
               uses apply-advanced;
             }
           }
           case case_2 {
             list hcm-url-rule-sets {
               key name;
               ordered-by user;
               description "One or more HCM url rule sets";
               leaf name {
                 description "Name of rule set";
                 type string {
                   length "1 .. 63";
                 }
               }
               uses apply-advanced;
             }
           }
         }
         choice hcm-tag-rules-choice {
           case case_1 {
             list tag-rules {
               key name;
               ordered-by user;
               description "One or more HCM tag rules";
               leaf name {
                 description "Rule name";
                 type string {
                   length "1 .. 63";
                 }
               }
               uses apply-advanced;
             }
           }
           case case_2 {
             list tag-rule-sets {
               key name;
               ordered-by user;
               description "One or more HCM tag rule sets";
               leaf name {
                 description "Name of rule set";
                 type string {
                   length "1 .. 63";
                 }
               }
               uses apply-advanced;
             }
           }
         }
         choice idppolicy-choice {
           case case_1 {
             leaf idp-profile {
               description "IDP policy to use";
               type string {
                 length "1 .. 63";
               }
             }
           }
         }
         choice cpcdd-choice {
           case case_1 {
             leaf captive-portal-content-delivery-profile {
               description "Define captive portal and content delivery profile";
               type string {
                 length "1 .. 63";
               }
             }
           }
         }
         choice lpdf-stats-choice {
           case case_1 {
             container policy-decision-statistics-profile {
               description "Define policy decision statistics profile";
               uses apply-advanced;
               leaf profile-name {
                 description "Policy decision statistics profile name";
                 type string {
                   length "1 .. 63";
                 }
               }
             }
           }
         }
         choice service_type_choice {
           case case_1 {
             container interface-service {
               description "Define parameters for interface-specific service sets";
               uses apply-advanced;
               leaf service-interface {
                 description "Services interface to use";
                 type union {
                   type jt:interface-unit;
                   type string {
                     pattern "<.*>|$.*";
                   }
                 }
               }
               container load-balancing-options {
                 uses apply-advanced;
                 container hash-keys {
                   presence "enable hash-keys";
                   uses apply-advanced;
                   leaf resource-triggered {
                     description "Resource Triggered load balancing";
                     type empty;
                   }
                   leaf-list ingress-key {
                     ordered-by user;
                     description "Hash Key for the ingress direction";
                     type enumeration {
                       enum "source-ip" {
                         description "Source Ip Address";
                       }
                       enum "destination-ip" {
                         description "Destination Ip Address";
                       }
                       enum "protocol" {
                         description "Protocol";
                       }
                       enum "iif" {
                         description "Incoming Interface";
                       }
                     }
                   }
                   leaf-list egress-key {
                     ordered-by user;
                     description "Hash Key for the egress direction";
                     type enumeration {
                       enum "source-ip" {
                         description "Source Ip Address";
                       }
                       enum "destination-ip" {
                         description "Destination Ip Address";
                       }
                       enum "protocol" {
                         description "Protocol";
                       }
                       enum "oif" {
                         description "Outgoing Interface";
                       }
                     }
                   }
                 }
               }
             }
           }
           case case_2 {
             container sampling-service {
               description "Define parameters for sampling service sets";
               uses apply-advanced;
               leaf service-interface {
                 description "Services interface to use";
                 type union {
                   type jt:interface-unit;
                   type string {
                     pattern "<.*>|$.*";
                   }
                 }
               }
             }
           }
           case case_3 {
             container next-hop-service {
               description "Define parameters for next-hop service sets";
               uses apply-advanced;
               leaf inside-service-interface {
                 description "Service interface to inside network";
                 type union {
                   type jt:interface-unit;
                   type string {
                     pattern "<.*>|$.*";
                   }
                 }
               }
               leaf outside-service-interface {
                 description "Service interface name";
                 type union {
                   type jt:interface-unit;
                   type string {
                     pattern "<.*>|$.*";
                   }
                 }
               }
               leaf outside-service-interface-type {
                 description "Service interface type local for reassembly service";
                 type enumeration {
                   enum "local" {
                     description "Must be local for reassembly service";
                   }
                 }
               }
               leaf service-interface-pool {
                 description "Service interface pool name";
                 type string {
                   length "1 .. 63";
                 }
               }
             }
           }
         }
         list extension-service {
           key name;
           ordered-by user;
           description "Define the customer specific extensions";
           max-elements 2;
           leaf name {
             description "Customer-prefixed service name";
             type string {
               length "1 .. 63";
             }
           }
           uses apply-advanced;
         }
         container service-order {
           presence "enable service-order";
           description "Define of order of services to be applied";
           uses apply-advanced;
           leaf-list forward-flow {
             ordered-by user;
             description "Service Order for forward flow";
             type string;
           }
           leaf-list reverse-flow {
             ordered-by user;
             description "Service Order for reverse flow";
             type string;
           }
         }
         container jflow-log {
           description "Define Jflow-logging parameters.";
           uses apply-advanced;
           leaf template-profile {
             description "Allow jflow messages for applications";
             type string {
               length "1 .. 63";
             }
           }
         }
         container flow {
           description "Define flow parameters";
           uses apply-advanced;
           container traceoptions {
             description "Trace options for flow services";
           }
         }
         container ipsec-vpn-options {
           description "Define IPSec VPN options";
           uses service_set_ipsec_vpn_options_object;
         }
         choice ipsec_vpn_rules_choice {
           case case_1 {
             list ipsec-vpn-rules {
               key name;
               ordered-by user;
               description "List of IPSec VPN rules";
               leaf name {
                 type string {
                   length "1 .. 63";
                 }
               }
               uses apply-advanced;
             }
           }
           case case_2 {
             list ipsec-vpn-rule-sets {
               key name;
               ordered-by user;
               description "List of IPSec VPN rule sets";
               leaf name {
                 type string {
                   length "1 .. 63";
                 }
               }
               uses apply-advanced;
             }
           }
         }
         leaf ipsec-group-vpn {
           description "Designate service-set to a Group VPN";
           type string;
         }
         leaf redundancy-set-id {
           description "Redundancy set identifier";
           type union {
             type string {
               pattern "<.*>|$.*";
             }
             type uint32 {
               range "1 .. 100";
             }
           }
         }
       }
       container ipsec-vpn {
         description "Configure IPSec VPN service";
         uses apply-advanced;
         list rule {
           key name;
           ordered-by user;
           description "Define an IPSec rule";
           uses ipsec_vpn_rule_object;
         }
         list rule-set {
           key name;
           ordered-by user;
           description "Defines a set of IPSec rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         container ipsec {
           description "IPSec configuration";
           uses services-ipsec;
         }
         container ike {
           description "IKE configuration";
           uses services-ike;
         }
         container traceoptions {
           description "Trace options for IPSec key management process";
           uses ipsec-services-traceoptions;
         }
         leaf no-ipsec-tunnel-in-traceroute {
           description "Do not display IPSec tunnel endpoint in traceroute output";
           type empty;
         }
         leaf establish-tunnels {
           description "Define the criteria to establish tunnels";
           default "on-traffic";
           type enumeration {
             enum "immediately" {
               description "Establish tunnels immediately";
             }
             enum "on-traffic" {
               description "Establish tunnels on traffic";
             }
             enum "responder-only" {
               description "Don't establish tunnels on responder only";
             }
           }
         }
         leaf clear-ike-sas-on-pic-restart {
           description "Clear IKE SAs when the corresponding PIC restarts";
           type empty;
         }
         leaf clear-ipsec-sas-on-pic-restart {
           description "Clear IPSec SAs when the corresponding PIC restarts";
           type empty;
         }
         leaf disable-natt {
           description "Disable NAT traversal even if NAT is detected";
           type empty;
         }
       }
       container ggsn {
         description "GGSN settings";
         uses ggsn_type;
       }
       container application-identification {
         presence "enable application-identification";
       }
       container lrf {
         description "Logging and reporting service configuration";
         uses apply-advanced;
         list profile {
           key name;
           ordered-by user;
           description "One or more LRF profiles";
           max-elements 8;
           uses lrf-profile-object;
         }
       }
       container pcef {
         description "Policy and Charging Enforcement Function(PCEF) configuration";
         uses services-pcef;
       }
       container mobile-edge {
         description "Mobile edge configuration";
         uses apply-advanced;
         leaf session-scale {
           description "Mobile edge system session scale configuration(requires system reboot)";
           type enumeration {
             enum "50k" {
               description "50k sessions";
             }
             enum "100k" {
               description "100k sessions";
             }
             enum "250k" {
               description "250k sessions";
             }
             enum "500k" {
               description "500k sessions";
             }
             enum "750k" {
               description "750k sessions";
             }
             enum "1m" {
               description "1 million sessions";
             }
           }
         }
         container gateways {
           description "Gateways";
           uses apply-advanced;
           leaf description {
             description "Description of the gateway";
             type string {
               length "1 .. 64";
             }
           }
           container resource-management {
             description "Configure resource management packet steering daemon";
             uses apply-advanced;
             container server {
               description "Configure resource management packet steering daemon";
               uses apply-advanced;
               container traceoptions {
                 description "Resource management packet steering daemon trace options";
                 uses rmpsd-traceoptions-type;
               }
             }
             container client {
               description "Configure resource management packet steering client";
               uses apply-advanced;
               container traceoptions {
                 description "Resource management packet steering client trace options";
                 uses rmps-clnt-traceoptions-type;
               }
             }
           }
           list saegw {
             key name;
             ordered-by user;
             description "SAE gateway name";
             max-elements 1;
             uses saegw-names;
           }
         }
         container pfcp {
           presence "enable pfcp";
           description "Trace options for upad pfcp";
           uses apply-advanced;
           container traceoptions {
             description "SAEGW upad pfcp trace options";
             uses pfcp-traceoptions-type;
           }
         }
         container session-manager {
           presence "enable session-manager";
           description "Trace options for upad session-manager";
           uses apply-advanced;
           container traceoptions {
             description "SAEGW upad session-manager trace options";
             uses sm-traceoptions-type;
           }
         }
         container charging-module {
           presence "enable charging-module";
           description "Trace options for upad charging-module";
           uses apply-advanced;
           container traceoptions {
             description "SAEGW upad charging-module trace options";
             uses cm-traceoptions-type;
           }
         }
       }
       container paa {
         presence "enable paa";
         uses apply-advanced;
         container test-agent {
           presence "enable test-agent";
           description "Paragon Active Assurance test agent";
           uses apply-advanced;
           leaf cc-host {
             description "DNS name of the PAA Control Center";
             type string;
           }
           leaf cc-account {
             description "User account for PAA Control Center";
             type string;
           }
           leaf cc-user {
             description "User email registered with PAA Control Center";
             type string;
           }
           leaf cc-password {
             description "Password for PAA Control Center user";
             type jt:unreadable;
           }
           leaf ta-version {
             description "PAA Test agent version";
             type string;
           }
           leaf ta-name {
             description "PAA Test agent name (default is host name)";
             type string;
           }
           leaf cc-port {
             description "PAA Control Center port (default is 6800)";
             type union {
               type string {
                 pattern "<.*>|$.*";
               }
               type uint32 {
                 range "1 .. 65535";
               }
             }
           }
           leaf cc-insecure {
             description "Allow insecure connection to PAA Control Center";
             type empty;
           }
           leaf cc-download-base-url {
             description "URL to download PAA Test Agent installation files";
             type string;
           }
         }
       }
       container monitoring {
         description "Network Performance monitoring utilities";
         uses apply-advanced;
         container rpm {
           description "Real-time performance monitoring";
           uses apply-advanced;
           list owner {
             key name;
             ordered-by user;
             description "RPM test collection owner";
             leaf name {
               description "Owner name";
               type string {
                 length "1 .. 32";
               }
             }
             uses apply-advanced;
             list test {
               key name;
               ordered-by user;
               description "RPM single test";
               leaf name {
                 description "Test name";
                 type string {
                   length "1 .. 32";
                 }
               }
               uses apply-advanced;
               leaf probe-type {
                 description "RPM probe test type";
                 type enumeration {
                   enum "icmp-ping" {
                     description "Monitor target using ICMP echo request";
                   }
                   enum "icmp-ping-timestamp" {
                     description "Monitor target using ICMP timestamp request";
                   }
                   enum "udp-ping" {
                     description "Monitor target using UDP packets";
                   }
                   enum "udp-ping-timestamp" {
                     description "Monitor target using UDP packets with timestamp";
                   }
                   enum "tcp-ping" {
                     description "Monitor target using TCP message";
                   }
                   enum "http-get" {
                     description "Monitor target using HTTP GET request";
                   }
                   enum "http-metadata-get" {
                     description "Monitor target using HTTP HEAD request";
                   }
                 }
               }
               leaf offload-type {
                 description "RPM probe processing offload";
                 default "pfe-timestamp";
                 type enumeration {
                   enum "none" {
                     description "Timestamping performed on the routing-engine";
                   }
                   enum "pfe-timestamp" {
                     description "Timestamping performed on the pfe host";
                   }
                 }
               }
               container target {
                 presence "enable target";
                 description "Target destination for test";
                 leaf address {
                   description "Target destination host or URL for test";
                   type string {
                     length "1 .. 1024";
                   }
                 }
                 leaf local-link {
                   description "Target destination link for test when relevant";
                   type union {
                     type jt:interface-unit;
                     type string {
                       pattern "<.*>|$.*";
                     }
                   }
                 }
               }
               leaf destination-port {
                 description "Target port number for test";
                 type union {
                   type string {
                     pattern "<.*>|$.*";
                   }
                   type uint16 {
                     range "7 .. 65535";
                   }
                 }
               }
               leaf source-address {
                 description "Source ipv4 or ipv6 address for test";
                 type jt:ipaddr;
               }
               leaf routing-instance {
                 description "Routing instance used for test";
                 type string {
                 }
               }
               leaf data-size {
                 description "Size of the data portion of the test packet";
                 type union {
                   type string {
                     pattern "<.*>|$.*";
                   }
                   type uint32 {
                     range "0 .. 65400";
                   }
                 }
               }
               leaf data-fill {
                 description "Define contents of the data portion of the test packet";
                 type string {
                   length "1 .. 2048";
                 }
               }
               leaf dscp-code-points {
                 description "Differentiated Services code point bits or alias";
                 type string {
                 }
               }
               leaf ttl {
                 description "Time to Live (hop-limit) value for an RPM packet";
                 type union {
                   type string {
                     pattern "<.*>|$.*";
                   }
                   type uint32 {
                     range "1 .. 255";
                   }
                 }
               }
               leaf probe-count {
                 description "Total number of probes per test";
                 default "1";
                 type union {
                   type string {
                     pattern "<.*>|$.*";
                   }
                   type uint32 {
                     range "1 .. 15";
                   }
                 }
               }
               container probe-interval {
                 presence "enable probe-interval";
                 description "Delay between two consecutive probes";
                 leaf interval {
                   description "Time value for the delay between two consecutive probes";
                   type union {
                     type string {
                       pattern "<.*>|$.*";
                     }
                     type uint32 {
                       range "1 .. 1000";
                     }
                   }
                 }
               }
               leaf test-interval {
                 description "Delay between tests";
                 units "seconds";
                 type union {
                   type string {
                     pattern "<.*>|$.*";
                   }
                   type uint32 {
                     range "1 .. 86400";
                   }
                 }
               }
               leaf history-size {
                 description "Number of stored history entries";
                 default "50";
                 type union {
                   type string {
                     pattern "<.*>|$.*";
                   }
                   type uint32 {
                     range "1 .. 512";
                   }
                 }
               }
               leaf moving-average-size {
                 description "Number of samples used for moving average";
                 type union {
                   type string {
                     pattern "<.*>|$.*";
                   }
                   type uint32 {
                     range "0 .. 512";
                   }
                 }
               }
               container thresholds {
                 description "Test failure triggers. Set 0 to disable.";
                 uses apply-advanced;
                 container egress-time {
                   presence "enable egress-time";
                   description "Threshold on source to destination time per probe";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 container ingress-time {
                   presence "enable ingress-time";
                   description "Threshold on destination to source time per probe";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 container jitter-egress {
                   presence "enable jitter-egress";
                   description "Threshold on source to destination jitter per test";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 container jitter-ingress {
                   presence "enable jitter-ingress";
                   description "Threshold on destination to source jitter per test";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 container jitter-rtt {
                   presence "enable jitter-rtt";
                   description "Threshold on round trip jitter per test";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 container rtt {
                   presence "enable rtt";
                   description "Threshold on round trip time per probe";
                   leaf limit-value {
                     description "Threshold value";
                     units "microseconds";
                     type union {
                       type string {
                         pattern "<.*>|$.*";
                       }
                       type uint32 {
                         range "0 .. 60000000";
                       }
                     }
                   }
                   leaf average {
                     description "Threshold on average instead of maximum";
                     type empty;
                   }
                 }
                 leaf successive-loss {
                   description "Threshold on successive probe loss";
                   type union {
                     type string {
                       pattern "<.*>|$.*";
                     }
                     type uint32 {
                       range "0 .. 15";
                     }
                   }
                 }
                 leaf total-loss {
                   description "Threshold on total probe loss";
                   type union {
                     type string {
                       pattern "<.*>|$.*";
                     }
                     type uint32 {
                       range "0 .. 15";
                     }
                   }
                 }
               }
               leaf-list traps {
                 ordered-by user;
                 description "Traps to send if relevant condition is met";
                 type enumeration {
                   enum "probe-failure" {
                     description "Exceeded successive probe loss threshold";
                   }
                   enum "test-failure" {
                     description "Exceeded total probe loss threshold";
                   }
                   enum "test-completion" {
                     description "Test completed";
                   }
                   enum "rtt-exceeded" {
                     description "Exceeded round trip time threshold";
                   }
                   enum "jitter-exceeded" {
                     description "Exceeded round trip time jitter threshold";
                   }
                   enum "ingress-time-exceeded" {
                     description "Exceeded ingress time threshold";
                   }
                   enum "ingress-jitter-exceeded" {
                     description "Exceeded ingress time jitter threshold";
                   }
                   enum "egress-time-exceeded" {
                     description "Exceeded egress time threshold";
                   }
                   enum "egress-jitter-exceeded" {
                     description "Exceeded egress time jitter threshold";
                   }
                 }
               }
             }
           }
           container probe-server {
             description "RPM probe server settings";
             uses apply-advanced;
             container icmp {
               presence "enable icmp";
               description "Enable RPM probe server for ICMP requests";
             }
             container udp {
               presence "enable udp";
               description "Enable RPM probe server for UDP requests";
               uses apply-advanced;
               leaf-list port {
                 ordered-by user;
                 description "Ports the RPM probe server should be listening to";
                 type union {
                   type uint16;
                   type string {
                     pattern "<.*>|$.*";
                   }
                 }
               }
             }
             container tcp {
               presence "enable tcp";
               description "Enable RPM probe server for TCP requests";
               uses apply-advanced;
               leaf-list port {
                 ordered-by user;
                 description "Ports the RPM probe server should be listening to";
                 type union {
                   type uint16;
                   type string {
                     pattern "<.*>|$.*";
                   }
                 }
               }
             }
           }
         }
         container twamp {
           description "Two-way Active Measurement Protocol configuration";
           uses apply-advanced;
           container client {
             description "TWAMP client configuration";
             uses apply-advanced;
             list control-connection {
               key name;
               ordered-by user;
               description "TWAMP control connection configuration";
               leaf name {
                 description "Control connection name";
                 type string {
                   length "1 .. 32";
                 }
               }
               uses apply-advanced;
               leaf control-type {
                 description "TWAMP control connection type";
                 type enumeration {
                   enum "light" {
                     description "No control connection to manage test sessions";
                   }
                   enum "managed" {
                     description "Control connection will negotiate test sessions";
                   }
                 }
               }
               leaf target {
                 description "Target destination for control connection";
                 type string {
                   length "1 .. 32";
                 }
               }
               leaf source-address {
                 description "Source ipv4 or ipv6 address for control connection";
                 type jt:ipaddr;
               }
               leaf destination-port {
                 description "Target port number for test";
                 type union {
                   type string {
                     pattern "<.*>|$.*";
                   }
                   type uint16 {
                     range "862 .. 65535";
                   }
                 }
               }
               leaf routing-instance {
                 description "Routing instance for control connection and test session";
                 type string {
                 }
               }
               leaf test-start {
                 description "TWAMP tests start trigger type";
                 type enumeration {
                   enum "auto" {
                     description "Tests will start immediately and keep repeating";
                   }
                   enum "manual" {
                     description "Tests will only run upon user request";
                   }
                 }
               }
               leaf test-interval {
                 description "Delay between tests";
                 units "seconds";
                 type union {
                   type string {
                     pattern "<.*>|$.*";
                   }
                   type uint32 {
                     range "1 .. 86400";
                   }
                 }
               }
               leaf-list traps {
                 ordered-by user;
                 description "Traps to send if relevant condition is met";
                 type enumeration {
                   enum "test-iteration-done" {
                     description "All initiated test sessions have completed";
                   }
                   enum "control-connection-closed" {
                     description "Control connection has closed";
                   }
                 }
               }
               list test-session {
                 key name;
                 ordered-by user;
                 description "TWAMP test session configuration";
                 leaf name {
                   description "Test session name";
                   type string {
                     length "1 .. 32";
                   }
                 }
                 uses apply-advanced;
                 leaf offload-type {
                   description "TWAMP probe processing offload";
                   default "pfe-timestamp";
                   type enumeration {
                     enum "none" {
                       description "Timestamping performed on the routing-engine";
                     }
                     enum "pfe-timestamp" {
                       description "Timestamping performed on the pfe host";
                     }
                     enum "inline-timestamp" {
                       description "Timestamping performed inline";
                     }
                   }
                 }
                 container target {
                   presence "enable target";
                   description "Target destination for test";
                   leaf address {
                     description "Target destination host for test";
                     type string {
                       length "1 .. 32";
                     }
                   }
                   leaf local-link {
                     description "Target destination link for test when relevant";
                     type union {
                       type jt:interface-unit;
                       type string {
                         pattern "<.*>|$.*";
                       }
                     }
                   }
                 }
                 leaf destination-port {
                   description "Target port number for test";
                   type union {
                     type string {
                       pattern "<.*>|$.*";
                     }
                     type uint16 {
                       range "862 .. 65535";
                     }
                   }
                 }
                 leaf source-address {
                   description "Source ipv4 or ipv6 address for test";
                   type jt:ipaddr;
                 }
                 leaf data-size {
                   description "Size of the data portion of the test packet";
                   type union {
                     type string {
                       pattern "<.*>|$.*";
                     }
                     type uint32 {
                       range "0 .. 65400";
                     }
                   }
                 }
                 leaf dscp-code-points {
                   description "Differentiated Services code point bits or alias";
                   type string {
                   }
                 }
                 leaf ttl {
                   description "Time to Live (hop-limit) value for TWAMP packets";
                   type union {
                     type string {
                       pattern "<.*>|$.*";
                     }
                     type uint32 {
                       range "1 .. 255";
                     }
                   }
                 }
                 leaf probe-count {
                   description "Total number of probes per test";
                   default "1";
                   type union {
                     type string {
                       pattern "<.*>|$.*";
                     }
                     type uint32 {
                       range "1 .. 255";
                     }
                   }
                 }
                 container probe-interval {
                   presence "enable probe-interval";
                   description "Delay between two consecutive probes";
                   leaf interval {
                     description "Time value for the delay between two consecutive probes";
                     type union {
                       type string {
                         pattern "<.*>|$.*";
                       }
                       type uint32 {
                         range "1 .. 1000";
                       }
                     }
                   }
                 }
                 leaf history-size {
                   description "Number of stored history entries";
                   default "50";
                   type union {
                     type string {
                       pattern "<.*>|$.*";
                     }
                     type uint32 {
                       range "1 .. 512";
                     }
                   }
                 }
                 leaf moving-average-size {
                   description "Number of samples used for moving average";
                   type union {
                     type string {
                       pattern "<.*>|$.*";
                     }
                     type uint32 {
                       range "0 .. 512";
                     }
                   }
                 }
                 container thresholds {
                   description "Test failure triggers. Set 0 to disable when numeric.";
                   uses apply-advanced;
                   container egress-time {
                     presence "enable egress-time";
                     description "Threshold source to destination time per probe";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   container ingress-time {
                     presence "enable ingress-time";
                     description "Threshold destination to source time per probe";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   container jitter-egress {
                     presence "enable jitter-egress";
                     description "Threshold source to destination jitter per test";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   container jitter-ingress {
                     presence "enable jitter-ingress";
                     description "Threshold destination to source jitter per test";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   container jitter-rtt {
                     presence "enable jitter-rtt";
                     description "Threshold round trip jitter per test";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   container rtt {
                     presence "enable rtt";
                     description "Threshold round trip time per probe";
                     leaf limit-value {
                       description "Threshold value";
                       units "microseconds";
                       type union {
                         type string {
                           pattern "<.*>|$.*";
                         }
                         type uint32 {
                           range "0 .. 60000000";
                         }
                       }
                     }
                     leaf average {
                       description "Threshold on average instead of maximum";
                       type empty;
                     }
                   }
                   leaf successive-loss {
                     description "Threshold on successive probe loss";
                     type union {
                       type string {
                         pattern "<.*>|$.*";
                       }
                       type uint32 {
                         range "0 .. 15";
                       }
                     }
                   }
                   leaf total-loss {
                     description "Threshold on total probe loss";
                     type union {
                       type string {
                         pattern "<.*>|$.*";
                       }
                       type uint32 {
                         range "0 .. 15";
                       }
                     }
                   }
                   leaf control-failure {
                     description "Control negotiation failure means test failure";
                     type enumeration {
                       enum "on" {
                         description "Control failure means test failure";
                       }
                       enum "off" {
                         description "Control failure does not mean test failure";
                       }
                     }
                   }
                 }
                 leaf-list traps {
                   ordered-by user;
                   description "Traps to send if relevant condition is met";
                   type enumeration {
                     enum "probe-failure" {
                       description "Exceeded successive probe loss threshold";
                     }
                     enum "test-failure" {
                       description "Exceeded total probe loss threshold";
                     }
                     enum "test-completion" {
                       description "Test completed";
                     }
                     enum "rtt-exceeded" {
                       description "Exceeded round trip time threshold";
                     }
                     enum "jitter-exceeded" {
                       description "Exceeded round trip time jitter threshold";
                     }
                     enum "ingress-time-exceeded" {
                       description "Exceeded ingress time threshold";
                     }
                     enum "ingress-jitter-exceeded" {
                       description "Exceeded ingress time jitter threshold";
                     }
                     enum "egress-time-exceeded" {
                       description "Exceeded egress time threshold";
                     }
                     enum "egress-jitter-exceeded" {
                       description "Exceeded egress time jitter threshold";
                     }
                   }
                 }
               }
             }
           }
           container server {
             presence "enable server";
             description "TWAMP server configuration";
             uses apply-advanced;
             container managed {
               presence "enable managed";
               description "Enable TWAMP server for managed control on the default port";
               uses apply-advanced;
               leaf-list port {
                 ordered-by user;
                 description "TCP ports accepting TWAMP control connections";
                 type union {
                   type uint16;
                   type string {
                     pattern "<.*>|$.*";
                   }
                 }
               }
               container client-list {
                 description "List of allowed clients";
                 uses apply-advanced;
                 list address {
                   key name;
                   ordered-by user;
                   description "Allowed clients specification";
                   leaf name {
                     description "Allowed ipv4 or ipv6 prefix";
                     type jt:ipprefix-mandatory;
                   }
                   uses apply-advanced;
                   list routing-instance {
                     key name;
                     ordered-by user;
                     description "List of routing instances for allowed prefix";
                     leaf name {
                       type string;
                     }
                     uses apply-advanced;
                   }
                 }
               }
               leaf client-limit {
                 description "Maximum number of TWAMP clients";
                 type union {
                   type string {
                     pattern "<.*>|$.*";
                   }
                   type uint32 {
                     range "0 .. 1000";
                   }
                 }
               }
               leaf control-per-client-limit {
                 description "Maximum number of TWAMP control connections per client";
                 type union {
                   type string {
                     pattern "<.*>|$.*";
                   }
                   type uint32 {
                     range "0 .. 1000";
                   }
                 }
               }
               leaf test-per-client-limit {
                 description "Maximum number of TWAMP test sessions per client";
                 type union {
                   type string {
                     pattern "<.*>|$.*";
                   }
                   type uint32 {
                     range "0 .. 1000";
                   }
                 }
               }
               leaf control-maximum-duration {
                 description "Hard limit on control connection duration";
                 units "seconds";
                 type union {
                   type string {
                     pattern "<.*>|$.*";
                   }
                   type uint32 {
                     range "0 .. 86400";
                   }
                 }
               }
               leaf control-inactivity-timeout {
                 description "Inactivity timeout on control connection";
                 units "seconds";
                 type union {
                   type string {
                     pattern "<.*>|$.*";
                   }
                   type uint32 {
                     range "0 .. 86400";
                   }
                 }
               }
               leaf offload-type {
                 description "TWAMP probe processing offload";
                 default "pfe-timestamp";
                 type enumeration {
                   enum "none" {
                     description "Timestamping performed on the routing-engine";
                   }
                   enum "pfe-timestamp" {
                     description "Timestamping performed on the pfe host";
                   }
                   enum "inline-timestamp" {
                     description "Timestamping performed inline";
                   }
                 }
               }
               leaf stateful-sequence {
                 description "Enable STAMP compliant sequence numbers";
                 type empty;
               }
             }
             container light {
               presence "enable light";
               description "Enable TWAMP server for light control on the default port";
               uses apply-advanced;
               leaf-list port {
                 ordered-by user;
                 description "UDP ports reflecting TWAMP light test packets";
                 type union {
                   type uint16;
                   type string {
                     pattern "<.*>|$.*";
                   }
                 }
               }
               leaf offload-type {
                 description "TWAMP probe processing offload";
                 default "pfe-timestamp";
                 type enumeration {
                   enum "none" {
                     description "Timestamping performed on the routing-engine";
                   }
                   enum "pfe-timestamp" {
                     description "Timestamping performed on the pfe host";
                   }
                   enum "inline-timestamp" {
                     description "Timestamping performed inline";
                   }
                 }
               }
               container stateful-sequence {
                 presence "enable stateful-sequence";
                 description "Enable STAMP compliant sequence numbers";
                 uses apply-advanced;
                 leaf cache-size {
                   description "TWAMP light session sequence numbers cache size ";
                   type union {
                     type string {
                       pattern "<.*>|$.*";
                     }
                     type uint32 {
                       range "1000 .. 1000000";
                     }
                   }
                 }
               }
             }
           }
         }
         container rfc2544 {
           description "Rfc2544 benchmarking tests";
           uses apply-advanced;
           list test-profile {
             key name;
             ordered-by user;
             description "Generator test profile";
             leaf name {
               description "Test profile name";
               type string {
                 length "1 .. 32";
               }
             }
             uses apply-advanced;
             leaf test-type {
               description "RFC2544 test types";
               type enumeration {
                 enum "throughput" {
                   description "Throughput tests";
                 }
                 enum "latency" {
                   description "Latency tests";
                 }
                 enum "frame-loss" {
                   description "Frame loss tests require step-percent configuration";
                 }
                 enum "back-to-back" {
                   description "Back-to-back frame tests";
                 }
               }
             }
             container bandwidth {
               presence "enable bandwidth";
               description "Theoretical service bandwidth rate in bps(value range K/M/Gbps)";
               leaf bw {
                 description "Bandwidth value for testing RFC2544 traffic generation";
                 type union {
                   type string {
                     pattern "<.*>|$.*";
                   }
                   type uint32 {
                     range "1 .. 100000000";
                   }
                 }
               }
               choice bandwidth-unit {
                 case case_1 {
                   leaf kbps {
                     description "Bandwidth unit in kilo bits per seconds(kbps)";
                     type empty;
                   }
                 }
                 case case_2 {
                   leaf mbps {
                     description "Bandwidth unit in mega bits per seconds(mbps)";
                     type empty;
                   }
                 }
                 case case_3 {
                   leaf gbps {
                     description "Bandwidth unit in Giga bits per seconds(gbps)";
                     type empty;
                   }
                 }
               }
             }
             leaf-list packet-size {
               ordered-by user;
               description "Size of the test packet";
               type union {
                 type uint16;
                 type string {
                   pattern "<.*>|$.*";
                 }
               }
             }
             leaf step-percent {
               description "Step percent for test";
               default "10";
               type union {
                 type string {
                   pattern "<.*>|$.*";
                 }
                 type uint32 {
                   range "1 .. 100";
                 }
               }
             }
           }
           container tests {
             presence "enable tests";
             description "Rfc2544 test configuration";
             uses apply-advanced;
             list test-name {
               key name;
               ordered-by user;
               description "Test definition";
               leaf name {
                 description "Test name";
                 type string {
                   length "1 .. 32";
                 }
               }
               uses apply-advanced;
               leaf mode {
                 description "Test mode";
                 type enumeration {
                   enum "reflect" {
                     description "Reflector end";
                   }
                   enum "initiate-and-terminate" {
                     description "Generator end";
                   }
                 }
               }
               leaf family {
                 description "Family type";
                 type enumeration {
                   enum "inet" {
                     description "Inet family";
                   }
                   enum "ccc" {
                     description "CCC family ";
                   }
                   enum "bridge" {
                     description "Bridge family ";
                   }
                   enum "ethernet-switching" {
                     description "Ethernet-switching family ";
                   }
                 }
               }
               leaf direction {
                 description "Direction of test";
                 type enumeration {
                   enum "ingress" {
                     description "Pseudo-wire/Bridge/Vpls Ingress direction";
                   }
                   enum "egress" {
                     description "Pseudo-wire/Bridge/Vpls Egress direction";
                   }
                 }
               }
               leaf test-interface {
                 description "Name of interface(ifl) for test";
                 type union {
                   type jt:interface-name;
                   type string {
                     pattern "<.*>|$.*";
                   }
                 }
               }
               leaf source-mac-address {
                 description "MAC address of source host in xx:xx:xx:xx:xx:xx format - Generator MAC";
                 type jt:mac-unicast;
               }
               leaf destination-mac-address {
                 description "MAC address of destination host in xx:xx:xx:xx:xx:xx format - Reflector MAC";
                 type jt:mac-addr;
               }
               leaf service-type {
                 description "Service type";
                 type enumeration {
                   enum "eline" {
                     description "Eline service";
                   }
                   enum "elan" {
                     description "Elan service";
                   }
                 }
               }
               leaf reflect-mode {
                 description "Reflect mode";
                 type enumeration {
                   enum "mac-swap" {
                     description "Mac swap ";
                   }
                   enum "no-mac-swap" {
                     description "No mac-swap";
                   }
                 }
               }
               leaf reflect-etype {
                 description "Etype to match for reflect mode";
                 type union {
                   type string {
                     pattern "<.*>|$.*";
                   }
                   type uint32 {
                     range "1 .. 65535";
                   }
                 }
               }
               leaf in-service {
                 description "Test executed in-service mode";
                 type empty;
               }
               leaf ip-swap {
                 description "Swap IP in the test payload";
                 type empty;
               }
               leaf udp-port-swap {
                 description "Swap UDP port in the test payload";
                 type empty;
               }
               leaf source-udp-port {
                 description "Source udp port";
                 type union {
                   type string {
                     pattern "<.*>|$.*";
                   }
                   type uint32 {
                     range "1 .. 65535";
                   }
                 }
               }
               leaf destination-udp-port {
                 description "Destination udp port";
                 type union {
                   type string {
                     pattern "<.*>|$.*";
                   }
                   type uint32 {
                     range "1 .. 65535";
                   }
                 }
               }
               leaf destination-ipv4-address {
                 description "Destination address for test";
                 type jt:ipv4addr;
               }
               leaf source-ipv4-address {
                 description "Source address for test";
                 type jt:ipv4addr;
               }
               leaf disable-signature-check {
                 description "Signature check disable";
                 type empty;
               }
               leaf test-profile {
                 description "Test profile for the generator traffic tests";
                 type string;
               }
               leaf dscp-code-points {
                 description "Differentiated Services code point bits or alias";
                 type string {
                 }
               }
               leaf test-iterator-duration {
                 description "Duration of each iteration in seconds";
                 type union {
                   type string {
                     pattern "<.*>|$.*";
                   }
                   type uint32 {
                     range "10 .. 300";
                   }
                 }
               }
               leaf halt-on-prefix-down {
                 description "Halt test on prefix down";
                 type empty;
               }
               leaf skip-arp-iteration {
                 description "Skip arp iteration in tests";
                 type empty;
               }
             }
           }
         }
       }
       container security-intelligence {
         uses apply-advanced;
         leaf url {
           description "Configure the url of feed server [https://<ip or hostname>:<port>/<uri>]";
           type string;
         }
         container authentication {
           description "Authenticate to use feed update services";
           uses apply-advanced;
           leaf auth-token {
             description "Token string for authentication";
             type string {
             }
           }
           leaf tls-profile {
             description "TLS profile";
             type string;
           }
         }
         container traceoptions {
           description "Security intelligence trace options";
           uses secintel-traceoptions;
         }
       }
       container trace {
         presence "enable trace";
         description "Enable tracing";
         uses apply-advanced;
         leaf evpn-vxlan {
           description "Enable evpn-vxlan tracing";
           type empty;
         }
       }
       container evpn {
         description "Auto-configuration for various layer2 features";
         uses apply-advanced;
         container traceoptions {
           description "Trace options for evpn services";
           uses apply-advanced;
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           container flag {
             description "Type of operation to be traced";
             uses apply-advanced;
             leaf input-configuration {
               description "Trace input configuration";
               type empty;
             }
             leaf chassis {
               description "Trace chassis configuration";
               type empty;
             }
             leaf interfaces {
               description "Trace interfaces configuration";
               type empty;
             }
             leaf routing-instance {
               description "Trace routing-instance configuration";
               type empty;
             }
             leaf routing-options {
               description "Trace routing-options configuration";
               type empty;
             }
             leaf policy-options {
               description "Trace policy-options configuration";
               type empty;
             }
             leaf protocols {
               description "Trace protocols configuration";
               type empty;
             }
             leaf forwarding-options {
               description "Trace forwarding-options configuration";
               type empty;
             }
             leaf all {
               description "Trace all generated configuration";
               type empty;
             }
           }
         }
         container defaults-override {
           description "Select configuration generation override";
           uses apply-advanced;
           leaf no-platform-defaults-config {
             description "Do not auto-derive platform specific configurations";
             type empty;
           }
           leaf no-aggregate-device-count-config {
             description "Do not auto-derive aggregated device count configurations";
             type empty;
           }
           leaf no-policy-and-routing-options-config {
             description "Do not auto-derive routing-options and policy-options configurations";
             type empty;
           }
           leaf no-loop-detect-config {
             description "Do not auto-derive loop-detect configurations";
             type empty;
           }
           leaf no-storm-control-config {
             description "Do not auto-derive loop-detect configurations";
             type empty;
           }
           leaf no-underlay-config {
             description "Do not auto-derive underlay configurations";
             type empty;
           }
           leaf no-overlay-bgp-config {
             description "Do not auto-derive BGP overlay configurations";
             type empty;
           }
         }
         container global-parameters {
           description "Global parameters";
           uses apply-advanced;
           leaf start-aggregate-ethernet-index {
             description "Start index for aggregate interfaces";
             type union {
               type string {
                 pattern "<.*>|$.*";
               }
               type uint32 {
                 range "1 .. 255";
               }
             }
           }
           leaf default-vlan-id {
             description "Vlan-id to be used as a default vlan-id";
             type string;
           }
           leaf anycast-mac {
             description "Configure anycast MAC address";
             type jt:mac-unicast;
           }
           container virtual-gateway {
             description "Configure virtual gateway MAC address";
             leaf v4-mac {
               description "Configure virtual gateway IPV4 virtual MAC address";
               type jt:mac-unicast;
             }
             leaf v6-mac {
               description "Configure virtual gateway IPV6 virtual MAC address";
               type jt:mac-unicast;
             }
           }
           leaf virtual-gateway-mac {
             description "Configure virtual gateway IPV4 virtual MAC address";
             type jt:mac-unicast;
           }
           leaf no-irb-address-auto-derive {
             description "Do not auto-dervie address and use the subnet address as is";
             type empty;
           }
           container mtu {
             description "Configure maximum transmission unit";
             leaf underlay {
               description "Configure maximum transmission unit for underlay interfaces";
               type union {
                 type uint32;
                 type string {
                   pattern "<.*>|$.*";
                 }
               }
             }
             leaf overlay {
               description "Configure maximum transmission unit for overlay interfaces";
               type union {
                 type uint32;
                 type string {
                   pattern "<.*>|$.*";
                 }
               }
             }
           }
         }
         container device-attribute {
           description "Device specific attributes";
           uses apply-advanced;
           leaf peer-id {
             description "Assign an id for each PEER device";
             type union {
               type string {
                 pattern "<.*>|$.*";
               }
               type uint32 {
                 range "1 .. 2";
               }
             }
           }
           choice loopback-choice {
             case case_1 {
               leaf loopback-subnet {
                 description "Ipv4 address prefix for loopback subnet";
                 status deprecated;
                 type jt:ipv4prefix;
               }
             }
             case case_2 {
               container loopback {
                 description "Ipv4 address prefix for loopback subnet";
                 uses apply-advanced;
                 leaf peer1-subnet {
                   description "Ipv4 address prefix for peer1 loopback subnet";
                   type jt:ipv4prefix;
                 }
                 leaf peer2-subnet {
                   description "Ipv4 address prefix for peer2 loopback subnet";
                   type jt:ipv4prefix;
                 }
               }
             }
           }
           leaf remote-peer-as {
             description " Autonomous system number in plain number or 'higher 16bits'.'Lower 16 bits' format";
             type string {
             }
           }
           leaf system-id {
             description "Node's System ID, encoded as a MAC address";
             type jt:mac-unicast;
           }
           container peer-to-peer {
             description "Interface between PEER to PEER";
             uses apply-advanced;
             container peer-subnet {
               description "PEER to PEER subnet";
               leaf inet {
                 description "IPv4 address prefix for aggregated-ethernet interface bundle";
                 type jt:ipv4prefix;
               }
               leaf inet6 {
                 description "IPv6 address prefix for aggregated-ethernet interface bundle";
                 type jt:ipv6prefix;
               }
               leaf-list interface-name {
                 description "Interface or list of peer to peer interfaces";
                 type union {
                   type jt:interface-device;
                   type string {
                     pattern "<.*>|$.*";
                   }
                 }
               }
             }
             container overlay-connectivity {
               uses apply-advanced;
               leaf ibgp {
                 description "Setup IBGP as OVERLAY";
                 type empty;
               }
             }
             container underlay-connectivity {
               uses apply-advanced;
               leaf ospf {
                 description "Setup OSPF as UNDERLAY";
                 type empty;
               }
             }
           }
         }
         container evpn-vxlan {
           description "EVPN VXLAN configurations";
           uses apply-advanced;
           list dhcp-relay {
             key name;
             description "Dynamic Host Configuration Protocol relay configuration";
             leaf name {
               description "Group name to identify a Server/Relay group";
               type string;
             }
             uses apply-advanced;
             leaf relay-source {
               description "Interface for relay source";
               type union {
                 type jt:interface-name;
                 type string {
                   pattern "<.*>|$.*";
                 }
               }
             }
             list dhcp-server-address {
               key name;
               description "IP Address of one or more DHCP servers";
               max-elements 32;
               leaf name {
                 description "IP Address of DHCP server";
                 type jt:ipaddr;
               }
               uses apply-advanced;
             }
             leaf vrf-instance {
               description "Identifier for VRF instance";
               type union {
                 type string {
                   pattern "<.*>|$.*";
                 }
                 type uint32 {
                   range "1 .. 255";
                 }
               }
             }
             leaf routing-instance {
               description "Name of the routing-instance from where server-group is reachable";
               type string {
               }
             }
           }
           list irb {
             key name;
             description "IRB settings";
             leaf name {
               description "IRB instance";
               type string {
               }
             }
             uses apply-advanced;
             leaf use-anycast-address {
               description "Use anycast address";
               type empty;
             }
             leaf no-dhcp-relay {
               description "Exclude this irb from dhcp-relay";
               type empty;
             }
             leaf vlan-id {
               description "IEEE 802.1q VLAN identifier for VLAN";
               type string;
             }
             container subnet-address {
               description "Subnet address";
               leaf-list inet {
                 description "Ipv4 subnet address";
                 type jt:ipv4prefix;
               }
               leaf virtual-gateway-v4-address {
                 description "Virtual Gateway IPv4 address";
                 type jt:ipv4addr;
               }
               leaf-list inet6 {
                 description "Ipv6 subnet address";
                 type jt:ipv6prefix;
               }
               leaf virtual-gateway-v6-address {
                 description "Virtual Gateway IPv6 address";
                 type jt:ipv6addr;
               }
               leaf no-irb-address-auto-derive {
                 description "Do not auto-dervie address and use the subnet address as is";
                 type empty;
               }
             }
             container instance {
               description "Specify mac-vrf-instance or vrf-instance instance";
               leaf vrf-instance {
                 description "VRF instance identifier";
                 type union {
                   type string {
                     pattern "<.*>|$.*";
                   }
                   type uint32 {
                     range "1 .. 255";
                   }
                 }
               }
               leaf mac-vrf-instance {
                 description "MAC-VRF instance identifier";
                 type union {
                   type string {
                     pattern "<.*>|$.*";
                   }
                   type uint32 {
                     range "1 .. 255";
                   }
                 }
               }
             }
             leaf apply-config-groups {
               description "Apply groups to the generated irb configuration";
               type string;
             }
           }
           list server {
             key name;
             description "Server configuration";
             leaf name {
               description "SERVER name";
               type string {
               }
             }
             uses apply-advanced;
             choice esi-lag-id-choice {
               case case_1 {
                 leaf esi-lag-id {
                   description "Assign an identifier for each server";
                   type union {
                     type string {
                       pattern "<.*>|$.*";
                     }
                     type uint32 {
                       range "1 .. 1024";
                     }
                   }
                 }
               }
               case case_2 {
                 leaf single-home-id {
                   description "Assign an identifier for a single home server";
                   type union {
                     type string {
                       pattern "<.*>|$.*";
                     }
                     type uint32 {
                       range "1 .. 1024";
                     }
                   }
                 }
               }
             }
             leaf-list vlan-id-list {
               description "Create VLAN for each of the vlan-id specified in the vlan-id-list";
               type jt:vlan-range;
             }
             list mac-vrf-instance {
               key name;
               description "MAC-VRF instance identifier";
               leaf name {
                 description "Instance identifier";
                 type union {
                   type string {
                     pattern "<.*>|$.*";
                   }
                   type uint32 {
                     range "1 .. 255";
                   }
                 }
               }
               uses apply-advanced;
               leaf-list vlan-id-list {
                 description "Create VLAN for each of the vlan-id specified in the vlan-id-list";
                 type jt:vlan-range;
               }
             }
             leaf-list interface {
               description "Interface or list of peer to server interfaces";
               type union {
                 type jt:interface-device;
                 type string {
                   pattern "<.*>|$.*";
                 }
               }
             }
             leaf enable-pxe-boot {
               description "Enable PXE boot";
               type empty;
             }
             leaf apply-config-groups {
               description "Apply groups to the generated interface configuration";
               type string;
             }
             leaf no-lacp {
               description "Do not configure LACP for this server";
               type empty;
             }
           }
         }
       }
       container ssl {
         description "Configuration for Secure Socket Layer support service";
         uses apply-advanced;
         container traceoptions {
           description "Trace options for Secure Socket Layer support service";
           uses ssl-traceoptions;
         }
         container termination {
           description "Configuration for Secure Socket Layer termination support service";
           uses ssl-termination-config;
         }
         container initiation {
           description "Configuration for Secure Socket Layer initiation support service";
           uses ssl-initiation-config;
         }
         container proxy {
           description "Configuration for Secure Socket Layer proxy support service";
           uses ssl-proxy-config;
         }
       }
       container stateful-firewall {
         description "Configure stateful firewall services";
         uses apply-advanced;
         list rule {
           key name;
           ordered-by user;
           description "Define a stateful firewall rule";
           uses sfw_rule_object;
         }
         list rule-set {
           key name;
           ordered-by user;
           description "Define a set of stateful firewall rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container ip-reassembly {
         description "Configure ip-reassembly services";
         uses apply-advanced;
         list profile {
           key name;
           description "Define a ip reassembly profile";
           uses ipr_profile_object;
         }
         list rule {
           key name;
           ordered-by user;
           description "Define a ip reassembly rule";
           uses ipr_rule_object;
         }
         list rule-set {
           key name;
           ordered-by user;
           description "Define a set of ip reassembly rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container softwire {
         description "Configure softwire services";
         uses apply-advanced;
         list ipv6-multicast-interfaces {
           key name;
           ordered-by user;
           description "Enable IPv6 multicast filter";
           leaf name {
             description "Interface name";
             type string;
           }
           uses apply-advanced;
         }
         container softwire-concentrator {
           description "Configure softwire concentrators";
           uses apply-advanced;
           list ds-lite {
             key name;
             ordered-by user;
             description "Configure DS-Lite concentrator";
             uses dslite_object;
           }
           list v6rd {
             key name;
             ordered-by user;
             description "Configure 6rd concentrator";
             uses v6rd_object;
           }
           list map-e {
             key name;
             ordered-by user;
             description "Configure MAP-E concentrator";
             uses mape_object;
           }
           list map-t {
             key name;
             ordered-by user;
             description "Configure MAP-T concentrator";
             uses mapt_object;
           }
         }
         list rule {
           key name;
           ordered-by user;
           description "Define a softwire rule";
           uses sw_rule_object;
         }
         list rule-set {
           key name;
           ordered-by user;
           description "Define a set of softwire rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container aacl {
         description "Application Aware Access List services configuration";
         uses apply-advanced;
         list rule {
           key name;
           ordered-by user;
           description "One or more AACL rules";
           uses aacl_rule_object;
         }
         list rule-set {
           key name;
           ordered-by user;
           description "Define a Set of AACL rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list aacl-dyn-rule-set {
           key name;
           ordered-by user;
           description "Define a set of AACL dynamic rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container hcm {
         description "Http Content Management services configuration";
         uses apply-advanced;
         list url-rule {
           key name;
           ordered-by user;
           description "One or more url HCM rules";
           uses hcm_url_rule_object;
         }
         list tag-rule {
           key name;
           ordered-by user;
           description "One or more  HCM tag rules";
           uses hcm_tag_rule_object;
         }
         list url-list {
           key name;
           ordered-by user;
           description "List of URL's";
           uses hcm_url_list_object;
         }
         leaf-list tag-attribute {
           ordered-by user;
           description "Tag Attributes (Subscriber Aware Attrs: imsi,msisdn,ipv4addr,imei,ipv6addr,apn,ggsnipv4,ggsnipv6)";
           type enumeration {
             enum "ipv4addr" {
             }
             enum "ipv6addr" {
             }
           }
         }
         list url-rule-set {
           key name;
           ordered-by user;
           description "Define a Set of HCM url rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list tag-rule-set {
           key name;
           ordered-by user;
           description "Define a Set of HCM tag rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         list profile {
           key name;
           ordered-by user;
           description "HCM Profile Name";
           max-elements 101;
           leaf name {
             description "HCM profile name";
             type string {
               length "1 .. 63";
             }
           }
           uses apply-advanced;
           container tag-rule {
             description "Tag rule to be included in this profile";
             uses apply-advanced;
             leaf tag-rule-name {
               description "Tag Rule name";
               type string {
               }
             }
           }
         }
       }
       container cos {
         description "Class of Service services configuration";
         uses cos-object;
       }
       container pgcp {
         description "Packet Gateway Control Protocol services configuration";
         uses apply-advanced;
         container traceoptions {
           description "Trace options for packet gateway service";
           uses apply-advanced;
           container flag {
             presence "enable flag";
             description "Per-component trace options";
             uses apply-advanced;
             leaf default {
               description "Default trace level for all the components";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
             container h248-stack {
               presence "enable h248-stack";
               description "H248 stack sub-components";
               uses apply-advanced;
               leaf default {
                 description "Default trace level for the H248 stack subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf control-association {
                 description "Control association trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf media-gateway {
                 description "Media gateway trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messages {
                 description "Enable H248 dump messages";
                 type empty;
               }
             }
             container bgf-core {
               presence "enable bgf-core";
               description "BGF core sub-components";
               uses apply-advanced;
               leaf default {
                 description "Default trace level for the bgf core subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf firewall {
                 description "Firewall trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf gate-logic {
                 description "Gate trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf policy {
                 description "Policy trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf pic-broker {
                 description "PIC broker trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf statistics {
                 description "Statistics trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common  trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
             container sbc-utils {
               presence "enable sbc-utils";
               description "SBC utils sub-components";
               uses apply-advanced;
               leaf default {
                 description "Default trace level for the sbc-utils subcomponents";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf common {
                 description "Common utils trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf configuration {
                 description "Configuration trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf device-monitor {
                 description "Device-monitor trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf ipc {
                 description "IPC trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf memory-management {
                 description "Memory mgmt trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf messaging {
                 description "Messaging trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
               leaf user-interface {
                 description "UI trace level";
                 default "error";
                 type enumeration {
                   enum "trace" {
                     description "Trace functions entering and exiting";
                   }
                   enum "debug" {
                     description "Trace code flow, branching, positive style guide check";
                   }
                   enum "info" {
                     description "Summary logs for normal operations";
                   }
                   enum "warning" {
                     description "Failure-recovery or Failure of an external entity";
                   }
                   enum "error" {
                     description "Failure with short-term affect";
                   }
                 }
               }
             }
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
         }
         list media-service {
           key name;
           ordered-by user;
           description "One or more PGCP media service";
           status deprecated;
           max-elements 32;
           uses pgcp_media_service_object;
         }
         list virtual-interface {
           key name;
           ordered-by user;
           description "One or more Virtual Interfaces";
           max-elements 1024;
           uses pgcp_virtual_interface_object;
         }
         list gateway {
           key name;
           ordered-by user;
           description "One or more Packet Gateways";
           max-elements 32;
           uses pgcp_gateway_object;
         }
         list rule {
           key name;
           ordered-by user;
           description "One or more PGCP rules";
           max-elements 64;
           uses pgcp_rule_object;
         }
         list rule-set {
           key name;
           ordered-by user;
           description "Define a Set of PGCP rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
         container session-mirroring {
           description "Session mirroring configuration";
           presence "enable session-mirroring";
           uses pgcp_session_mirroring_object;
         }
         leaf notification-rate-limit {
           description "Max number of notifications/second sent to PGC";
           type union {
             type string {
               pattern "<.*>|$.*";
             }
             type int32 {
               range "10 .. 1000";
             }
           }
         }
       }
       container border-signaling-gateway {
         description "Border signaling service configuration";
         uses apply-advanced;
         list gateway {
           key name;
           ordered-by user;
           max-elements 4;
           uses gateway_type;
         }
       }
       container ids {
         description "Configure the intrusion detection system";
         uses apply-advanced;
         list rule {
           key name;
           ordered-by user;
           description "Define an IDS rule";
           uses ids_rule_object;
         }
         list rule-set {
           key name;
           ordered-by user;
           description "Define a set of IDS rules";
           max-elements 16960;
           leaf name {
             description "Name of the rule set";
             type string {
               length "1 .. 63";
             }
           }
           uses apply-advanced;
           list rule {
             key name;
             ordered-by user;
             description "Rule to be included in this rule set";
             max-elements 16960;
             leaf name {
               description "Rule name";
               type string {
               }
             }
             uses apply-advanced;
           }
         }
       }
       container nat {
         description "Configure Network Address Translation";
         uses nat-object;
       }
       container pcp {
         description "Configure Port Control Protocol";
         uses pcp-object;
       }
       container l2tp {
         presence "enable l2tp";
         description "Configure Layer 2 Tunneling Protocol service";
         uses apply-advanced;
         list tunnel-group {
           key name;
           ordered-by user;
           description "Layer 2 Tunneling Protocol profile";
           uses l2tp_tunnel_group_object;
         }
         container ip-reassembly {
           description "Configure IP Reassembly parameters";
           uses apply-advanced;
           leaf service-set {
             description "Name of IP Reassembly service set";
             type string {
               length "1 .. 63";
             }
           }
         }
         container traceoptions {
           description "Layer 2 Tunneling Protocol daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           leaf level {
             description "Level of debugging output";
             default "error";
             type enumeration {
               enum "error" {
                 description "Match error conditions";
               }
               enum "warning" {
                 description "Match warning messages";
               }
               enum "notice" {
                 description "Match conditions that should be handled specially";
               }
               enum "info" {
                 description "Match informational messages";
               }
               enum "verbose" {
                 description "Match verbose messages";
               }
               enum "all" {
                 description "Match all levels";
               }
             }
           }
           list flag {
             key name;
             ordered-by user;
             description "Tracing parameters";
             leaf name {
               type enumeration {
                 enum "gres" {
                   description "Trace GRES events";
                 }
                 enum "init" {
                   description "Trace daemon initialization";
                 }
                 enum "events" {
                   description "Trace interface events";
                 }
                 enum "memory" {
                   description "Trace memory management code";
                 }
                 enum "message" {
                   description "Trace message processing code";
                 }
                 enum "packet-error" {
                   description "Trace Packet error events";
                 }
                 enum "parse" {
                   description "Trace parsing events";
                 }
                 enum "receive-packets" {
                   description "Trace received L2TP packets";
                 }
                 enum "session-db" {
                   description "Trace session database interactions";
                 }
                 enum "states" {
                   description "Trace state machine events";
                 }
                 enum "timer" {
                   description "Trace timer events";
                 }
                 enum "transmit-packets" {
                   description "Trace tranmitted L2TP packets";
                 }
                 enum "routing-socket" {
                   description "Trace routing socket events";
                 }
                 enum "routing-process" {
                   description "Trace routing process interactions";
                 }
                 enum "protocol" {
                   description "Trace Layer 2 Tunneling Protocol events";
                 }
                 enum "configuration" {
                   description "Trace configuration events";
                 }
                 enum "ipc-tx" {
                   description "Trace IPC transmit events";
                 }
                 enum "ipc-rx" {
                   description "Trace IPC receive events";
                 }
                 enum "general" {
                   description "Trace general events";
                 }
                 enum "tunnel" {
                   description "Trace tunnel events";
                 }
                 enum "stats" {
                   description "Trace libstats events";
                 }
                 enum "authentication" {
                   description "Trace authentication process interactions";
                 }
                 enum "all" {
                   description "Trace everything";
                 }
               }
             }
           }
           leaf debug-level {
             description "Trace level for PPP, L2TP, RADIUS, and UDP";
             type enumeration {
               enum "error" {
                 description "Errors";
               }
               enum "detail" {
                 description "Detailed debug information";
               }
               enum "packet-dump" {
                 description "Packet decode information";
               }
             }
           }
           container filter {
             presence "enable filter";
             description "Filter to control trace messages";
             uses apply-advanced;
             list protocol {
               key name;
               ordered-by user;
               description "Additional filter for protocol";
               leaf name {
                 type enumeration {
                   enum "ppp" {
                     description "Trace Point-to-Point Protocol events";
                   }
                   enum "l2tp" {
                     description "Trace Layer 2 Tunneling Protocol events";
                   }
                   enum "radius" {
                     description "Trace RADIUS events";
                   }
                   enum "udp" {
                     description "Trace User Datagram Protocol events";
                   }
                 }
               }
             }
             leaf user-name {
               description "Additional filter by user name";
               type string {
                 length "1 .. 64";
               }
             }
             container user {
               presence "enable user";
               description "Filter by user name";
               uses apply-advanced;
               leaf username {
                 description "Name of the user to be filtered";
                 type string {
                   length "1 .. 64";
                 }
               }
             }
           }
           list interfaces {
             key name;
             ordered-by user;
             description "Layer 2 Tunneling Protocol service interface";
             uses l2tp_interface_traceoptions;
           }
         }
         leaf weighted-load-balancing {
           description "Enable weighted-load-balancing for LAC sessions";
           type empty;
         }
         leaf destination-equal-load-balancing {
           description "Enable equal load balancing of destinations";
           type empty;
         }
         leaf drain {
           description "Prevents creation of destinations, tunnels and sessions";
           type empty;
         }
         leaf failover-within-preference {
           description "Enable failover-within-preference level for LAC sessions";
           type empty;
         }
         leaf disable-calling-number-avp {
           description "Disable the calling number AVP in ICRQ packet";
           type empty;
         }
         leaf disable-failover-protocol {
           description "Disable failover protocol resync mechanism";
           status deprecated;
           type empty;
         }
         leaf rx-connect-speed-when-equal {
           description "Generate rx connect speed AVP when tx equals rx speed";
           type empty;
         }
         leaf tx-connect-speed-method {
           description "TX connect speed method";
           default "static";
           type enumeration {
             enum "none" {
               description "Disable sending tx/rx speed AVPs";
             }
             enum "static" {
               description "Use advisory speed";
             }
             enum "ancp" {
               description "Use ANCP sourced tx/rx speed";
             }
             enum "pppoe-ia-tag" {
               description "Use tx/rx speed sent in the PPPoE IA tag";
             }
             enum "service-profile" {
               description "Use tx/rx speed from service profile configuration";
             }
           }
         }
         leaf maximum-sessions {
           description "Maximum number of sessions per chassis";
           default "512000";
           type union {
             type uint32;
             type string {
               pattern "<.*>|$.*";
             }
           }
         }
         container tunnel {
           description "System wide tunnel attributes";
           uses apply-advanced;
           list name {
             key name;
             ordered-by user;
             leaf name {
               description "Locally assigned name of the tunnel(in format Destination name/Tunnel name or Tunnel name)";
               type string {
                 length "1 .. 129";
               }
             }
             list address {
               key name;
               ordered-by user;
               description "Address of the tunnel destination";
               leaf name {
                 description "Address of remote system";
                 type jt:ipv4addr;
               }
               list routing-instance {
                 key name;
                 ordered-by user;
                 description "Routing instance in which tunnel exists";
                 leaf name {
                   description "Routing instance in which tunnel exists";
                   type string {
                   }
                 }
                 leaf drain {
                   description "Prevents assignment of sessions to tunnel";
                   type empty;
                 }
               }
               leaf drain {
                 description "Prevents assignment of sessions to tunnel";
                 type empty;
               }
             }
             leaf drain {
               description "Prevents sessions assignment to tunnel";
               type empty;
             }
           }
           leaf assignment-id-format {
             description "Assignment id format";
             default "assignment-id";
             type enumeration {
               enum "assignment-id" {
                 description "Configure the format to be assignment-id only";
               }
               enum "client-server-id" {
                 description "Configure the format to be client-auth-id + server-auth-id + assignment-id";
               }
             }
           }
           leaf retransmission-count-established {
             description "Max Retransmission count for Established tunnels";
             default "7";
             type union {
               type string {
                 pattern "<.*>|$.*";
               }
               type uint16 {
                 range "2 .. 30";
               }
             }
           }
           leaf retransmission-count-not-established {
             description "Max Retransmission count for Not Established tunnels";
             default "5";
             type union {
               type string {
                 pattern "<.*>|$.*";
               }
               type uint16 {
                 range "2 .. 30";
               }
             }
           }
           leaf nas-port-method {
             description "Tunnel network access server port method";
             type enumeration {
               enum "cisco-avp" {
                 description "Limited Cisco vendor specific mechanism";
               }
             }
           }
           leaf minimum-retransmission-timeout {
             description "Min retransmission timeout for control packets in seconds (default 1)";
             default "1";
             type enumeration {
               enum "1" {
                 description "1 second";
               }
               enum "2" {
                 description "2 seconds";
               }
               enum "4" {
                 description "4 seconds";
               }
               enum "8" {
                 description "8 seconds";
               }
               enum "16" {
                 description "16 seconds";
               }
             }
           }
           leaf idle-timeout {
             description "Tunnel idle timeout value in seconds";
             default "60";
             type union {
               type string {
                 pattern "<.*>|$.*";
               }
               type uint32 {
                 range "0 .. 86400";
               }
             }
           }
           leaf rx-window-size {
             description "Tunnel Receive Window Size";
             default "4";
             type union {
               type string {
                 pattern "<.*>|$.*";
               }
               type uint16 {
                 range "4 .. 128";
               }
             }
           }
           container tx-address-change {
             presence "enable tx-address-change";
             description "Tunnel Tx Address Change";
             uses apply-advanced;
             leaf accept {
               description "Accept Tx IP Address or UDP Port Change";
               type empty;
             }
             leaf ignore {
               description "Ignore Tx IP Address or UDP Port Change";
               type empty;
             }
             leaf ignore-ip-address {
               description "Ignore Tx IP Address Change";
               type empty;
             }
             leaf ignore-udp-port {
               description "Ignore Tx UDP Port Change";
               type empty;
             }
             leaf reject {
               description "Reject Tx IP Address or UDP Port Change";
               type empty;
             }
             leaf reject-ip-address {
               description "Reject Tx IP Address Change";
               type empty;
             }
             leaf reject-udp-port {
               description "Reject Tx UDP Port Change";
               type empty;
             }
           }
           leaf maximum-sessions {
             description "Maximum number of sessions per tunnel";
             default "65535";
             type union {
               type uint32;
               type string {
                 pattern "<.*>|$.*";
               }
             }
           }
           leaf failover-resync {
             description "Tunnel Failover Resync Mechanism";
             type enumeration {
               enum "silent-failover" {
                 description "Use silent failover as failover resync mechanism";
               }
               enum "failover-protocol" {
                 description "Use L2TP failover protocol as failover resync mechanism if peer supports";
               }
             }
           }
         }
         leaf destruct-timeout {
           description "The destruct timeout in seconds";
           default "300";
           type union {
             type string {
               pattern "<.*>|$.*";
             }
             type uint16 {
               range "10 .. 3600";
             }
           }
         }
         leaf tunnel-switch-profile {
           description "Default tunnel switch profile name";
           type string {
             length "1 .. 63";
           }
         }
         container destination {
           description "System wide destination attributes";
           presence "enable destination";
           uses l2tp_destination_object;
         }
         container access-line-information {
           description "Enable system wide sending of access-line attributes";
           presence "enable access-line-information";
           uses l2tp_access_line_object;
         }
         list session-limit-group {
           key name;
           ordered-by user;
           description "Session-limit-group configuration";
           leaf name {
             description "Name of the group";
             type string {
               length "1 .. 63";
             }
           }
           uses apply-advanced;
           leaf maximum-sessions {
             description "Maximum number of sessions per tunnel-group";
             type union {
               type uint32;
               type string {
                 pattern "<.*>|$.*";
               }
             }
           }
         }
         leaf enable-ipv6-services-for-lac {
           description "Enable IPv6 services for LAC sessions";
           type empty;
         }
         leaf enable-snmp-tunnel-statistics {
           description "Enable L2TP tunnel statistics for availability via SNMP";
           type empty;
         }
       }
       container adaptive-services-pics {
         description "Adaptive Services PIC daemon configuration";
         uses apply-advanced;
         container traceoptions {
           description "Adaptive Services PIC daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "Tracing parameters";
             leaf name {
               type enumeration {
                 enum "routing-socket" {
                   description "Trace routing socket events";
                 }
                 enum "routing-protocol" {
                   description "Trace routing protocol events";
                 }
                 enum "service-identification" {
                   description "Trace service-identification events";
                 }
                 enum "configuration" {
                   description "Trace configuration events";
                 }
                 enum "ipc" {
                   description "Trace IPC related events";
                 }
                 enum "kernel-object" {
                   description "Trace kernel object management";
                 }
                 enum "snmp" {
                   description "Trace SNMP operations";
                 }
                 enum "all" {
                   description "Trace everything";
                 }
               }
             }
           }
         }
       }
       container license-management {
         description "Configure license management server";
         uses apply-advanced;
         container license-server {
           presence "enable license-server";
           uses apply-advanced;
           leaf ip-address {
             description "Address of the license log server";
             type jt:ipv4addr;
           }
           leaf log-interval {
             description "Time interval to send data to Log Collector";
             default "300";
             type union {
               type string {
                 pattern "<.*>|$.*";
               }
               type uint32 {
                 range "60 .. 86400";
               }
             }
           }
           leaf-list services {
             ordered-by user;
             description "List of services that require throughput data export";
             type enumeration {
               enum "jflow" {
                 description "Jflow Service";
               }
               enum "cgnat" {
                 description "CGNAT Service";
               }
               enum "firewall" {
                 description "Firewall Service";
               }
             }
           }
         }
       }
       container rtlog {
         presence "enable rtlog";
         description "Secure log daemon options";
         uses apply-advanced;
         container traceoptions {
           description "Security log daemon trace options";
           uses apply-advanced;
           leaf no-remote-trace {
             description "Disable remote tracing";
             type empty;
           }
           container file {
             description "Trace file information";
             leaf filename {
               description "Name of file in which to write trace information";
               type string {
                 length "1 .. 1024";
               }
             }
             leaf size {
               description "Maximum trace file size";
               type string;
             }
             leaf files {
               description "Maximum number of trace files";
               default "3";
               type union {
                 type string {
                   pattern "<.*>|$.*";
                 }
                 type uint32 {
                   range "2 .. 1000";
                 }
               }
             }
             choice world-readable-choice {
               leaf world-readable {
                 description "Allow any user to read the log file";
                 type empty;
               }
               leaf no-world-readable {
                 description "Don't allow any user to read the log file";
                 type empty;
               }
             }
             leaf match {
               description "Regular expression for lines to be logged";
               type jt:regular-expression;
             }
           }
           list flag {
             key name;
             ordered-by user;
             description "List of things to include in trace";
             leaf name {
               type enumeration {
                 enum "source" {
                   description "Communication with security log forwarder";
                 }
                 enum "configuration" {
                   description "Reading of configuration";
                 }
                 enum "all" {
                   description "Everything";
                 }
                 enum "report" {
                   description "Trace report";
                 }
                 enum "hpl" {
                   description "Trace HPL logging";
                 }
               }
             }
           }
         }
       }
       container soft-gre {
         presence "enable soft-gre";
         description "Soft GRE tunnel definitions";
         uses apply-advanced;
         list tunnel-group {
           key name;
           ordered-by user;
           uses soft_gre_tunnel_group_object;
         }
       }
       container service-interface-pools {
         description "Configure service interface pools";
         uses apply-advanced;
         list pool {
           key name;
           ordered-by user;
           description "Define service interface pool";
           uses service_interface_pool_object;
         }
       }
       container hosted-services {
         description "Configuration for services performed in the remote server";
         uses apply-advanced;
         list client-profile {
           key name;
           ordered-by user;
           description "Configure client profile";
           leaf name {
             description "Client profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf client-address {
             description "Client address";
             type jt:ipv4addr;
           }
           leaf hosted-service-identifier {
             description "Identifier for the service performed on the remote server";
             type union {
               type string {
                 pattern "<.*>|$.*";
               }
               type int32 {
                 range "1 .. 63";
               }
             }
           }
         }
         list server-profile {
           key name;
           ordered-by user;
           description "Configure server profile";
           leaf name {
             description "Server profile name";
             type string {
               length "3 .. 32";
             }
           }
           uses apply-advanced;
           leaf transport-type {
             description "Transport type";
             type enumeration {
               enum "GRE" {
                 description "GRE";
               }
               enum "UDP" {
                 description "UDP";
               }
               enum "TCP" {
                 description "TCP";
               }
             }
           }
           leaf server-address {
             description "Server address";
             type jt:ipv4addr;
           }
           leaf client-address {
             description "Client address";
             type jt:ipv4addr;
           }
           leaf hosted-service-identifier {
             description "Identifier for the service performed in the remote server";
             type union {
               type string {
                 pattern "<.*>|$.*";
               }
               type int32 {
                 range "1 .. 63";
               }
             }
           }
         }
       }
       container jflow-log {
         presence "enable jflow-log";
         description "Configure jflow-logging parameters for services";
         uses apply-advanced;
         list collector {
           key name;
           ordered-by user;
           description "Collector attributes";
           leaf name {
             description "Profile name";
             type string {
               length "1 .. 63";
             }
           }
           uses apply-advanced;
           leaf destination-address {
             description "IPv4 Address or hostname of the collector";
             type string {
             }
           }
           leaf destination-port {
             description "Destination port of the collector";
             type union {
               type string {
                 pattern "<.*>|$.*";
               }
               type uint16 {
                 range "1 .. 65535";
               }
             }
           }
           leaf source-ip {
             description "Source IPv4 Address from which logging is to be done";
             type jt:ipv4addr;
           }
         }
         list collector-group {
           key name;
           ordered-by user;
           leaf name {
             description "Name of collector-group";
             type string {
               length "1 .. 63";
             }
           }
           uses apply-advanced;
           leaf-list collector {
             ordered-by user;
             description "List of Collector profiles";
             type string {
               length "1 .. 63";
             }
             max-elements 8;
           }
         }
         list template-profile {
           key name;
           ordered-by user;
           leaf name {
             description "Specify name of the template";
             type string {
               length "1 .. 63";
             }
           }
           uses apply-advanced;
           leaf collector {
             description "Specify a collector name";
             type string {
               length "1 .. 63";
             }
           }
           leaf-list collector-group {
             ordered-by user;
             description "Specify a collector-group name";
             type string {
               length "1 .. 63";
             }
             max-elements 1;
           }
           leaf template-type {
             description "Allow jflow-log for applications";
             type enumeration {
               enum "nat" {
                 description "Enable jflow-logs for NAT events";
               }
             }
           }
           leaf version {
             description "Version of jflow-logging";
             type enumeration {
               enum "v9" {
                 description "Version 9";
               }
               enum "ipfix" {
                 description "Ipfix";
               }
             }
           }
           container refresh-rate {
             presence "enable refresh-rate";
             uses apply-advanced;
             leaf packets {
               description "Specify number of packets after which templates are sent to collector";
               default "4800";
               type union {
                 type string {
                   pattern "<.*>|$.*";
                 }
                 type uint32 {
                   range "1 .. 48000";
                 }
               }
             }
             leaf seconds {
               description "Specify number of seconds after which templates are sent to collector";
               default "1800";
               type union {
                 type string {
                   pattern "<.*>|$.*";
                 }
                 type uint32 {
                   range "10 .. 1800";
                 }
               }
             }
           }
           leaf session-end-reason {
             description "Session end reason";
             type enumeration {
               enum "custom-reason" {
                 description "Custom specific session end reason";
               }
               enum "default-reason" {
                 description "Default session end reason";
               }
             }
           }
         }
       }
       container service-device-pools {
         description "Configure service device pools";
         uses apply-advanced;
         list pool {
           key name;
           ordered-by user;
           description "Define service device pool";
           uses service_device_pool_object;
         }
       }
       container network-slicing {
         description "Configure network wide slicing parameters";
         uses apply-advanced;
         list slice {
           key name;
           description "Configure network wide slice name";
           max-elements 8000;
           leaf name {
             description "Name of the network wide slice";
             type string {
               length "1 .. 64";
             }
           }
         }
       }
       container redundancy-set {
         description "Redundancy-set settings";
         uses apply-advanced;
         container traceoptions {
           description "Services redundancy trace options";
           uses srd-traceoptions-object;
         }
         list rs-id-object {
           key name;
           ordered-by user;
           description "Definition of redundancy-set";
           uses srd-rs-id-object;
         }
       }
       container analytics {
         presence "enable analytics";
         description "Traffic analytics configuration options";
         uses apply-advanced;
         container zero-suppression {
           description "Configure suppression of zeros for GRPC sensors";
           uses apply-advanced;
           leaf no-zero-suppression {
             description "Disable zero suppression";
             type empty;
           }
         }
         list streaming-server {
           key name;
           ordered-by user;
           description "Define Telemetry data servers";
           leaf name {
             description "Telemetry App server Name";
             type string {
               length "1 .. 128";
             }
           }
           uses apply-advanced;
           leaf remote-address {
             description "Telemetry server IP address";
             type jt:host;
           }
           leaf remote-port {
             description "Telemetry server Port";
             type union {
               type uint16;
               type string {
                 pattern "<.*>|$.*";
               }
             }
           }
           leaf transport {
             description "Telemetry export transport protocol";
             type enumeration {
               enum "udp" {
                 description "Use UDP transport protocol";
               }
               enum "grpc" {
                 description "Use grpc transport";
               }
             }
           }
           leaf dialout {
             description "Supports dynamic dialout subscriptions";
             type empty;
           }
         }
         list export-profile {
           key name;
           ordered-by user;
           description "Telemetry export profile name";
           leaf name {
             description "Telemetry export profile name";
             type string {
               length "1 .. 128";
             }
           }
           uses apply-advanced;
           leaf local-address {
             description "Source address for exported packets";
             type jt:ipaddr;
           }
           leaf local-port {
             description "Source port for exported packets";
             type union {
               type uint16;
               type string {
                 pattern "<.*>|$.*";
               }
             }
           }
           leaf dscp {
             description "DSCP value for exported packets";
             type union {
               type string {
                 pattern "<.*>|$.*";
               }
               type uint8 {
                 range "0 .. 63";
               }
             }
           }
           leaf forwarding-class {
             description "Forwarding-class for exported packets, applicable only for PFE sensors";
             type string {
               length "1 .. 64";
             }
           }
           leaf loss-priority {
             description "Packet Loss Priority for exported packets, applicable only for PFE sensors";
             type enumeration {
               enum "low" {
                 description "Marking when loss priority is low";
               }
               enum "high" {
                 description "Marking when loss priority is high";
               }
               enum "medium-low" {
                 description "Marking when loss priority is medium-low";
               }
               enum "medium-high" {
                 description "Marking when loss priority is medium-high";
               }
             }
           }
           leaf reporting-rate {
             description "Telemetry interval in seconds, max 24 hours";
             units "seconds";
             type union {
               type string {
                 pattern "<.*>|$.*";
               }
               type uint32 {
                 range "0 .. 86400";
               }
             }
           }
           leaf payload-size {
             description "Telemetry payload size";
             default "5000";
             units "bytes";
             type union {
               type string {
                 pattern "<.*>|$.*";
               }
               type uint32 {
                 range "1400 .. 9192";
               }
             }
           }
           leaf format {
             description "Telemetry export record format";
             type enumeration {
               enum "gpb" {
                 description "Use gpb format";
               }
               enum "gpb-sdm" {
                 description "Use gpb self-describing-message format";
               }
               enum "gpb-gnmi" {
                 description "Use gnmi format for gpb messages";
               }
               enum "json-gnmi" {
                 description "Use gnmi format for json messages";
               }
             }
           }
           leaf transport {
             description "Telemetry export transport protocol";
             type enumeration {
               enum "udp" {
                 description "Use UDP transport protocol";
               }
               enum "grpc" {
                 description "Use grpc transport";
               }
             }
           }
           leaf routing-instance {
             description "Routing instance to be used for grpc transport";
             type string;
           }
         }
         list sensor {
           key name;
           ordered-by user;
           description "Define Telemetry sensors";
           leaf name {
             description "Name of the sensor";
             type string {
               length "1 .. 128";
             }
           }
           uses apply-advanced;
           leaf-list server-name {
             ordered-by user;
             description "Define Telemetry server ";
             type string {
               length "1 .. 128";
             }
           }
           leaf export-name {
             description "Define Telemetry export profiles";
             type string {
               length "1 .. 128";
             }
           }
           leaf polling-interval {
             description "Define sensor polling interval in nano secs (1 .. 4294967295)";
             status deprecated;
             units "nanoseconds";
             type union {
               type string {
                 pattern "<.*>|$.*";
               }
               type uint32 {
                 range "1 .. 4294967295";
               }
             }
           }
           leaf resource {
             description "System resource identifier string";
             type string {
               length "1 .. 1024";
             }
           }
           leaf resource-filter {
             description "Regexp for filtering resource instances (1 .. 1024)";
             type string {
               length "1 .. 1024";
             }
           }
           leaf subscription-id {
             description "Subscription ID (Used internally to group sensors)";
             type union {
               type uint64;
               type string {
                 pattern "<.*>|$.*";
               }
             }
           }
           leaf suppress-zeros {
             description "Supress zeros while data export";
             type empty;
           }
           leaf reporting-rate {
             description "Telemetry interval in seconds, max 24 hours";
             units "seconds";
             type union {
               type string {
                 pattern "<.*>|$.*";
               }
               type uint32 {
                 range "0 .. 86400";
               }
             }
           }
           leaf-list end-of-sync-identifiers {
             ordered-by user;
             description "Set of end-of-syncs for this sensor";
             type union {
               type string {
                 pattern "<.*>|$.*";
               }
               type uint32 {
                 range "1 .. 64";
               }
             }
             max-elements 30;
           }
           leaf target-defined {
             description "Allow target to decide periodic, on-change or mix";
             type empty;
           }
           leaf life-time {
             description "Denotes sensor life-time";
             type enumeration {
               enum "long-lived" {
                 description "A long-lived subscription";
               }
               enum "one-off" {
                 description "An one-off subscription";
               }
             }
           }
         }
         list export-profiles {
           key name;
           ordered-by user;
           description "Mapping of export-profiles to collectors";
           leaf name {
             description "Export profile name";
             type string {
               length "1 .. 64";
             }
           }
           uses apply-advanced;
           leaf stream-format {
             description "Streaming data format";
             default "gpb";
             type enumeration {
               enum "gpb" {
                 description "Google protocol buffer format";
               }
               enum "json" {
                 description "Java script object notation format";
               }
               enum "csv" {
                 description "Comma separated value";
               }
               enum "tsv" {
                 description "Tab separated value";
               }
             }
           }
           container interface {
             presence "enable interface";
             description "Interface specific information";
             uses apply-advanced;
             leaf information {
               description "Enable streaming of interface information";
               type empty;
             }
             container statistics {
               description "Type of statistics to stream";
               uses apply-advanced;
               leaf traffic {
                 description "Enable streaming of interface traffic statistics";
                 type empty;
               }
               leaf queue {
                 description "Enable streaming of interface queue statistics";
                 type empty;
               }
             }
             container status {
               description "Type of statistics to stream";
               uses apply-advanced;
               leaf link {
                 description "Enable streaming of interface link status";
                 type empty;
               }
               leaf traffic {
                 description "Enable streaming of interface traffic status";
                 type empty;
               }
               leaf queue {
                 description "Enable streaming of interface queue status";
                 type empty;
               }
             }
           }
           container system {
             presence "enable system";
             description "Interface specific information";
             uses apply-advanced;
             leaf information {
               description "Enable streaming of system information";
               type empty;
             }
             container status {
               description "Type of statistics to stream";
               uses apply-advanced;
               leaf traffic {
                 description "Enable streaming of system traffic status";
                 type empty;
               }
               leaf queue {
                 description "Enable streaming of system queue status";
                 type empty;
               }
             }
           }
         }
         list resource-profiles {
           key name;
           ordered-by user;
           description "Mapping of resource profiles to interfaces/queues/system";
           leaf name {
             description "Export profile name";
             type string {
               length "1 .. 64";
             }
           }
           uses apply-advanced;
           choice queue-monitoring-choice {
             leaf queue-monitoring {
               description "Enable queue statistics monitoring";
               type empty;
             }
             leaf no-queue-monitoring {
               description "Don't enable queue statistics monitoring";
               type empty;
             }
           }
           choice traffic-monitoring-choice {
             leaf traffic-monitoring {
               description "Enable traffic statistics monitoring";
               type empty;
             }
             leaf no-traffic-monitoring {
               description "Don't enable traffic statistics monitoring";
               type empty;
             }
           }
           container depth-threshold {
             description "Depth threshold configuration";
             leaf high {
               description "High queue depth threshold";
               units "bytes";
               type union {
                 type string {
                   pattern "<.*>|$.*";
                 }
                 type uint32 {
                   range "1 .. 1250000000";
                 }
               }
             }
             leaf low {
               description "Low queue depth threshold";
               units "bytes";
               type union {
                 type string {
                   pattern "<.*>|$.*";
                 }
                 type uint32 {
                   range "1 .. 1250000000";
                 }
               }
             }
           }
           container latency-threshold {
             description "Latency threshold configuration";
             leaf high {
               description "High latency threshold";
               units "nanoseconds";
               type union {
                 type string {
                   pattern "<.*>|$.*";
                 }
                 type uint32 {
                   range "1 .. 100000000";
                 }
               }
             }
             leaf low {
               description "Low latency threshold";
               units "nanoseconds";
               type union {
                 type string {
                   pattern "<.*>|$.*";
                 }
                 type uint32 {
                   range "1 .. 100000000";
                 }
               }
             }
           }
         }
         container resource {
           presence "enable resource";
           uses apply-advanced;
           container system {
             description "System configuration options";
             uses apply-advanced;
             leaf resource-profile {
               description "Resouce profile name";
               type string {
                 length "1 .. 64";
               }
             }
             container polling-interval {
               description "Polling interval";
               uses apply-advanced;
               leaf traffic-monitoring {
                 description "Traffic statistics polling interval";
                 units "seconds";
                 type union {
                   type string {
                     pattern "<.*>|$.*";
                   }
                   type uint32 {
                     range "1 .. 300";
                   }
                 }
               }
               leaf queue-monitoring {
                 description "Queue statistics polling interval";
                 units "milliseconds";
                 type union {
                   type string {
                     pattern "<.*>|$.*";
                   }
                   type uint32 {
                     range "1 .. 1000";
                   }
                 }
               }
             }
           }
           container interfaces {
             description "Interface configuration options";
             uses apply-advanced;
             list interface {
               key name;
               uses interface_type;
             }
           }
         }
         container collector {
           description "Remote streaming servers configuration options";
           uses apply-advanced;
           container local {
             description "Remote streaming servers configuration options";
             uses apply-advanced;
             container file {
               description "Log file information";
               leaf filename {
                 description "Name of file in which to write log information";
                 type jt:filename;
               }
               leaf size {
                 description "Maximum log file size";
                 type string;
               }
               leaf files {
                 description "Maximum number of trace files";
                 default "10";
                 type union {
                   type string {
                     pattern "<.*>|$.*";
                   }
                   type uint32 {
                     range "2 .. 1000";
                   }
                 }
               }
             }
           }
           list address {
             key name;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               list transport {
                 key name;
                 description "Transport protocol";
                 leaf name {
                   type enumeration {
                     enum "tcp" {
                       description "Transmission control protocol";
                     }
                     enum "udp" {
                       description "User datagram protocol";
                     }
                   }
                 }
                 uses apply-advanced;
                 leaf export-profile {
                   description "Export profile name";
                   type string {
                     length "1 .. 64";
                   }
                 }
               }
             }
           }
         }
         container traffic-statistics {
           description "Traffic statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Traffic statistics polling interval";
             units "seconds";
             type union {
               type string {
                 pattern "<.*>|$.*";
               }
               type uint32 {
                 range "1 .. 300";
               }
             }
           }
         }
         container queue-statistics {
           description "Microburst statistics configuration options";
           status deprecated;
           uses apply-advanced;
           container file {
             description "Log file information";
             leaf filename {
               description "Name of file in which to write log information";
               type jt:filename;
             }
             leaf size {
               description "Maximum log file size";
               type string;
             }
             leaf files {
               description "Maximum number of trace files";
               default "10";
               type union {
                 type string {
                   pattern "<.*>|$.*";
                 }
                 type uint32 {
                   range "2 .. 1000";
                 }
               }
             }
           }
           leaf interval {
             description "Queue statistics polling interval";
             units "milliseconds";
             type union {
               type string {
                 pattern "<.*>|$.*";
               }
               type uint32 {
                 range "1 .. 1000";
               }
             }
           }
         }
         container interfaces {
           description "Interface configuration options";
           status deprecated;
           uses apply-advanced;
           list interface {
             key name;
             uses interface_type;
           }
         }
         container streaming-servers {
           description "Remote streaming servers configuration options";
           status deprecated;
           uses apply-advanced;
           list address {
             key name;
             ordered-by user;
             description "IP address of remote server";
             leaf name {
               description "IP address";
               type jt:ipaddr;
             }
             uses apply-advanced;
             list port {
               key name;
               description "Remote streaming server port number";
               leaf name {
                 description "Port number";
                 type union {
                   type string {
                     pattern "<.*>|$.*";
                   }
                   type uint32 {
                     range "1 .. 65535";
                   }
                 }
               }
               uses apply-advanced;
               leaf stream-format {
                 description "Streaming data format";
                 type enumeration {
                   enum "json" {
                     description "Javascript object notation";
                   }
                   enum "csv" {
                     description "Comma separated value";
                   }
                   enum "tsv" {
                     description "Tab separated value";
                   }
                 }
               }
               list stream-type {
                 key name;
                 description "Type of statistics to stream";
                 leaf name {
                   type enumeration {
                     enum "traffic-statistics" {
                       description "Enable streaming of traffic statistics";
                     }
                     enum "queue-statistics" {
                       description "Enable streaming of queue statistics";
                     }
                   }
                 }
                 uses apply-advanced;
               }
             }
           }
         }
       }
       container traffic-load-balance {
         description "Traffic load balance configuration";
         uses tdir_service_load_balance_object;
       }
       container network-monitoring {
         description "Network monitoring probe configuration";
         uses tdir_netmon_object;
       }
       container web-filter {
         description "Web Filtering service configuration";
         uses apply-advanced;
         leaf multi-tenant-support {
           description "Enable multi-tenant-support";
           type empty;
         }
         container multi-tenant-hash {
           description "Multi-tenant hashed file configuration";
           uses dnsf-multitenant-hash-object;
         }
         list profile {
           key name;
           ordered-by user;
           description "Web Filter profile";
           max-elements 8;
           uses urlf-profile-object;
         }
         list ip-address-list {
           key name;
           ordered-by user;
           description "SecIntel ip address list";
           uses si-ip-address-list-object;
         }
         container traceoptions {
           description "Trace options for Web Filter ";
           uses urlf-traceoptions-object;
         }
       }
     }
   }
   grouping aacl_rule_object {
     leaf name {
       description "Rule name";
       type string {
         length "1 .. 63";
       }
     }
     uses apply-advanced;
     leaf dynamic {
       description "Make rule dynamic";
       type empty;
     }
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in AACL rule";
       leaf name {
         description "Term name";
         type string {
           length "1 .. 63";
         }
       }
       uses apply-advanced;
       container from {
         description "Match criteria";
         presence "enable from";
         uses aacl_match_object;
       }
       container then {
         description "Action to take if the 'from' condition is matched";
         uses apply-advanced;
         leaf forwarding-class {
           description "Forwarding class assigned to outgoing packets";
           type string {
           }
         }
         leaf count {
           description "Count packets by application or Application group";
           type enumeration {
             enum "none" {
               description "Do not count any application or group";
             }
             enum "application" {
               description "Count by application name";
             }
             enum "application-group" {
               description "Count by application group";
             }
             enum "application-group-any" {
               description "Count all application groups as a single total in group 'any'";
             }
             enum "nested-application" {
               description "Count by nested application name";
             }
           }
         }
         leaf log {
           description "Log session information for this application match";
           type enumeration {
             enum "none" {
               description "Do not log session information";
             }
             enum "session-start" {
               description "Log session start information for this match";
             }
             enum "session-start-end" {
               description "Log session start/end information for this match";
             }
             enum "session-start-end-no-stats" {
               description "Log session start/end information with no stats";
             }
             enum "session-start-interim-end" {
               description "Log session start/interim/end information for this match";
             }
             enum "session-interim-end" {
               description "Log session interim/end information for this match";
             }
             enum "session-end" {
               description "Log session end information for this match";
             }
           }
         }
         leaf police {
           description "Policer name";
           type string {
           }
         }
         choice designation {
           case case_1 {
             leaf accept {
               description "Accept the packet";
               type empty;
             }
           }
           case case_2 {
             leaf discard {
               description "Discard the packet";
               type empty;
             }
           }
         }
       }
     }
   }
   grouping aacl_match_object {
     uses apply-advanced;
     list source-address {
       key name;
       ordered-by user;
       description "Match IP source address";
       uses sfw_addr_object;
     }
     list destination-address {
       key name;
       ordered-by user;
       description "Match IP destination address";
       uses sfw_addr_object;
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     choice app-rule {
       case case_1 {
         leaf application-group-any {
           description "Use to wildcard or match any application group";
           type empty;
         }
       }
       case case_2 {
         leaf application-unknown {
           description "Use to specify unknown application as the match criteria.";
           type empty;
         }
       }
       case case_3 {
         leaf nested-application-unknown {
           description "Use to specify unknown nested application as the match criteria.";
           type empty;
         }
       }
       case case_4 {
         leaf-list applications {
           ordered-by user;
           description "Match one or more applications";
           type string;
         }
       }
       case case_5 {
         leaf-list nested-applications {
           ordered-by user;
           description "Match one or more nested-applications";
           type string;
         }
       }
       case case_6 {
         leaf-list application-groups {
           ordered-by user;
           description "Match one or more applications";
           type string;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping bbefwa-trace-options-type {
     description "Trace options for fixed wireless access service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Fixed wireless access operations to include in debugging trace";
       leaf name {
         type enumeration {
           enum "configuration" {
             description "Configuration operations";
           }
           enum "cli" {
             description "Cli command operations";
           }
           enum "general" {
             description "Miscellaneous operations";
           }
           enum "statistics" {
             description "Statistics operations";
           }
           enum "tunnel" {
             description "GTP-U Tunnel operations";
           }
           enum "gateway" {
             description "Mobile management entity operations";
           }
           enum "authentication" {
             description "Mme authentication operations";
           }
           enum "infra" {
             description "Infrastructure operations";
           }
           enum "all" {
             description "All operations";
           }
         }
       }
     }
   }
   grouping cm-traceoptions-type {
     description "Trace options for SAEGW charging";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "general" {
             description "Trace general events";
           }
           enum "state-machine" {
             description "Trace state-machine events";
           }
           enum "mirroring" {
             description "Trace mirroring events";
           }
           enum "all" {
             description "Trace everything";
           }
         }
       }
     }
   }
   grouping collector_destinations_type {
     leaf name {
       description "FTP destination URL (allows {text} macros)";
       type string;
     }
     uses apply-advanced;
     leaf password {
       description "Password for accessing URL";
       type jt:unreadable;
     }
   }
   grouping collector_transfer_log_archive_type {
     uses apply-advanced;
     leaf filename-prefix {
       description "Filename prefix for transfer log";
       type string {
       }
     }
     leaf maximum-age {
       description "Maximum age of transfer log file";
       default "15";
       units "minutes";
       type union {
         type string {
           pattern "<.*>|$.*";
         }
         type uint32 {
           range "1 .. 360";
         }
       }
     }
     list archive-sites {
       key name;
       ordered-by user;
       max-elements 5;
       leaf name {
         description "Primary and failover URLs to receive archive files";
         type string;
       }
       leaf password {
         description "Password to log in to the archive site";
         type jt:unreadable;
       }
     }
   }
   grouping cos-object {
     description "Class of Service services configuration";
     uses apply-advanced;
     list application-profile {
       key name;
       ordered-by user;
       description "One or more CoS application profiles";
       uses cos_application_profile_object;
     }
     list rule {
       key name;
       ordered-by user;
       description "One or more CoS rules";
       uses cos_rule_object;
     }
     list rule-set {
       key name;
       ordered-by user;
       description "Define a Set of CoS rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping cos_application_profile_object {
     leaf name {
       description "Profile name";
       type string {
         length "1 .. 63";
       }
     }
     uses apply-advanced;
     container sip {
       presence "enable sip";
       description "CoS treatment of Session Initiation Protocol data";
       uses apply-advanced;
       container voice {
         presence "enable voice";
         description "CoS treatment of SIP voice data";
         uses apply-advanced;
         leaf dscp {
           description "Code point alias or bit string";
           type string {
           }
         }
         leaf forwarding-class {
           description "Forwarding class assigned to outgoing packets";
           type string {
           }
         }
       }
       container video {
         presence "enable video";
         description "CoS treatment of SIP video data";
         uses apply-advanced;
         leaf dscp {
           description "Code point alias or bit string";
           type string {
           }
         }
         leaf forwarding-class {
           description "Forwarding class assigned to outgoing packets";
           type string {
           }
         }
       }
     }
     container ftp {
       presence "enable ftp";
       description "CoS treatment for FTP data";
       uses apply-advanced;
       container data {
         presence "enable data";
         uses apply-advanced;
         leaf dscp {
           description "Code point alias or bit string";
           type string {
           }
         }
         leaf forwarding-class {
           description "Forwarding class assigned to outgoing packets";
           type string {
           }
         }
       }
     }
   }
   grouping cos_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "One or more terms in CoS rule";
       leaf name {
         description "Term name";
         type string {
           length "1 .. 63";
         }
       }
       uses apply-advanced;
       container from {
         description "Match criteria";
         uses sfw_match_object;
       }
       container then {
         description "Action to take if the 'from' condition is matched";
         uses apply-advanced;
         leaf dscp {
           description "Code point alias or bit string";
           type string {
           }
         }
         leaf forwarding-class {
           description "Forwarding class assigned to outgoing packets";
           type string {
           }
         }
         leaf application-profile {
           description "CoS application profile";
           type string {
           }
         }
         leaf syslog {
           description "System log information about the packet";
           type empty;
         }
         choice designation {
           case case_1 {
             leaf reflexive {
               description "Apply mirror rule to reverse traffic";
               type empty;
             }
           }
           case case_2 {
             leaf revert {
               description "Apply received COS values to reverse traffic";
               type empty;
             }
           }
           case case_3 {
             container reverse {
               presence "enable reverse";
               description "CoS treatment for reverse traffic";
               uses apply-advanced;
               leaf dscp {
                 description "Code point alias or bit string";
                 type string {
                 }
               }
               leaf forwarding-class {
                 description "Forwarding class assigned to outgoing packets";
                 type string {
                 }
               }
               leaf application-profile {
                 description "CoS application profile";
                 type string {
                 }
               }
               leaf syslog {
                 description "System log information about the packet";
                 type empty;
               }
             }
           }
         }
       }
     }
     list policy {
       key name;
       ordered-by user;
       description "One or more policies in CoS rule";
       leaf name {
         description "Policy name";
         type string {
           length "1 .. 63";
         }
       }
       uses apply-advanced;
       container match {
         description "Match criteria";
         uses sfw_match_object;
       }
       container then {
         description "Action to take if the 'from' condition is matched";
         uses apply-advanced;
         leaf dscp {
           description "Code point alias or bit string";
           type string {
           }
         }
         leaf forwarding-class {
           description "Forwarding class assigned to outgoing packets";
           type string {
           }
         }
         leaf application-profile {
           description "CoS application profile";
           type string {
           }
         }
         choice designation {
           case case_1 {
             leaf reflexive {
               description "Apply mirror rule to reverse traffic";
               type empty;
             }
           }
           case case_2 {
             leaf revert {
               description "Apply received COS values to reverse traffic";
               type empty;
             }
           }
           case case_3 {
             container reverse {
               presence "enable reverse";
               description "CoS treatment for reverse traffic";
               uses apply-advanced;
               leaf dscp {
                 description "Code point alias or bit string";
                 type string {
                 }
               }
               leaf forwarding-class {
                 description "Forwarding class assigned to outgoing packets";
                 type string {
                 }
               }
               leaf application-profile {
                 description "CoS application profile";
                 type string {
                 }
               }
             }
           }
         }
       }
     }
   }
   grouping cpcd-rule-object-type {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a captive portal content delivery term";
       leaf name {
         description "Term name";
         type string {
           length "1 .. 63";
         }
       }
       uses apply-advanced;
       container from {
         description "Define match criteria";
         uses cpcd-match-object-type;
       }
       container then {
         description "Action to take if the 'from' condition is matched";
         uses cpcd-action-object-type;
       }
     }
   }
   grouping cpcd-action-object-type {
     uses apply-advanced;
     choice designation {
       case case_1 {
         leaf accept {
           description "Accept the packet";
           type empty;
         }
       }
       case case_2 {
         container rewrite {
           presence "enable rewrite";
           description "Rewrite the IP-DA of the packet";
           uses apply-advanced;
           leaf destination-address {
             description "The destination IP address";
             type jt:ipaddr;
           }
           leaf destination-port {
             description "The destination port";
             type union {
               type string {
                 pattern "<.*>|$.*";
               }
               type uint16 {
                 range "1 .. 65535";
               }
             }
           }
         }
       }
       case case_3 {
         container redirect {
           presence "enable redirect";
           description "Redirect the http packet";
           leaf url {
             description "URL of the captive portal file";
             type string {
             }
           }
         }
       }
       case case_4 {
         container insert {
           description "Insert tag into the http packet";
           uses apply-advanced;
           list tag {
             key name;
             ordered-by user;
             description "Tag name to be inserted";
             leaf name {
               description "Tag name";
               type string {
                 length "1 .. 127";
               }
             }
             uses apply-advanced;
             leaf tag-value {
               description "Tag value to be inserted";
               type string;
             }
           }
         }
       }
     }
     leaf syslog {
       description "System log information about the packet";
       type empty;
     }
   }
   grouping cpcd-match-object-type {
     uses apply-advanced;
     list destination-address {
       key name;
       ordered-by user;
       description "Match IP destination address";
       leaf name {
         description "Match IP address";
         type string;
       }
       leaf except {
         description "Match address not in this prefix";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     list applications {
       key name;
       ordered-by user;
       description "Match one or more applications";
       leaf name {
         type string {
           length "1 .. 63";
         }
       }
       uses apply-advanced;
       leaf application-protocol {
         description "Application protocol type";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf protocol {
         description "Match IP protocol type";
         type string;
       }
       leaf source-port {
         description "Match TCP/UDP source port";
         type string;
       }
       leaf destination-port {
         description "Match TCP/UDP destination port";
         type string;
       }
     }
   }
   grouping cpcd-trace-options-type {
     description "Trace options for captive portal and content delivery service";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Captive portal operations to include in debugging trace";
       leaf name {
         type enumeration {
           enum "configuration" {
             description "Configuration operations";
           }
           enum "clicommand" {
             description "Cli command operations";
           }
           enum "general" {
             description "Miscellaneous operations";
           }
           enum "rtsock" {
             description "Routing socket operations";
           }
           enum "statistics" {
             description "Statistics operations";
           }
           enum "rules" {
             description "Rules operations";
           }
           enum "ssets" {
             description "Service sets operations";
           }
           enum "ipc" {
             description "RE-PIC operations";
           }
           enum "gres" {
             description "GRES operations";
           }
           enum "re-services" {
             description "RE Service Operations";
           }
           enum "re-svc-debug-stat" {
             description "RE Service debug stats";
           }
           enum "all" {
             description "All operations";
           }
         }
       }
     }
   }
   grouping dfc_group_type {
     description "Configure DFC group parameters";
     leaf name {
       description "DFC group name";
       type string {
         length "1 .. 64";
       }
     }
     uses apply-advanced;
     leaf-list interfaces {
       ordered-by user;
       description "DFC PIC(s) in this group";
       type union {
         type jt:interface-device;
         type string {
           pattern "<.*>|$.*";
         }
       }
       max-elements 1;
     }
     leaf input-packet-rate-threshold {
       description " Input pps (max 300k on MO-III, 1M on MS-400)";
       default "1024000";
       units "pps";
       type string;
     }
     leaf max-duplicates {
       description "Maximum content destinations for the capture group";
       type union {
         type string {
           pattern "<.*>|$.*";
         }
         type uint32 {
           range "1 .. 64";
         }
       }
     }
     leaf duplicates-dropped-periodicity {
       description "Periodicity of DuplicatesDropped notification in secs";
       type union {
         type string {
           pattern "<.*>|$.*";
         }
         type uint32 {
           range "1 .. 255";
         }
       }
     }
     container pic-memory-threshold {
       description "PIC memory threshold";
       leaf percentage {
         description "Threshold in percentage";
         units "percent";
         type union {
           type string {
             pattern "<.*>|$.*";
           }
           type uint32 {
             range "10 .. 100";
           }
         }
       }
     }
     list control-source {
       key name;
       ordered-by user;
       description "Configure control source parameters";
       max-elements 64;
       uses dfc_control_source_type;
     }
     list content-destination {
       key name;
       ordered-by user;
       description "Configure content destination parameters";
       max-elements 64;
       uses content_destination_type;
     }
   }
   grouping content_destination_type {
     leaf name {
       description "Content destination identifier";
       type string {
         length "1 .. 48";
       }
     }
     uses apply-advanced;
     leaf address {
       description "Content destination IP address";
       type jt:ipv4addr;
     }
     leaf ttl {
       description "Time to live";
       default "255";
       type union {
         type string {
           pattern "<.*>|$.*";
         }
         type uint32 {
           range "1 .. 255";
         }
       }
     }
     leaf soft-limit-clear {
       description "Soft limit clear threshold";
       units "bps";
       type string;
     }
     leaf soft-limit {
       description "Soft limit threshold";
       units "bps";
       type string;
     }
     leaf hard-limit-target {
       description "Hard limit target threshold";
       units "bps";
       type string;
     }
     leaf hard-limit {
       description "Hard limit threshold";
       units "bps";
       type string;
     }
   }
   grouping dfc_control_source_type {
     leaf name {
       description "Control source identifier";
       type string {
         length "1 .. 48";
       }
     }
     uses apply-advanced;
     leaf-list source-addresses {
       ordered-by user;
       description "Allowed control source IP address list";
       type jt:ipv4addr;
       max-elements 8;
     }
     leaf service-port {
       description "Service port";
       type union {
         type uint16;
         type string {
           pattern "<.*>|$.*";
         }
       }
     }
     list notification-targets {
       key name;
       description "Notification target list";
       max-elements 8;
       uses dfc_notification_target_type;
     }
     leaf no-syslog {
       description "Disable syslog";
       type empty;
     }
     leaf shared-key {
       description "Shared key with control source";
       type string {
         length "1 .. 20";
       }
     }
     leaf-list allowed-destinations {
       ordered-by user;
       description "Allowed destinations";
       type string {
         length "1 .. 48";
       }
       max-elements 16;
     }
     leaf minimum-priority {
       description "Minimum priority of the control source";
       default "0";
       type union {
         type string {
           pattern "<.*>|$.*";
         }
         type uint32 {
           range "0 .. 255";
         }
       }
     }
   }
   grouping dfc_notification_target_type {
     leaf name {
       description "Notification target IP address";
       type jt:ipv4addr;
     }
     uses apply-advanced;
     leaf port {
       description "Notification target port";
       type union {
         type uint16;
         type string {
           pattern "<.*>|$.*";
         }
       }
     }
   }
   grouping dnsf-multitenant-hash-object {
     uses apply-advanced;
     container file-hash-key {
       description "Define web-filter global file key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
     }
   }
   grouping drop-policy-term {
     description "One or more drop terms";
     leaf name {
       description "Term name";
       type string {
       }
     }
     uses apply-advanced;
     container from {
       description "Define match criteria";
       uses apply-advanced;
       container source-address {
         description "Source IP Address";
         presence "enable source-address";
         uses li_policy_addr_simple_object;
       }
       container destination-address {
         description "Destination IP Address";
         presence "enable destination-address";
         uses li_policy_addr_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping drop-policy6-term {
     description "One or more drop terms";
     leaf name {
       description "Term name";
       type string {
       }
     }
     uses apply-advanced;
     container from {
       description "Define match criteria";
       uses apply-advanced;
       container source-address {
         description "Source IPv6 Address or Prefix";
         presence "enable source-address";
         uses li_policy_addr6_simple_object;
       }
       container destination-address {
         description "Destination IPv6 Address or Prefix";
         presence "enable destination-address";
         uses li_policy_addr6_simple_object;
       }
       choice source-port_choice {
         case case_1 {
           container source-port {
             description "Match source port";
             uses match_li_simple_port_value;
           }
         }
       }
       choice destination-port_choice {
         case case_1 {
           container destination-port {
             description "Match destination port";
             uses match_li_simple_port_value;
           }
         }
       }
       choice protocol_choice {
         case case_1 {
           container protocol {
             description "Match IP protocol type";
             uses match_li_simple_protocol_value;
           }
         }
       }
       choice dscp_choice {
         case case_1 {
           container dscp {
             description "Match Differentiated Services (DiffServ) code point";
             uses match_li_simple_dscp_value;
           }
         }
       }
     }
   }
   grouping dslite_object {
     leaf name {
       description "DS-Lite concentrator name";
       type string {
         length "1 .. 63";
       }
     }
     uses apply-advanced;
     leaf softwire-address {
       description "Softwire concentrator address";
       type jt:ipv6addr;
     }
     leaf mtu-v6 {
       description "MTU for the softwire tunnel";
       type union {
         type string {
           pattern "<.*>|$.*";
         }
         type uint32 {
           range "1280 .. 9192";
         }
       }
     }
     leaf copy-dscp {
       description "Copy DSCP (type of service) from IPv6 to IPv4 header";
       type empty;
     }
     leaf auto-update-mtu {
       description "Auto update MTU from received ICMPv6 messages";
       type empty;
     }
     leaf flow-limit {
       description "Max Number of IPv4 flows per Softwire";
       default "0";
       type union {
         type string {
           pattern "<.*>|$.*";
         }
         type uint32 {
           range "0 .. 16384";
         }
       }
     }
     leaf session-limit-per-prefix {
       description "Max number of sessions allowed per Softwire prefix";
       default "0";
       type union {
         type string {
           pattern "<.*>|$.*";
         }
         type uint32 {
           range "0 .. 16384";
         }
       }
     }
   }
   grouping family {
     container inet {
       description "IPv4 parameters";
       uses apply-advanced;
       choice if-addr {
         case case_1 {
           leaf dhcp {
             description "Enable DHCP on ethernet interface";
             type empty;
           }
         }
         case case_2 {
           leaf address {
             description "Interface address/destination prefix";
             type jt:ipv4prefix;
           }
         }
       }
     }
   }
   grouping file_specification_type {
     leaf name {
       description "Name for file type";
       type string;
     }
     uses apply-advanced;
     leaf name-format {
       description "Format string for filename (allows {text} macros)";
       type string;
     }
     leaf data-format {
       description "Data format for flow collection output";
       type enumeration {
         enum "flow-compressed" {
           description "Flow format (compressed)";
         }
       }
     }
     container transfer {
       leaf timeout {
         description "Timeout in seconds when the file is transferred";
         default "600";
         type union {
           type string {
             pattern "<.*>|$.*";
           }
           type uint32 {
             range "60 .. 1800";
           }
         }
       }
       leaf record-level {
         description "Number of records at which the file is transferred";
         default "500000";
         type union {
           type string {
             pattern "<.*>|$.*";
           }
           type uint32 {
             range "10000 .. 1000000";
           }
         }
       }
     }
   }
   grouping fiveqi {
     leaf name {
       description "5QI number";
       type union {
         type string {
           pattern "<.*>|$.*";
         }
         type uint32 {
           range "1 .. 254";
         }
       }
     }
     uses apply-advanced;
     container upstream-rewrite {
       description "AGF Upstream QOS attribute - rewrite";
       uses apply-advanced;
       leaf forwarding-class {
         description "Name of forwarding class";
         type string {
           length "1 .. 64";
         }
       }
       leaf loss-priority {
         description "Loss priority (low/high)";
         type enumeration {
           enum "low" {
             description "Code points to classify to loss priority low";
           }
           enum "high" {
             description "Code points to classify to loss priority high";
           }
         }
       }
       leaf dscp {
         type union {
           type string {
             pattern "<.*>|$.*";
           }
           type uint32 {
             range "0 .. 63";
           }
         }
       }
       leaf dscp-n3 {
         type union {
           type string {
             pattern "<.*>|$.*";
           }
           type uint32 {
             range "0 .. 63";
           }
         }
       }
     }
   }
   grouping fwa-authentication-type {
     description "FWA authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf imsi {
         description "Include IMSI";
         type empty;
       }
       leaf msisdn {
         description "Include MSISDN";
         type empty;
       }
       leaf mei {
         description "Include MEI";
         type empty;
       }
     }
   }
   grouping gateway_type {
     leaf name {
       description "Gateway name";
       type string;
     }
     uses apply-advanced;
     leaf service-interface {
       description "Associated services interface";
       type union {
         type jt:interface-device;
         type string {
           pattern "<.*>|$.*";
         }
       }
     }
     container sip {
       presence "enable sip";
       uses apply-advanced;
       container timers {
         description "Timers configuration";
         presence "enable timers";
         uses sip_timers_type;
       }
       list new-transaction-policy {
         key name;
         ordered-by user;
         description "Definition of a new-transaction policy";
         max-elements 500;
         uses transaction_policy_type;
       }
       list new-transaction-policy-set {
         key name;
         ordered-by user;
         description "Definition of a new-transaction policy set";
         max-elements 5;
         uses new_transaction_set_type;
       }
       list new-registration-policy {
         key name;
         ordered-by user;
         description "Definition of a new-registration policy";
         max-elements 500;
         uses registration_policy_type;
       }
       list new-registration-policy-set {
         key name;
         ordered-by user;
         description "Definition of a new-registration policy set";
         max-elements 5;
         uses new_registration_set_type;
       }
       list new-call-usage-policy {
         key name;
         ordered-by user;
         description "Definition of a new-call usage policy";
         max-elements 500;
         uses call_usage_policy_type;
       }
       list new-call-usage-policy-set {
         key name;
         ordered-by user;
         description "Definition of a new-call usage policy set";
         max-elements 5;
         uses new_call_usage_set_type;
       }
       container routing-destinations {
         description "Definition of routing destinations";
         presence "enable routing-destinations";
         uses routing-destinations;
       }
       container message-manipulation-rules {
         description "Definition of manipulation rules";
         uses header-manipulation-message-manipulation-rules-type;
       }
       leaf local-tag-prefix {
         description "Local tag prefix";
         default "bsg";
         type string;
       }
       list signaling-realms {
         key name;
         ordered-by user;
         description "Signaling realm";
         uses signaling-realm;
       }
       leaf local-uri-prefix {
         description "Local URI prefix";
         default "J";
         type string;
       }
     }
     list admission-control {
       key name;
       ordered-by user;
       description "Definition of an admission controller";
       max-elements 10;
       uses admission-control-type;
     }
     list service-point {
       key name;
       ordered-by user;
       max-elements 100;
       uses service_point_type;
     }
     container name-resolution-cache {
       presence "enable name-resolution-cache";
       uses name-resolution-cache-type;
     }
     container embedded-spdf {
       presence "enable embedded-spdf";
       uses apply-advanced;
       list service-class {
         key name;
         ordered-by user;
         description "Definition of service class policies";
         max-elements 5;
         leaf name {
           description "Service class name";
           type string {
             length "1 .. 63";
           }
         }
         uses apply-advanced;
         list term {
           key name;
           ordered-by user;
           description "Service class settings by media type";
           max-elements 6;
           leaf name {
             description "Term name";
             type string;
           }
           uses apply-advanced;
           container from {
             presence "enable from";
             description "The media-related filter that the rate limiting and DSCP marking are based on";
             uses apply-advanced;
             leaf-list media-type {
               ordered-by user;
               description "Media types to filter on";
               type enumeration {
                 enum "any-media" {
                 }
                 enum "audio" {
                 }
                 enum "video" {
                 }
               }
             }
           }
           container then {
             presence "enable then";
             description "The action to take based on the 'from' filter";
             uses apply-advanced;
             leaf reject {
               description "Reject the request";
               type empty;
             }
             leaf committed-information-rate {
               description "Committed information rate value per stream";
               default "0x7FFFFFFF";
               units "bytes-per-second";
               type union {
                 type string {
                   pattern "<.*>|$.*";
                 }
                 type uint32 {
                   range "0 .. 2147483647";
                 }
               }
             }
             leaf committed-burst-size {
               description "Committed burst size value per stream";
               default "0x7FFFFFFF";
               units "bytes";
               type union {
                 type string {
                   pattern "<.*>|$.*";
                 }
                 type uint32 {
                   range "20 .. 2147483647";
                 }
               }
             }
             leaf dscp {
               description "Code point alias or 6-bit pattern";
               default "be";
               type string {
               }
             }
           }
         }
       }
     }
     container traceoptions {
       description "Trace options for border signaling gateway";
       uses apply-advanced;
       container flag {
         presence "enable flag";
         description "Per-component trace options";
         uses apply-advanced;
         leaf minimum {
           description "Minimum trace level for all the components";
           default "error";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         leaf session-trace {
           description "Trace level for the session tracing component";
           type enumeration {
             enum "trace" {
               description "Trace functions entering and exiting";
             }
             enum "debug" {
               description "Trace code flow, branching, positive style guide check";
             }
             enum "info" {
               description "Summary logs for normal operations";
             }
             enum "warning" {
               description "Failure-recovery or Failure of an external entity";
             }
             enum "error" {
               description "Failure with short-term affect";
             }
           }
         }
         container sip-stack {
           presence "enable sip-stack";
           description "Sip stack trace level options";
           uses apply-advanced;
           leaf event-tracing {
             description "Event tracing";
             type empty;
           }
           leaf ips-tracing {
             description "IPS tracing";
             type empty;
           }
           leaf per-tracing {
             description "Performance tracing";
             type empty;
           }
           leaf dev-logging {
             description "Development tracing";
             type empty;
           }
           leaf verbose-logging {
             description "Verbose tracing";
             type empty;
           }
           leaf pd-log-level {
             description "Set pd trace level";
             type enumeration {
               enum "problem" {
                 description "Record a problem";
               }
               enum "exception" {
                 description "Record and exception that has been encountered in the code";
               }
               enum "audit" {
                 description "Record ordinary events for accounting purposes";
               }
             }
           }
           leaf pd-log-detail {
             description "Set detail level for DC logs";
             type enumeration {
               enum "full" {
                 description "Full details for every entry";
               }
               enum "summary" {
                 description "Summary details for every entry";
               }
             }
           }
         }
         container signaling {
           presence "enable signaling";
           description "Signaling component sub-components";
           uses apply-advanced;
           leaf minimum {
             description "Minimum trace level for the signaling subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf sip-stack-wrapper {
             description "Sip stack wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b-wrapper {
             description "B2B wrapper trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ua {
             description "UA trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf b2b {
             description "B2B trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf topology-hiding {
             description "Topology hiding trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf policy {
             description "Policy trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf name-resolution-cache {
             description "Name resolution cache trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf accounting-trigger {
             description "Accounting trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event-trigger {
             description "Event trigger trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Packet capture trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container framework {
           presence "enable framework";
           description "Framework component sub-components";
           uses apply-advanced;
           leaf minimum {
             description "Minimum trace level for the framework subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf executor {
             description "Executor trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf action {
             description "Action trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf event {
             description "Event trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf freezer {
             description "Freezer trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory pool trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container datastore {
           presence "enable datastore";
           description "Datastore component sub-components";
           uses apply-advanced;
           leaf minimum {
             description "Minimum trace level for the datastore subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf data {
             description "Data trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf handle {
             description "Handle trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf db {
             description "DB trace level ";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
         container sbc-utils {
           presence "enable sbc-utils";
           description "SBC utils component sub-components";
           uses apply-advanced;
           leaf minimum {
             description "Minimum trace level for the sbc-utils subcomponents";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf configuration {
             description "Configuration trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf ipc {
             description "IPC trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf device-monitor {
             description "Device-monitor trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-management {
             description "Memory mgmt trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf message {
             description "Messaging trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf common {
             description "Common utils trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf user-interface {
             description "User-interface trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf memory-pool {
             description "Memory-pool trace level";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
           leaf packet-capture {
             description "Trace packet capture events";
             default "error";
             type enumeration {
               enum "trace" {
                 description "Trace functions entering and exiting";
               }
               enum "debug" {
                 description "Trace code flow, branching, positive style guide check";
               }
               enum "info" {
                 description "Summary logs for normal operations";
               }
               enum "warning" {
                 description "Failure-recovery or Failure of an external entity";
               }
               enum "error" {
                 description "Failure with short-term affect";
               }
             }
           }
         }
       }
       container file {
         description "Trace file information";
         status deprecated;
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
     }
   }
   grouping admission-control-type {
     leaf name {
       description "Admission control profile name";
       type string;
     }
     uses apply-advanced;
     container dialogs {
       presence "enable dialogs";
       description "Dialog admission control rules";
       uses apply-advanced;
       leaf maximum-concurrent {
         description "Maximum concurrent dialogs allowed";
         type union {
           type string {
             pattern "<.*>|$.*";
           }
           type uint32 {
             range "0 .. 100000";
           }
         }
       }
       leaf committed-attempts-rate {
         description "Committed rate of dialog admission attempts";
         type union {
           type string {
             pattern "<.*>|$.*";
           }
           type uint32 {
             range "0 .. 500";
           }
         }
       }
       leaf committed-burst-size {
         description "Committed burst size of dialog admission attempts";
         type union {
           type string {
             pattern "<.*>|$.*";
           }
           type uint32 {
             range "0 .. 1000";
           }
         }
       }
     }
     container transactions {
       presence "enable transactions";
       description "Transaction admission control rules";
       uses apply-advanced;
       leaf maximum-concurrent {
         description "Maximum concurrent transactions allowed";
         type union {
           type string {
             pattern "<.*>|$.*";
           }
           type uint32 {
             range "0 .. 50000";
           }
         }
       }
       leaf committed-attempts-rate {
         description "Committed rate of transaction admission attempts";
         type union {
           type string {
             pattern "<.*>|$.*";
           }
           type uint32 {
             range "0 .. 1500";
           }
         }
       }
       leaf committed-burst-size {
         description "Committed burst size of transaction admission attempts";
         type union {
           type string {
             pattern "<.*>|$.*";
           }
           type uint32 {
             range "0 .. 3000";
           }
         }
       }
     }
   }
   grouping call_usage_policy_type {
     leaf name {
       description "Policy name";
       type string;
     }
     uses apply-advanced;
     list term {
       key name;
       ordered-by user;
       description "Term definition";
       max-elements 20;
       leaf name {
         description "Term name";
         type string;
       }
       uses apply-advanced;
       container from {
         presence "enable from";
         uses apply-advanced;
         leaf-list source-address {
           ordered-by user;
           description "Source addresses and masks";
           type jt:ipaddr;
           max-elements 5;
         }
         list method {
           key name;
           ordered-by user;
           description "Methods";
           uses call-usage-method-type;
         }
         container request-uri {
           presence "enable request-uri";
           description "Request URI field";
           uses apply-advanced;
           leaf-list regular-expression {
             ordered-by user;
             description "Regular expression matched on incoming Request-URI";
             type jt:regular-expression;
             max-elements 5;
           }
         }
         container contact {
           presence "enable contact";
           description "Contact field";
           uses apply-advanced;
           leaf-list regular-expression {
             ordered-by user;
             description "Regular expression matched on incoming contact";
             type jt:regular-expression;
             max-elements 5;
           }
         }
       }
       container then {
         description "Action";
         presence "enable then";
         uses new_call_then_type;
       }
     }
   }
   grouping call-usage-method-type {
     leaf name {
       type enumeration {
         enum "method-invite" {
         }
       }
     }
     uses apply-advanced;
   }
   grouping ggsn_type {
     uses apply-advanced;
     leaf node {
       description "Identifier for GGSN node";
       type string {
       }
     }
     list apn {
       key name;
       description "Access point configuration";
       uses apn_type;
     }
     container charging {
       description "GGSN charging and CDR configuration";
       uses charging_type;
     }
     container dhcp {
       description "DHCP settings";
       uses apply-advanced;
       list server {
         key name;
         description "Shared DHCP server configuration";
         max-elements 9999;
         uses dhcp_shared_type;
       }
     }
     container ggsnc {
       description "Global settings for GGSN-C PICs";
       uses apply-advanced;
       leaf gn-address-range {
         description "Gn network address range for GGSN-C PICs";
         type jt:ipv4prefix;
       }
       leaf gom-address-range {
         description "Gom network address range for GGSN-C PICs";
         type jt:ipv4prefix;
       }
       container redundancy {
         description "Preferred redundancy arrangement for GGSN-C PICs";
         presence "enable redundancy";
         status deprecated;
         uses failover_type;
       }
     }
     container pic-allocation {
       presence "enable pic-allocation";
       description "PIC allocation";
       uses apply-advanced;
       container dynamic-pics {
         presence "enable dynamic-pics";
         description "PICs with dynamic role capabilities";
         uses apply-advanced;
         leaf number-of-ggsnc {
           description "Number of GGSN-C PICs";
           type union {
             type string {
               pattern "<.*>|$.*";
             }
             type uint32 {
               range "0 .. 16";
             }
           }
         }
         leaf number-of-ggsnu {
           description "Number of GGSN-U PICs";
           type union {
             type string {
               pattern "<.*>|$.*";
             }
             type uint32 {
               range "0 .. 16";
             }
           }
         }
         leaf number-of-ggsnt {
           description "Number of GGSN-T PICs";
           type union {
             type string {
               pattern "<.*>|$.*";
             }
             type uint32 {
               range "0 .. 16";
             }
           }
         }
       }
       container static-pics {
         presence "enable static-pics";
         description "PICs with static roles";
         uses apply-advanced;
         leaf number-of-ggsnc {
           description "Number of GGSN-C PICs";
           type union {
             type string {
               pattern "<.*>|$.*";
             }
             type uint32 {
               range "0 .. 16";
             }
           }
         }
         leaf number-of-ggsnu {
           description "Number of GGSN-U PICs";
           type union {
             type string {
               pattern "<.*>|$.*";
             }
             type uint32 {
               range "0 .. 16";
             }
           }
         }
         leaf number-of-ggsnt {
           description "Number of GGSN-T PICs";
           type union {
             type string {
               pattern "<.*>|$.*";
             }
             type uint32 {
               range "0 .. 16";
             }
           }
         }
       }
     }
     container isp {
       description "ISP settings";
       uses apply-advanced;
       container session-resilience {
         description "Session resilience settings";
         uses apply-advanced;
         leaf session-controller {
           description "Enable session controller resilience";
           type empty;
         }
       }
     }
     container ggsnu {
       description "Global settings for GGSN-U PICs";
       uses apply-advanced;
       leaf gn-address-range {
         description "Gn network address range for GGSN-U PICs";
         type jt:ipv4prefix;
       }
       leaf gom-address-range {
         description "Gom network address range for GGSN-U PICs";
         type jt:ipv4prefix;
       }
       container redundancy {
         description "Preferred redundancy arrangement for GGSN-U PICs";
         presence "enable redundancy";
         status deprecated;
         uses failover_type;
       }
     }
     leaf gom-routing-instance {
       description "Routing instance for Gom network";
       type string {
       }
     }
     container gtp {
       description "GTP settings";
       uses gtp_type;
     }
     leaf address-reuse-timeout {
       description "Timeout for reuse of IP addresses";
       default "300";
       units "seconds";
       type union {
         type string {
           pattern "<.*>|$.*";
         }
         type uint32 {
           range "120 .. 500";
         }
       }
     }
     leaf no-address-reuse-quarantine {
       description "Don't quarantine addresses before reuse";
       type empty;
     }
     container ipv6-router-advertisement {
       description "IPv6 router advertisement parameters";
       uses apply-advanced;
       leaf maximum-router-advertisement-interval {
         description "Maximum interval between router advertisements";
         default "21600";
         units "seconds";
         type union {
           type string {
             pattern "<.*>|$.*";
           }
           type uint32 {
             range "5400 .. 21600";
           }
         }
       }
       leaf minimum-router-advertisement-interval {
         description "Minimum interval between router advertisements";
         default "16200";
         units "seconds";
         type union {
           type string {
             pattern "<.*>|$.*";
           }
           type uint32 {
             range "3600 .. 16200";
           }
         }
       }
       leaf maximum-initial-router-advertisement-interval {
         description "Maximum interval between initial router advertisements";
         default "10";
         units "seconds";
         type union {
           type string {
             pattern "<.*>|$.*";
           }
           type uint32 {
             range "10 .. 16";
           }
         }
       }
       leaf maximum-initial-router-advertisements {
         description "Maximum number of initial router advertisements";
         default "3";
         type union {
           type string {
             pattern "<.*>|$.*";
           }
           type uint32 {
             range "2 .. 5";
           }
         }
       }
       leaf link-local-interface-identifier {
         description "Interface identifier for GGSN-U PIC link-local addresses";
         default "::1";
         type jt:ipv6addr;
       }
       leaf reachable-time {
         description "Value to be placed in Reachable Time field";
         default "0";
         units "milliseconds";
         type union {
           type string {
             pattern "<.*>|$.*";
           }
           type uint32 {
             range "0 .. 3600000";
           }
         }
       }
       leaf retransmission-timer {
         description "Value to be placed in Retrans Timer field";
         default "0";
         units "milliseconds";
         type union {
           type uint32;
           type string {
             pattern "<.*>|$.*";
           }
         }
       }
       leaf router-lifetime {
         description "Value to be placed in Router Lifetime field";
         default "21840";
         units "seconds";
         type union {
           type string {
             pattern "<.*>|$.*";
           }
           type uint32 {
             range "5400 .. 21840";
           }
         }
       }
       leaf current-hop-limit {
         description "Value to be placed in Cur Hop Limit field";
         default "0";
         type union {
           type string {
             pattern "<.*>|$.*";
           }
           type uint32 {
             range "0 .. 3";
           }
         }
       }
     }
     list logical-apn {
       key name;
       description "Logical access point name configuration";
       max-elements 200;
       uses logapn_type;
     }
     choice ggsn-mcc-plmn {
       case case_1 {
         leaf mcc-mnc {
           description "Mobile Country Code and Mobile Network Code";
           status deprecated;
           type string {
           }
         }
       }
       case case_2 {
         leaf ggsn-plmn-id {
           description "GGSN Public Land Mobile Network identifier";
           type string {
           }
         }
       }
     }
     list plmn {
       key name;
       ordered-by user;
       description "PLMN network data";
       uses plmn_type;
     }
     container pdp-context {
       description "PDP context settings";
       uses pdp_context_type;
     }
     container radius {
       description "RADIUS settings";
       uses apply-advanced;
       list server {
         key name;
         ordered-by user;
         description "Shared RADIUS server configuration";
         max-elements 9999;
         uses radius_shared_type;
       }
     }
     container service-based-charging {
       description "Service-based charging settings";
       uses sbcc_node_type;
     }
     list sgsn {
       key name;
       description "SGSN settings";
       uses sgsn_type;
     }
     list rule-space {
       key name;
       ordered-by user;
       description "Rule space configuration for charging control";
       max-elements 64;
       uses rule_space_type;
     }
     list service-set {
       key name;
       ordered-by user;
       description "Service set configuration for packet inspection";
       uses service_set_type;
     }
     container service-identification {
       description "Service identification configuration for packet inspection";
       uses service_identification_type;
     }
     container fault-management {
       presence "enable fault-management";
       description "Settings for fault management";
       uses apply-advanced;
       container alarm {
         presence "enable alarm";
         description "Settings for alarms";
         uses apply-advanced;
         container service-based-charging {
           presence "enable service-based-charging";
           description "Settings for service-based-charging related alarms";
           uses apply-advanced;
           leaf no-invalid-service-context-id-ccr {
             description "Do not issue alarm on invalid service-context-id in CCR";
             type empty;
           }
           leaf invalid-rating-group-ccr {
             description "Issue alarm on invalid rating group in CCR";
             type empty;
           }
           leaf no-invalid-rating-group-cca {
             description "Do not issue alarm on invalid rating group in CCA";
             type empty;
           }
           leaf no-invalid-cca {
             description "Do not issue alarm on invalid CCA";
             type empty;
           }
           leaf no-invalid-rule-space-cca {
             description "Do not issue alarm on invalid rule-space CCA";
             type empty;
           }
           container error-indication-cca {
             presence "enable error-indication-cca";
             description "Codes for error indication CCA";
             leaf-list error-codes {
               ordered-by user;
               description "Error codes";
               type string {
                 length "1 .. 11";
               }
               max-elements 64;
             }
           }
         }
       }
     }
   }
   grouping apn_type {
     leaf name {
       description "Access point name";
       type string {
       }
     }
     uses apply-advanced;
     leaf access-type {
       description "User access to the APN";
       status deprecated;
       default "restricted";
       type enumeration {
         enum "public" {
           description "User does not need to be subscribed for APN";
           status deprecated;
         }
         enum "from-user" {
           description "Can choose which APN to connect";
           status deprecated;
         }
         enum "from-sgsn" {
           description "Can connect to default APN for the SGSN";
           status deprecated;
         }
         enum "restricted" {
           description "Admit only users subscribed for APN";
           status deprecated;
         }
       }
     }
     container access-restrictions {
       description "Settings for APN access restrictions. ";
       uses apply-advanced;
       leaf selection-mode {
         description "User access to the APN";
         default "restricted";
         type enumeration {
           enum "public" {
             description "User does not need to be subscribed for APN";
           }
           enum "from-user" {
             description "Can choose which APN to connect";
           }
           enum "from-sgsn" {
             description "Can connect to default APN for the SGSN";
           }
           enum "restricted" {
             description "Admit only users subscribed for APN";
           }
         }
       }
       container radius-assisted-apn-selection {
         presence "enable radius-assisted-apn-selection";
         description "Enable RADIUS assisted APN selection";
         uses apply-advanced;
         leaf default {
           description "Default APN name for radius assisted APN selection";
           type string {
           }
         }
       }
     }
     leaf routing-instance {
       description "Routing instance for in-APN traffic";
       type string {
       }
     }
     leaf gi-address-range {
       description "IPv4 address range to use in APN routing instance";
       type jt:ipv4prefix;
     }
     container pdp-context {
       description "APN-specific PDP context settings";
       uses apply-advanced;
       leaf creation {
         description "PDP context creation state";
         type enumeration {
           enum "unblocked" {
             description "No restrictions on PDP context creation";
           }
           enum "blocked" {
             description "New PDP context creation fully blocked";
           }
         }
       }
       leaf pdp-type {
         description "PDP context type";
         type enumeration {
           enum "ipv4" {
             description "IPv4 PDP context type";
           }
           enum "ipv6" {
             description "IPv6 PDP context type";
           }
           enum "ipv4+ipv6" {
             description "IPv4 and IPv6 PDP contexts";
           }
         }
       }
       leaf limit {
         description "Maximum active PDP contexts";
         type union {
           type string {
             pattern "<.*>|$.*";
           }
           type uint32 {
             range "1 .. 4294967295";
           }
         }
       }
       list address {
         key name;
         ordered-by user;
         description "APN IPv4 address range";
         max-elements 99;
         uses apn_address_type;
       }
       list ipv6-address {
         key name;
         ordered-by user;
         description "APN IPv6 address range";
         max-elements 99;
         uses apn_ipv6_address_type;
       }
       container policing {
         description "Policing settings";
         uses policing_apn_type;
       }
       container session-management {
         description "Session management settings";
         status deprecated;
         uses apply-advanced;
         choice idle-control {
           case case_1 {
             leaf idle-timeout {
               description "Maximum consecutive idle minutes for a context";
               units "minutes";
               type union {
                 type string {
                   pattern "<.*>|$.*";
                 }
                 type uint32 {
                   range "1 .. 525600";
                 }
               }
             }
           }
           case case_2 {
             leaf no-idle-supervision {
               description "Don't limit lifetime of idle PDP contexts";
               type empty;
             }
           }
         }
         choice session-control {
           case case_1 {
             leaf session-timeout {
               description "Maximum duration for a context";
               units "minutes";
               type union {
                 type string {
                   pattern "<.*>|$.*";
                 }
                 type uint32 {
                   range "15 .. 1440";
                 }
               }
             }
           }
           case case_2 {
             leaf no-session-supervision {
               description "Don't limit lifetime of PDP contexts";
               type empty;
             }
           }
         }
         leaf measurement-type {
           description "Point of reference for idle time and duration measurement";
           type enumeration {
             enum "since-creation" {
               description "Relative to the PDP context creation time";
             }
             enum "since-update" {
               description "Relative to the last PDP context update time";
             }
           }
         }
       }
       container session-control {
         description "Session control settings";
         uses session_management_apn_type;
       }
       leaf address-allocation {
         description "Method used to allocate IPv4 addresses to PDP contexts";
         type enumeration {
           enum "static" {
             description "Only static addresses accepted";
           }
           enum "radius" {
             description "RADIUS authentication assigns addresses";
           }
           enum "dhcp-client" {
             description "DHCP server assigns addresses";
           }
           enum "local-pool" {
             description "GGSN assigns addresses from local pool";
           }
           enum "l2tp" {
             description "L2TP assigns addresses";
           }
         }
       }
       leaf ipv6-address-allocation {
         description "Method used to allocate IPv6 addresses to PDP contexts";
         type enumeration {
           enum "radius" {
             description "RADIUS authentication assigns addresses";
           }
           enum "local-pool" {
             description "GGSN assigns addresses from local pool";
           }
         }
       }
       leaf allocation-prefix {
         description "Subnet prefix to use for GGSNU distribution";
         type union {
           type string {
             pattern "<.*>|$.*";
           }
           type uint32 {
             range "21 .. 128";
           }
         }
       }
       leaf allocation-prefix-method {
         description "Prefix allocation method to use for GGSNU distribution";
         type enumeration {
           enum "slices" {
             description "Base slice allocation with even number of slices between GGSNUs";
           }
           enum "load" {
             description "Base slice allocation with even load between GGSNUs";
           }
         }
       }
       leaf load-factor {
         description "PDP context load factor for GGSNU distribution";
         type union {
           type string {
             pattern "<.*>|$.*";
           }
           type uint32 {
             range "1 .. 255";
           }
         }
       }
       leaf bandwidth-override {
         description "Override requested PDP context bandwidth";
         status deprecated;
         units "kbps";
         type union {
           type string {
             pattern "<.*>|$.*";
           }
           type uint32 {
             range "10 .. 700000";
           }
         }
       }
       leaf alarm-limit {
         description "APN utilization limit at which to raise alarm";
         units "percent";
         type union {
           type string {
             pattern "<.*>|$.*";
           }
           type uint32 {
             range "80 .. 100";
           }
         }
       }
       container signaling {
         description "PDP-Context signaling options for this APN";
         choice ggsn-deletes-choice {
           case case_1 {
             leaf ggsn-deletes-per-second {
               description "GGSN-initiated deletions per second per session controller";
               type union {
                 type string {
                   pattern "<.*>|$.*";
                 }
                 type uint32 {
                   range "1 .. 5000";
                 }
               }
             }
           }
           case case_2 {
             leaf ggsn-deletes-no-limit {
               description "No limit for GGSN-initiated deletions";
               type empty;
             }
           }
         }
         leaf sgsn-creates-per-second {
           description "Maximum SGSN creates per second per session controller";
           type union {
             type string {
               pattern "<.*>|$.*";
             }
             type uint32 {
               range "0 .. 5000";
             }
           }
         }
       }
       leaf allow-framed-ip-netmask {
         description "Allow framed-IP-netmask attribute from RADIUS";
         type empty;
       }
     }
     container l2tp {
       description "L2TP settings";
       uses apply-advanced;
       leaf l2tp-routing-instance {
         description "Routing instance for the L2TP network";
         type string {
         }
       }
       leaf hide-avps {
         description "Hide L2TP AVPs";
         type empty;
       }
       leaf lac-address {
         description "GGSN (LAC) IP address";
         type jt:ipv4addr;
       }
       list lns-server {
         key name;
         ordered-by user;
         description "L2TP network server";
         max-elements 2;
         uses lns_server_type;
       }
       leaf secret {
         description "Shared secret for tunnel authentication and AVP hiding";
         type jt:unreadable;
       }
       leaf hello-interval {
         description "Keepalive timer for the L2TP tunnel";
         default "30";
         units "seconds";
         type union {
           type string {
             pattern "<.*>|$.*";
           }
           type uint32 {
             range "0 .. 3600";
           }
         }
       }
       leaf receive-window {
         description "Size of receive window for the L2TP tunnel";
         default "16";
         type union {
           type string {
             pattern "<.*>|$.*";
           }
           type uint16 {
             range "1 .. 128";
           }
         }
       }
       leaf max-retry {
         description "Maximum number of retry attempts during L2TP negotiation";
         default "4";
         type union {
           type string {
             pattern "<.*>|$.*";
           }
           type uint32 {
             range "0 .. 60";
           }
         }
       }
       leaf max-retry-timeout {
         description "Maximum timeout between control channel retransmissions";
         default "60";
         units "seconds";
         type union {
           type string {
             pattern "<.*>|$.*";
           }
           type uint32 {
             range "0 .. 3600";
           }
         }
       }
       leaf copy-inner-ip-dscp {
         description "Copy DSCP field from inner to outer IP-header";
         type empty;
       }
       container ppp {
         description "Point-to-point protocol settings";
         uses apply-advanced;
         leaf retry-timeout {
           description "Timeout for a response during PPP negotiation";
           default "2";
           units "seconds";
           type union {
             type string {
               pattern "<.*>|$.*";
             }
             type uint32 {
               range "1 .. 300";
             }
           }
         }
         leaf max-retry {
           description "Maximum number of retry attempts during PPP negotiation";
           default "5";
           type union {
             type string {
               pattern "<.*>|$.*";
             }
             type uint32 {
               range "0 .. 60";
             }
           }
         }
         leaf mru {
           description "Maximum value for negotiable receive unit";
           default "1450";
           type union {
             type string {
               pattern "<.*>|$.*";
             }
             type uint32 {
               range "500 .. 1500";
             }
           }
         }
         leaf user-name {
           description "Default user name for user authentication";
           type string {
           }
         }
         leaf user-password {
           description "Default user password for user authentication";
           type jt:unreadable;
         }
       }
     }
     container radius {
       description "RADIUS configuration";
       uses apply-advanced;
       leaf retry-method {
         description "RADIUS retry scheme settings";
         default "single-server";
         type enumeration {
           enum "single-server" {
             description "Single server retry scheme";
           }
           enum "multiple-server" {
             description "Multiple server retry scheme";
           }
         }
       }
       leaf load-balancing {
         description "Use load balancing to distribute requests";
         type empty;
       }
       container authentication {
         description "RADIUS authentication settings";
         uses apply-advanced;
         container message-attributes {
           description "Attributes in RADIUS messages";
           uses apply-advanced;
           leaf apn-identifier {
             description "Include APN name";
             type empty;
           }
           leaf apn-selection-mode {
             description "Include APN selection information";
             type empty;
           }
           leaf charging-gateway {
             description "Include charging gateway address";
             type empty;
           }
           leaf charging-characteristics {
             description "Include charging characteristics";
             type empty;
           }
           leaf ggsn-address {
             description "Include GGSN node address";
             type empty;
           }
           leaf gprs-quality-of-service {
             description "Include GPRS quality of service";
             status deprecated;
             type empty;
           }
           leaf gprs-qos {
             description "Include GPRS quality of service";
             type empty;
           }
           leaf gprs-qos-extended {
             description "Include GPRS extended quality of service";
             type empty;
           }
           leaf imsi {
             description "Include IMSI";
             type empty;
           }
           leaf ms-timezone {
             description "Include MS timezone";
             type empty;
           }
           leaf user-location-info {
             description "Include user location info";
             type empty;
           }
           choice user-plmn-mcc {
             case case_1 {
               leaf mcc-mnc {
                 description "Include MCC-MNC information";
                 status deprecated;
                 type empty;
               }
             }
             case case_2 {
               leaf user-plmn-id {
                 description "Include User Public Land Mobile Network identifier";
                 type empty;
               }
             }
           }
           choice msisdn_choice {
             case case_1 {
               leaf msisdn {
                 description "Include MSISDN";
                 type empty;
               }
             }
             case case_2 {
               leaf msisdn-value {
                 description "MSISDN set to this value in RADIUS messages";
                 type string {
                 }
               }
             }
           }
           leaf nsapi {
             description "Include NSAPI";
             type empty;
           }
           leaf pdp-type {
             description "Include PDP type";
             type empty;
           }
           leaf signaling-sgsn {
             description "Include signaling SGSN address";
             type empty;
           }
           leaf user-value {
             description "User name set to this value in RADIUS messages";
             type string {
             }
           }
           choice nas_port_choice {
             case case_1 {
               leaf nas-port {
                 description "Include NAS port attribute";
                 type empty;
               }
             }
             case case_2 {
               leaf nas-port-value {
                 description "NAS port set to this value in RADIUS messages";
                 type string {
                 }
               }
             }
           }
           leaf nas-ip-address-value {
             description "NAS IP address set to this value in RADIUS messages";
             type jt:ipv4addr;
           }
           leaf sgsn-plmn-id {
             description "Include the SGSN Public Land Mobile Network identifier";
             type empty;
           }
           leaf ggsn-plmn-id {
             description "Include the GGSN Public Land Mobile Network identifier";
             type empty;
           }
           leaf rat-type {
             description "Include the radio access technology type in the request";
             type empty;
           }
           leaf imei-sv {
             description "Include the IMEI-SV in the request";
             type empty;
           }
           leaf override-user-info {
             description "Override username and password received in PCO";
             type empty;
           }
           leaf user-password-value {
             description "User password set to this value in messages";
             type string {
             }
           }
         }
         choice auth_shared_or_inband_choice {
           case case_1 {
             list server {
               key name;
               ordered-by user;
               description "Server for authentication requests";
               max-elements 10;
               uses radius_type;
             }
           }
           case case_2 {
             leaf shared-server {
               description "Shared RADIUS server for authentication";
               type string {
                 length "1 .. 64";
               }
             }
           }
         }
       }
       container accounting {
         description "RADIUS accounting settings";
         uses apply-advanced;
         container message-attributes {
           description "Attributes in RADIUS messages";
           uses apply-advanced;
           leaf apn-identifier {
             description "Include APN name";
             type empty;
           }
           leaf apn-selection-mode {
             description "Include APN selection information";
             type empty;
           }
           leaf charging-gateway {
             description "Include charging gateway address";
             type empty;
           }
           leaf charging-characteristics {
             description "Include charging characteristics";
             type empty;
           }
           leaf ggsn-address {
             description "Include GGSN node address";
             type empty;
           }
           leaf gprs-quality-of-service {
             description "Include GPRS quality of service";
             status deprecated;
             type empty;
           }
           leaf gprs-qos {
             description "Include GPRS quality of service";
             type empty;
           }
           leaf gprs-qos-extended {
             description "Include GPRS extended quality of service";
             type empty;
           }
           leaf imsi {
             description "Include IMSI";
             type empty;
           }
           leaf ms-timezone {
             description "Include MS timezone";
             type empty;
           }
           leaf user-location-info {
             description "Include user location info";
             type empty;
           }
           choice user-plmn-mcc {
             case case_1 {
               leaf mcc-mnc {
                 description "Include MCC-MNC information";
                 status deprecated;
                 type empty;
               }
             }
             case case_2 {
               leaf user-plmn-id {
                 description "Include User Public Land Mobile Network identifier";
                 type empty;
               }
             }
           }
           choice msisdn_choice {
             case case_1 {
               leaf msisdn {
                 description "Include MSISDN";
                 type empty;
               }
             }
             case case_2 {
               leaf msisdn-value {
                 description "MSISDN set to this value in RADIUS messages";
                 type string {
                 }
               }
             }
           }
           leaf nsapi {
             description "Include NSAPI";
             type empty;
           }
           leaf pdp-type {
             description "Include PDP type";
             type empty;
           }
           leaf signaling-sgsn {
             description "Include signaling SGSN address";
             type empty;
           }
           leaf user-value {
             description "User name set to this value in RADIUS messages";
             type string {
             }
           }
           choice nas_port_choice {
             case case_1 {
               leaf nas-port {
                 description "Include NAS port attribute";
                 type empty;
               }
             }
             case case_2 {
               leaf nas-port-value {
                 description "NAS port set to this value in RADIUS messages";
                 type string {
                 }
               }
             }
           }
           leaf nas-ip-address-value {
             description "NAS IP address set to this value in RADIUS messages";
             type jt:ipv4addr;
           }
           leaf sgsn-plmn-id {
             description "Include the SGSN Public Land Mobile Network identifier";
             type empty;
           }
           leaf ggsn-plmn-id {
             description "Include the GGSN Public Land Mobile Network identifier";
             type empty;
           }
           leaf rat-type {
             description "Include the radio access technology type in the request";
             type empty;
           }
           leaf imei-sv {
             description "Include the IMEI-SV in the request";
             type empty;
           }
           leaf override-user-info {
             description "Override username and password received in PCO";
             type empty;
           }
           leaf charging-identifier {
             description "Include user charging identifier";
             type empty;
           }
           leaf acct-input-octets {
             description "Include the number of octets sent";
             type empty;
           }
           leaf acct-output-octets {
             description "Include the number of octets received";
             type empty;
           }
           leaf acct-output-packets {
             description "Include the number of output packets";
             type empty;
           }
           leaf acct-input-packets {
             description "Include the number of input packets";
             type empty;
           }
           leaf negotiated-dscp {
             description "Include negotiated DSCP";
             type empty;
           }
           leaf packet-filter {
             description "Include packet filter";
             type empty;
           }
           leaf session-stop {
             description "Send session stop message";
             type empty;
           }
           leaf include-session-time-in-all {
             description "Include session-time in all RADIUS accounting messages";
             type empty;
           }
         }
         choice acct_shared_or_inband_choice {
           case case_1 {
             list server {
               key name;
               ordered-by user;
               description "Server for accounting requests";
               max-elements 10;
               uses radius_type;
             }
           }
           case case_2 {
             leaf shared-server {
               description "Name of shared RADIUS server";
               type string {
                 length "1 .. 64";
               }
             }
           }
         }
         leaf message-for-every-context {
           description "Send start/interim/stop message for every PDP context";
           type empty;
         }
         leaf no-accounting-on {
           description "Don't send accounting on and off messages";
           type empty;
         }
         container interim-update {
           description "Send interim accounting requests";
           uses apply-advanced;
           leaf transfer-interval {
             description "Send RADIUS interim update periodically";
             units "minutes";
             type union {
               type string {
                 pattern "<.*>|$.*";
               }
               type uint32 {
                 range "30 .. 1440";
               }
             }
           }
           leaf transfer-on-update {
             description "Send RADIUS interim update when receiving PDP context update request";
             type empty;
           }
         }
         leaf un-acknowledge {
           description "Run in Un-Acknowledge mode";
           type empty;
         }
       }
       leaf accept-disconnect {
         description "Perform PDP context deletion on receiving a disconnect request from a RADIUS server";
         type empty;
       }
     }
     container dhcp {
       description "DHCP server configuration";
       uses apply-advanced;
       choice ob_or_ib_dhcp_choice {
         case case_1 {
           list server {
             key name;
             ordered-by user;
             description "DHCP server for APN";
             max-elements 3;
             uses dhcp_server_type;
           }
         }
         case case_2 {
           leaf-list shared-server {
             ordered-by user;
             description "Shared DHCP server configuration";
             type string {
               length "1 .. 64";
             }
             max-elements 3;
           }
         }
       }
       leaf gtp-cpic-ipaddress {
         description "Include GTP-C_PIC_IP-address in Client ID parameter (Option 61)";
         type empty;
       }
       leaf imsi {
         description "Include IMSI in Client ID parameter (Option 61)";
         type empty;
       }
       leaf nsapi {
         description "Include NSAPI in Client ID parameter (Option 61)";
         type empty;
       }
       leaf msisdn {
         description "Include MSISDN in Client ID parameter (Option 61)";
         type empty;
       }
     }
     list bandwidth-constraint {
       key name;
       ordered-by user;
       description "APN bandwidth constraints";
       uses bandconst_type;
     }
     container quality-of-service {
       description "APN quality-of-service mapping";
       status deprecated;
       uses qosmap_type;
     }
     container uplink-dscp-remapping {
       description "Gi quality-of-service to DSCP remapping";
       uses dscp_qos_map_type;
     }
     leaf disable-uplink-dscp-remapping {
       description "Do not change DSCP in uplink packets";
       type empty;
     }
     list name-server {
       key name;
       ordered-by user;
       description "IPv4 DNS name server";
       max-elements 2;
       uses name_server_type;
     }
     list ipv6-name-server {
       key name;
       ordered-by user;
       description "IPv6 DNS name server";
       max-elements 2;
       uses ipv6_name_server_type;
     }
     container service-based-charging {
       description "Service-based charging configuration";
       uses sbcc_apn_type;
     }
     leaf-list allow-rule-space {
       ordered-by user;
       description "Rule space authorized for the APN";
       type string;
     }
     container charging {
       description "APN-specific charging configuration";
       uses apply-advanced;
       leaf select-gn-apn {
         description "Include Gn APN in CDR";
         type empty;
       }
       leaf allow-cc-from-radius {
         description "Enable charging characteristics from RADIUS";
         type empty;
       }
       container imsi-based-characteristics {
         description "Charging characteristic based on IMSI";
         uses apply-advanced;
         choice imsi-based-characteristics-choice {
           case case_1 {
             leaf disable {
               description "Disable IMSI-based selection of charging characteristics";
               type empty;
             }
           }
           case case_2 {
             leaf override {
               description "Force IMSI-based selection of charging characteristics";
               type empty;
             }
           }
         }
       }
     }
     container roaming {
       description "Roaming class settings";
       uses roaming_type;
     }
     container sgsn {
       description "SGSN class settings";
       uses apn_sgsn_type;
     }
     container user-category {
       description "User category settings";
       uses user_category_type;
     }
     container qos-control {
       description "QoS control";
       uses apply-advanced;
       list profile {
         key name;
         description "QoS control profile";
         max-elements 16;
         leaf name {
           description "Profile identifier";
           type string {
             length "1 .. 64";
           }
         }
         uses apply-advanced;
         container default {
           presence "enable default";
           description "Default QoS";
           uses apply-advanced;
           list quality-of-service {
             key name;
             description "Quality of service";
             uses fbc_qos_control_qos_type;
           }
           container default-quality-of-service {
             description "Default quality of service";
             uses apply-advanced;
             leaf traffic-class {
               description "Traffic class";
               type enumeration {
                 enum "conversational" {
                   description "Conversational quality of service";
                 }
                 enum "streaming" {
                   description "Streaming quality of service";
                 }
                 enum "interactive-1" {
                   description "Interactive priority 1 quality of service";
                 }
                 enum "interactive-2" {
                   description "Interactive priority 2 quality of service";
                 }
                 enum "interactive-3" {
                   description "Interactive priority 3 quality of service";
                 }
                 enum "background" {
                   description "Background quality of service";
                 }
               }
             }
             leaf policy {
               description "QoS policy";
               default "must";
               type enumeration {
                 enum "must" {
                   description "Exact QoS required";
                 }
                 enum "min-required" {
                   description "Minimum QoS required";
                 }
                 enum "max-allowed" {
                   description "Maximum QoS allowed";
                 }
               }
             }
             leaf maximum-bit-rate-uplink {
               description "Maximum uplink bit rate";
               units "kilobits";
               type union {
                 type string {
                   pattern "<.*>|$.*";
                 }
                 type uint32 {
                   range "0 .. 8640";
                 }
               }
             }
             leaf maximum-bit-rate-downlink {
               description "Maximum downlink bit rate";
               units "kilobits";
               type union {
                 type string {
                   pattern "<.*>|$.*";
                 }
                 type uint32 {
                   range "0 .. 16000";
                 }
               }
             }
             leaf guaranteed-bit-rate-uplink {
               description "Guaranteed uplink bit rate";
               units "kilobits";
               type union {
                 type string {
                   pattern "<.*>|$.*";
                 }
                 type uint32 {
                   range "0 .. 8640";
                 }
               }
             }
             leaf guaranteed-bit-rate-downlink {
               description "Guaranteed downlink bit rate";
               units "kilobits";
               type union {
                 type string {
                   pattern "<.*>|$.*";
                 }
                 type uint32 {
                   range "0 .. 16000";
                 }
               }
             }
             leaf transfer-delay {
               description "Transfer delay";
               units "milliseconds";
               type union {
                 type string {
                   pattern "<.*>|$.*";
                 }
                 type uint32 {
                   range "10 .. 4000";
                 }
               }
             }
           }
         }
         list roaming-class {
           key name;
           description "Roaming class";
           max-elements 24;
           leaf name {
             description "Roaming class identifier";
             type union {
               type string {
                 pattern "<.*>|$.*";
               }
               type uint32 {
                 range "1 .. 24";
               }
             }
           }
           uses apply-advanced;
           list quality-of-service {
             key name;
             description "Quality of service";
             uses fbc_qos_control_qos_type;
           }
           container default-quality-of-service {
             description "Default quality of service";
             uses apply-advanced;
             leaf traffic-class {
               description "Traffic class";
               type enumeration {
                 enum "conversational" {
                   description "Conversational quality of service";
                 }
                 enum "streaming" {
                   description "Streaming quality of service";
                 }
                 enum "interactive-1" {
                   description "Interactive priority 1 quality of service";
                 }
                 enum "interactive-2" {
                   description "Interactive priority 2 quality of service";
                 }
                 enum "interactive-3" {
                   description "Interactive priority 3 quality of service";
                 }
                 enum "background" {
                   description "Background quality of service";
                 }
               }
             }
             leaf policy {
               description "QoS policy";
               default "must";
               type enumeration {
                 enum "must" {
                   description "Exact QoS required";
                 }
                 enum "min-required" {
                   description "Minimum QoS required";
                 }
                 enum "max-allowed" {
                   description "Maximum QoS allowed";
                 }
               }
             }
             leaf maximum-bit-rate-uplink {
               description "Maximum uplink bit rate";
               units "kilobits";
               type union {
                 type string {
                   pattern "<.*>|$.*";
                 }
                 type uint32 {
                   range "0 .. 8640";
                 }
               }
             }
             leaf maximum-bit-rate-downlink {
               description "Maximum downlink bit rate";
               units "kilobits";
               type union {
                 type string {
                   pattern "<.*>|$.*";
                 }
                 type uint32 {
                   range "0 .. 16000";
                 }
               }
             }
             leaf guaranteed-bit-rate-uplink {
               description "Guaranteed uplink bit rate";
               units "kilobits";
               type union {
                 type string {
                   pattern "<.*>|$.*";
                 }
                 type uint32 {
                   range "0 .. 8640";
                 }
               }
             }
             leaf guaranteed-bit-rate-downlink {
               description "Guaranteed downlink bit rate";
               units "kilobits";
               type union {
                 type string {
                   pattern "<.*>|$.*";
                 }
                 type uint32 {
                   range "0 .. 16000";
                 }
               }
             }
             leaf transfer-delay {
               description "Transfer delay";
               units "milliseconds";
               type union {
                 type string {
                   pattern "<.*>|$.*";
                 }
                 type uint32 {
                   range "10 .. 4000";
                 }
               }
             }
           }
         }
         list sgsn-class {
           key name;
           description "SGSN class";
           max-elements 24;
           leaf name {
             description "SGSN class identifier";
             type union {
               type string {
                 pattern "<.*>|$.*";
               }
               type uint32 {
                 range "1 .. 24";
               }
             }
           }
           uses apply-advanced;
           list quality-of-service {
             key name;
             description "Quality of service";
             uses fbc_qos_control_qos_type;
           }
           container default-quality-of-service {
             description "Default quality of service";
             uses apply-advanced;
             leaf traffic-class {
               description "Traffic class";
               type enumeration {
                 enum "conversational" {
                   description "Conversational quality of service";
                 }
                 enum "streaming" {
                   description "Streaming quality of service";
                 }
                 enum "interactive-1" {
                   description "Interactive priority 1 quality of service";
                 }
                 enum "interactive-2" {
                   description "Interactive priority 2 quality of service";
                 }
                 enum "interactive-3" {
                   description "Interactive priority 3 quality of service";
                 }
                 enum "background" {
                   description "Background quality of service";
                 }
               }
             }
             leaf policy {
               description "QoS policy";
               default "must";
               type enumeration {
                 enum "must" {
                   description "Exact QoS required";
                 }
                 enum "min-required" {
                   description "Minimum QoS required";
                 }
                 enum "max-allowed" {
                   description "Maximum QoS allowed";
                 }
               }
             }
             leaf maximum-bit-rate-uplink {
               description "Maximum uplink bit rate";
               units "kilobits";
               type union {
                 type string {
                   pattern "<.*>|$.*";
                 }
                 type uint32 {
                   range "0 .. 8640";
                 }
               }
             }
             leaf maximum-bit-rate-downlink {
               description "Maximum downlink bit rate";
               units "kilobits";
               type union {
                 type string {
                   pattern "<.*>|$.*";
                 }
                 type uint32 {
                   range "0 .. 16000";
                 }
               }
             }
             leaf guaranteed-bit-rate-uplink {
               description "Guaranteed uplink bit rate";
               units "kilobits";
               type union {
                 type string {
                   pattern "<.*>|$.*";
                 }
                 type uint32 {
                   range "0 .. 8640";
                 }
               }
             }
             leaf guaranteed-bit-rate-downlink {
               description "Guaranteed downlink bit rate";
               units "kilobits";
               type union {
                 type string {
                   pattern "<.*>|$.*";
                 }
                 type uint32 {
                   range "0 .. 16000";
                 }
               }
             }
             leaf transfer-delay {
               description "Transfer delay";
               units "milliseconds";
               type union {
                 type string {
                   pattern "<.*>|$.*";
                 }
                 type uint32 {
                   range "10 .. 4000";
                 }
               }
             }
           }
         }
       }
     }
     container p-cscf {
       description "P-CSCF settings";
       uses p_cscf_apn_type;
     }
   }
   grouping apn_address_type {
     leaf name {
       description "Address range for APN network";
       type jt:ipv4prefix;
     }
     leaf static {
       description "Range is only for static contexts";
       type empty;
     }
     leaf subnet-name {
       description "Name of the subnet";
       type string {
         length "1 .. 64";
       }
     }
   }
   grouping apn_ipv6_address_type {
     leaf name {
       description "Address range for APN network";
       type jt:ipv6prefix;
     }
     leaf static {
       description "Range is only for static contexts";
       type empty;
     }
     leaf subnet-name {
       description "Name of the subnet";
       type string {
         length "1 .. 64";
       }
     }
   }
   grouping apn_sgsn_type {
     uses apply-advanced;
     list sgsn-class {
       key name;
       description "SGSN class";
       uses apn_sgsn_class_type;
     }
   }
   grouping apn_sgsn_class_type {
     leaf name {
       description "SGSN class identifier";
       type union {
         type string {
           pattern "<.*>|$.*";
         }
         type uint32 {
           range "1 .. 24";
         }
       }
     }
     uses apply-advanced;
     list sgsn-address {
       key name;
       ordered-by user;
       description "SGSN address associated with class";
       leaf name {
         description "SGSN address or address prefix";
         type jt:ipv4prefix;
       }
       uses apply-advanced;
       leaf-list rat-types {
         description "Radio access type (RAT) global defaults";
         type enumeration {
           enum "unknown" {
             description "Unknown or missing";
           }
           enum "utran" {
             description "WCDMA/UMTS Terrestrial radio access network";
           }
           enum "geran" {
             description "GSM/EDGE radio access network";
           }
           enum "wlan" {
             description "Wireless local area network";
           }
         }
       }
     }
   }
   grouping bandconst_type {
     leaf name {
       description "Type of traffic to limit";
       type enumeration {
         enum "ef" {
           description "Expedited forwarding";
         }
         enum "af1" {
           description "Assured forwarding class 1";
         }
         enum "af2" {
           description "Assured forwarding class 2";
         }
       }
     }
     leaf limit {
       description "Limit for traffic";
       units "kilobits";
       type union {
         type string {
           pattern "<.*>|$.*";
         }
         type uint32 {
           range "100 .. 10000000";
         }
       }
     }
   }
   grouping charging_type {
     uses apply-advanced;
     container cdr-attribute {
       description "Attributes in charging data records";
       uses apply-advanced;
       leaf no-reduced-partial {
         description "Generate fully qualified partial CDRs only";
         type empty;
       }
       leaf no-node-identifier {
         description "Don't include node identifier";
         type empty;
       }
       leaf no-local-record-sequence-number {
         description "Don't include local record sequence number";
         type empty;
       }
       choice msisdn-choice {
         case case_1 {
           leaf no-msisdn {
             description "Don't include MSISDN";
             type empty;
           }
         }
         case case_2 {
           leaf msisdn-always {
             description "Always include MSISDN even if there is no change";
             type empty;
           }
         }
       }
       leaf no-apn-network-identifier {
         description "Don't include network identifier of APN";
         type empty;
       }
       leaf no-pdp-type {
         description "Don't include PDP type";
         type empty;
       }
       leaf no-pdp-address {
         description "Don't include PDP address";
         type empty;
       }
       leaf no-dynamic-address-flag {
         description "Don't include indication if served PDP address is dynamic";
         type empty;
       }
       choice t-volume-choice {
         case case_1 {
           leaf no-traffic-volumes {
             description "Don't include list of traffic data volumes";
             type empty;
           }
         }
         case case_2 {
           container traffic-volumes {
             description "Include list of traffic data volumes";
             uses apply-advanced;
             leaf qos-always {
               description "Always include QoS information even if there is no change";
               type empty;
             }
           }
         }
       }
       leaf no-apn-selection-mode {
         description "Don't include index indicating how the APN was selected";
         type empty;
       }
       leaf no-cc-selection-mode {
         description "Don't include information about how charging characteristics were selected";
         type empty;
       }
       leaf record-extension {
         description "Include record extension";
         type empty;
       }
       leaf no-sgsn-plmn-id {
         description "Don't include the SGSN PLMN identifier";
         type empty;
       }
       leaf apn-encoding {
         description "Method of ASN.1 encoding of the APN field in G-CDR";
         type enumeration {
           enum "dot-notation" {
             description "Encode dot as '.'";
           }
           enum "digit-notation" {
             description "Encode dot as digit";
           }
         }
       }
       container record-extension-attributes {
         description "Record extension CDR attributes";
         uses apply-advanced;
         leaf user-category {
           description "Include user category";
           type empty;
         }
         leaf bearer-control {
           description "Include bearer control";
           type empty;
         }
         container service-based-charging {
           description "Service-based charging CDR attributes";
           uses apply-advanced;
           leaf service-identifier-volume {
             description "Include volume per service identifier";
             type empty;
           }
           container service-class-volume {
             presence "enable service-class-volume";
             description "Include volume per service class";
             uses apply-advanced;
             leaf include-rate {
               description "Include volume rate per service class";
               type empty;
             }
           }
           container service-class-block {
             presence "enable service-class-block";
             description "Include number of blocks per service class";
             uses apply-advanced;
             leaf include-rate {
               description "Include block-based rate per service class";
               type empty;
             }
             leaf payload-time {
               description "Include actual data transfer start and stop time";
               type empty;
             }
           }
           container block {
             presence "enable block";
             description "Include number of blocks";
             uses apply-advanced;
             leaf include-rate {
               description "Include block-based rate";
               type empty;
             }
             leaf payload-time {
               description "Include actual data transfer start and stop time";
               type empty;
             }
           }
           leaf initial-charge {
             description "Include initial charge";
             type empty;
           }
           leaf volume-limit-action {
             description "Include session policy volume limit action";
             type empty;
           }
           leaf block-based-limit-action {
             description "Include session policy block-based limit action";
             type empty;
           }
         }
         leaf include-uri {
           description "Include URI in CDRs for event-based packet inspection";
           type empty;
         }
         leaf include-redirect-info {
           description "Include redirect information";
           type empty;
         }
       }
       leaf no-external-charging-id {
         description "Don't include external charging id";
         type empty;
       }
       leaf no-ms-time-zone {
         description "Don't include ms time zone";
         type empty;
       }
       leaf no-user-location-information {
         description "Don't include user location information";
         type empty;
       }
       container enhanced-cdr {
         presence "enable enhanced-cdr";
         description "Attribute settings for enhanced CDR";
         uses apply-advanced;
         leaf no-ps-furnish-charging-information {
           description "Don't include PS furnish charging information";
           type empty;
         }
         leaf no-traffic-volume {
           description "Don't include traffic-volume";
           type empty;
         }
         leaf no-service-data {
           description "Don't include service data";
           type empty;
         }
         container service-data-attributes {
           presence "enable service-data-attributes";
           description "Settings for service data attributes";
           uses apply-advanced;
           leaf no-rat-type {
             description "Don't include radio access technology (RAT) type";
             type empty;
           }
           leaf no-sgsn-plmn-id {
             description "Don't include SGSN PLMN ID ";
             type empty;
           }
           leaf no-sgsn-address {
             description "Don't include SGSN address ";
             type empty;
           }
           leaf no-qos-information {
             description "Don't include QoS information ";
             type empty;
           }
           leaf reporting-level {
             description "Level for CDR reporting";
             default "rating-group";
             type enumeration {
               enum "rating-group" {
                 description "Report on rating-group level";
               }
               enum "service-id" {
                 description "Report on service-id level";
               }
             }
           }
           list rule-space {
             key name;
             ordered-by user;
             description "Setting for enhanced CDRs handling in rule-space";
             leaf name {
               description "Apply setting to rule space ";
               type string {
                 length "1 .. 64";
               }
             }
             uses apply-advanced;
             leaf-list service-id-level-reporting {
               ordered-by user;
               description "Report CDRs on SI level";
               type string {
                 length "1 .. 21";
               }
               max-elements 64;
             }
           }
         }
       }
       container service-based-charging {
         description "Service-based charging CDR attributes";
         status deprecated;
         uses apply-advanced;
         leaf identifier-volume {
           description "Include volume per service identifier";
           type empty;
         }
         leaf class-volume {
           description "Include volume per service class";
           type empty;
         }
         leaf rate {
           description "Include rate used for traffic";
           type empty;
         }
         leaf initial-charge {
           description "Include initial charge";
           type empty;
         }
       }
       leaf no-ims-signaling-context {
         description "Don't include IMS signaling context";
         type empty;
       }
       leaf no-rat-type {
         description "Don't include radio access technology (RAT) type";
         type empty;
       }
       leaf no-imei-sv {
         description "Don't include IMEI and software version";
         type empty;
       }
     }
     leaf node {
       description "Identifier for GGSN node";
       status deprecated;
       type string {
       }
     }
     container gtp-prime {
       description "GTP Prime configuration";
       uses apply-advanced;
       leaf keepalive-interval {
         description "Seconds between sending keepalive messages";
         default "60";
         units "seconds";
         type union {
           type string {
             pattern "<.*>|$.*";
           }
           type uint32 {
             range "60 .. 200";
           }
         }
       }
       leaf t3-response-time {
         description "Seconds between control message retries";
         default "20";
         units "seconds";
         type union {
           type string {
             pattern "<.*>|$.*";
           }
           type uint32 {
             range "1 .. 30";
           }
         }
       }
       leaf n3-requests {
         description "Retransmissions allowed for a control message";
         default "5";
         type union {
           type string {
             pattern "<.*>|$.*";
           }
           type uint32 {
             range "1 .. 8";
           }
         }
       }
       leaf diffserv {
         description "DiffServ DSCP for GTP packets";
         default "be";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       choice path-management-choice {
         leaf path-management {
           description "Use path management";
           type empty;
         }
         leaf no-path-management {
           description "Don't use path management";
           type empty;
         }
       }
       leaf version {
         description "GTP Prime version";
         default "v0-20";
         type enumeration {
           enum "v0-20" {
             description "Use GTP Prime version v0 with 20 bytes header";
           }
           enum "v0-6" {
             description "Use GTP Prime version v0 with 6 bytes header";
           }
         }
       }
     }
     leaf charging-format {
       description "Format of charging records";
       default "99";
       type enumeration {
         enum "97" {
           description "Version 97";
         }
         enum "98" {
           description "Version 98";
         }
         enum "99" {
           description "Version 99";
         }
         enum "4" {
           description "Version 4";
         }
         enum "5" {
           description "Version 5";
         }
         enum "6" {
           description "Version 6";
         }
       }
     }
     container charging-log {
       description "Charging records logged to node";
       uses charging_log_type;
     }
     container characteristics {
       description "Account-type charging characteristics";
       uses apply-advanced;
       leaf default {
         description "Profile applied to context if context contains no charging characteristic";
         type enumeration {
           enum "profile0" {
             description "Profile 0";
           }
           enum "profile1" {
             description "Profile 1";
           }
           enum "profile2" {
             description "Profile 2";
           }
           enum "profile3" {
             description "Profile 3";
           }
           enum "profile4" {
             description "Profile 4";
           }
           enum "profile5" {
             description "Profile 5";
           }
           enum "profile6" {
             description "Profile 6";
           }
           enum "profile7" {
             description "Profile 7";
           }
           enum "profile8" {
             description "Profile 8";
           }
           enum "profile9" {
             description "Profile 9";
           }
           enum "profile10" {
             description "Profile 10";
           }
           enum "profile11" {
             description "Profile 11";
           }
           enum "profile12" {
             description "Profile 12";
           }
           enum "profile13" {
             description "Profile 13";
           }
           enum "profile14" {
             description "Profile 14";
           }
           enum "profile15" {
             description "Profile 15";
           }
         }
       }
       container profile8 {
         description "Profile 8 clients";
         uses charging_attr_type;
       }
       container profile4 {
         description "Profile 4 clients";
         uses charging_attr_type;
       }
       container profile1 {
         description "Profile 1 clients";
         uses charging_attr_type;
       }
       container profile2 {
         description "Profile 2 clients";
         uses charging_attr_type;
       }
       container profile0 {
         description "Profile 0 clients";
         uses charging_attr_type;
       }
       container profile3 {
         description "Profile 3 clients";
         uses charging_attr_type;
       }
       container profile5 {
         description "Profile 5 clients";
         uses charging_attr_type;
       }
       container profile6 {
         description "Profile 6 clients";
         uses charging_attr_type;
       }
       container profile7 {
         description "Profile 7 clients";
         uses charging_attr_type;
       }
       container profile9 {
         description "Profile 9 clients";
         uses charging_attr_type;
       }
       container profile10 {
         description "Profile 10 clients";
         uses charging_attr_type;
       }
       container profile11 {
         description "Profile 11 clients";
         uses charging_attr_type;
       }
       container profile12 {
         description "Profile 12 clients";
         uses charging_attr_type;
       }
       container profile13 {
         description "Profile 13 clients";
         uses charging_attr_type;
       }
       container profile14 {
         description "Profile 14 clients";
         uses charging_attr_type;
       }
       container profile15 {
         description "Profile 15 clients";
         uses charging_attr_type;
       }
     }
     choice tariff_choice {
       case case_1 {
         list tariff-activation {
           key name;
           description "Local times when new tariffs apply";
           uses deprecated_tariff_type;
         }
       }
     }
     container imsi-based-characteristics {
       description "Select charging characteristic based on IMSI";
       uses apply-advanced;
       container profile8 {
         description "Profile 8 clients";
         uses imsi_charac_type;
       }
       container profile4 {
         description "Profile 4 clients";
         uses imsi_charac_type;
       }
       container profile1 {
         description "Profile 1 clients";
         uses imsi_charac_type;
       }
       container profile2 {
         description "Profile 2 clients";
         uses imsi_charac_type;
       }
       container profile0 {
         description "Profile 0 clients";
         uses imsi_charac_type;
       }
       container profile3 {
         description "Profile 3 clients";
         uses imsi_charac_type;
       }
       container profile5 {
         description "Profile 5 clients";
         uses imsi_charac_type;
       }
       container profile6 {
         description "Profile 6 clients";
         uses imsi_charac_type;
       }
       container profile7 {
         description "Profile 7 clients";
         uses imsi_charac_type;
       }
       container profile9 {
         description "Profile 9 clients";
         uses imsi_charac_type;
       }
       container profile10 {
         description "Profile 10 clients";
         uses imsi_charac_type;
       }
       container profile11 {
         description "Profile 11 clients";
         uses imsi_charac_type;
       }
       container profile12 {
         description "Profile 12 clients";
         uses imsi_charac_type;
       }
       container profile13 {
         description "Profile 13 clients";
         uses imsi_charac_type;
       }
       container profile14 {
         description "Profile 14 clients";
         uses imsi_charac_type;
       }
       container profile15 {
         description "Profile 15 clients";
         uses imsi_charac_type;
       }
     }
     leaf no-empty-cdr {
       description "Do not close CDR at time limit if volume is zero";
       type empty;
     }
   }
   grouping charging_attr_type {
     uses apply-advanced;
     leaf volume-limit {
       description "Volume of charging data to buffer";
       default "500";
       units "kilobytes";
       type union {
         type string {
           pattern "<.*>|$.*";
         }
         type uint32 {
           range "100 .. 1000000";
         }
       }
     }
     leaf time-limit {
       description "Time to buffer charging data";
       default "60";
       units "minutes";
       type union {
         type string {
           pattern "<.*>|$.*";
         }
         type uint32 {
           range "15 .. 1440";
         }
       }
     }
     leaf billing-method {
       description "Method used to bill customer";
       status deprecated;
       type enumeration {
         enum "prepaid" {
           description "Prepaid charging";
           status deprecated;
         }
         enum "postpaid" {
           description "Postpaid charging";
           status deprecated;
         }
       }
     }
     choice call-detail-choice {
       leaf call-detail {
         description "Generate call data records";
         type empty;
       }
       leaf no-call-detail {
         description "Don't generate call data records";
         type empty;
       }
     }
     leaf change-limit {
       description "Maximum record changes to buffer on PIC";
       default "1";
       type union {
         type string {
           pattern "<.*>|$.*";
         }
         type uint32 {
           range "1 .. 5";
         }
       }
     }
     leaf transfer-type {
       description "Method used to transfer charging data";
       type enumeration {
         enum "ftp-pull" {
           description "Charging data transfer uses FTP pull only";
         }
         enum "gtp-prime" {
           description "Charging data transfer uses GTP Prime only";
         }
         enum "gtpp-ftp" {
           description "Charging data transfer uses both FTP pull and GTP Prime";
         }
       }
     }
     container gtp-prime {
       description "Characteristic specific GTP Prime configuration";
       uses apply-advanced;
       leaf-list gateway {
         ordered-by user;
         description "Address of billing gateway";
         type jt:ipv4addr;
         max-elements 3;
       }
     }
   }
   grouping charging_log_type {
     description "Charging records logged to node";
     uses apply-advanced;
     leaf user {
       description "User to own charging files";
       type string {
       }
     }
     leaf world-readable {
       description "Allow any user to read the log file";
       type empty;
     }
     leaf maximum-size {
       description "Maximum size of charging log file";
       default "307200";
       units "kilobytes";
       type union {
         type string {
           pattern "<.*>|$.*";
         }
         type uint32 {
           range "1024 .. 1048576";
         }
       }
     }
     leaf maximum-age {
       description "Maximum age of charging log file";
       default "120";
       units "minutes";
       type union {
         type string {
           pattern "<.*>|$.*";
         }
         type uint32 {
           range "5 .. 1440";
         }
       }
     }
     leaf compression {
       description "Compress all CDR log files";
       type empty;
     }
     leaf no-mirror {
       description "Disable mirroring of charging log files on backup Routing Engine";
       type empty;
     }
     container local-log {
       description "CDRs meant for normal offline transfer";
       uses apply-advanced;
       leaf force-empty-files {
         description "Generate empty CDR log files if no CDRs are received";
         type empty;
       }
     }
     container gtp-prime-log {
       description "GTP Prime CDRs logged to disk on failure in reaching charging gateways";
       uses apply-advanced;
       leaf activate-on-failure {
         description "Store GTP Prime CDRs on disk if all charging gateways are down";
         type empty;
       }
     }
     container traceoptions {
       description "Charging-log trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "init" {
               description "Trace initialization events";
             }
             enum "connections" {
               description "Trace connection-specific events";
             }
             enum "charging" {
               description "Trace charging-specific events";
             }
             enum "all" {
               description "Trace everything";
             }
           }
         }
       }
     }
   }
   grouping deprecated_tariff_type {
     leaf name {
       description "Tariff time index";
       type union {
         type string {
           pattern "<.*>|$.*";
         }
         type uint32 {
           range "1 .. 24";
         }
       }
     }
     leaf starts {
       description "Local time that the new tariff is activated";
       type string {
       }
     }
   }
   grouping dhcp_server_type {
     leaf name {
       description "DHCP server address";
       type jt:ipv4addr;
     }
     uses apply-advanced;
     leaf timeout {
       description "Request timeout period";
       default "3";
       units "seconds";
       type union {
         type string {
           pattern "<.*>|$.*";
         }
         type uint32 {
           range "1 .. 90";
         }
       }
     }
     leaf retry {
       description "Retry attempts";
       default "3";
       type union {
         type string {
           pattern "<.*>|$.*";
         }
         type uint32 {
           range "1 .. 10";
         }
       }
     }
   }
   grouping dhcp_shared_type {
     leaf name {
       description "Name of server";
       type string {
         length "1 .. 64";
       }
     }
     uses apply-advanced;
     leaf-list address {
       ordered-by user;
       description "DHCP server addresses";
       type jt:ipv4addr;
     }
     leaf routing-instance {
       description "Routing instance for server";
       type string {
       }
     }
     choice address-range-choice {
       case case_1 {
         leaf address-range {
           description "Address range used in routing instance";
           status deprecated;
           type jt:ipv4prefix;
         }
       }
       case case_2 {
         leaf gi-address-range {
           description "Address range used in routing instance";
           type jt:ipv4prefix;
         }
       }
     }
     leaf timeout {
       description "Request timeout period";
       default "3";
       units "seconds";
       type union {
         type string {
           pattern "<.*>|$.*";
         }
         type uint32 {
           range "1 .. 90";
         }
       }
     }
     leaf retry {
       description "Retry attempts";
       default "3";
       type union {
         type string {
           pattern "<.*>|$.*";
         }
         type uint32 {
           range "1 .. 10";
         }
       }
     }
   }
   grouping dscp_qos_map_type {
     uses apply-advanced;
     container conversational-1 {
       description "DSCP name for conversational class 1 traffic";
       uses apply-advanced;
       leaf low-drop-precedence {
         description "SDU error ratio = (10^-4 | 10^-5 | 10^-6)";
         default "ef";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "ef";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "ef";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container conversational-2 {
       description "DSCP name for conversational class 2 traffic";
       uses apply-advanced;
       leaf low-drop-precedence {
         description "SDU error ratio = (10^-4 | 10^-5 | 10^-6)";
         default "af11";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af12";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af13";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container streaming-1 {
       description "DSCP name for streaming class 1 traffic";
       uses apply-advanced;
       leaf low-drop-precedence {
         description "SDU error ratio = (10^-4 | 10^-5 | 10^-6)";
         default "af11";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af12";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af13";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container streaming-2 {
       description "DSCP name for streaming class 2 traffic";
       uses apply-advanced;
       leaf low-drop-precedence {
         description "SDU error ratio = (10^-4 | 10^-5 | 10^-6)";
         default "af21";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af22";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af23";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container interactive-1 {
       description "DSCP name for interactive class 1 traffic";
       uses apply-advanced;
       leaf low-drop-precedence {
         description "SDU error ratio = (10^-4 | 10^-5 | 10^-6)";
         default "af21";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af22";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af23";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container interactive-2 {
       description "DSCP name for interactive class 2 traffic";
       uses apply-advanced;
       leaf low-drop-precedence {
         description "SDU error ratio = (10^-4 | 10^-5 | 10^-6)";
         default "af31";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af32";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af33";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container interactive-3 {
       description "DSCP name for interactive class 3 traffic";
       uses apply-advanced;
       leaf low-drop-precedence {
         description "SDU error ratio = (10^-4 | 10^-5 | 10^-6)";
         default "af41";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "af42";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "af43";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
     container background {
       description "DSCP name for background traffic";
       uses apply-advanced;
       leaf low-drop-precedence {
         description "SDU error ratio = (10^-4 | 10^-5 | 10^-6)";
         default "be";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf medium-drop-precedence {
         description "SDU error ratio = (7*10^-3 | 10^-3)";
         default "be";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
       leaf high-drop-precedence {
         description "SDU error ratio = (10^-1 | 10^-2)";
         default "be";
         type enumeration {
           enum "af11" {
             description "Assured forwarding class 1, low drop precedence";
           }
           enum "af12" {
             description "Assured forwarding class 1, medium drop precedence";
           }
           enum "af13" {
             description "Assured forwarding class 1, high drop precedence";
           }
           enum "af21" {
             description "Assured forwarding class 2, low drop precedence";
           }
           enum "af22" {
             description "Assured forwarding class 2, medium drop precedence";
           }
           enum "af23" {
             description "Assured forwarding class 2, high drop precedence";
           }
           enum "af31" {
             description "Assured forwarding class 3, low drop precedence";
           }
           enum "af32" {
             description "Assured forwarding class 3, medium drop precedence";
           }
           enum "af33" {
             description "Assured forwarding class 3, high drop precedence";
           }
           enum "af41" {
             description "Assured forwarding class 4, low drop precedence";
           }
           enum "af42" {
             description "Assured forwarding class 4, medium drop precedence";
           }
           enum "af43" {
             description "Assured forwarding class 4, high drop precedence";
           }
           enum "ef" {
             description "Expedited forwarding";
           }
           enum "be" {
             description "Best effort forwarding";
           }
         }
       }
     }
   }
   grouping failover_type {
     description "Redundancy settings";
     uses apply-advanced;
     leaf pics {
       description "Maximum number of PICs reserved for redundancy";
       default "0";
       type union {
         type string {
           pattern "<.*>|$.*";
         }
         type uint32 {
           range "0 .. 5";
         }
       }
     }
     leaf arrangement {
       description "Redundancy arrangement";
       status deprecated;
       type enumeration {
         enum "none" {
           description "No PIC reserved for redundancy";
           status deprecated;
         }
         enum "backup" {
           description "One or more PICs reserved for redundancy";
           status deprecated;
         }
       }
     }
     leaf minimum-pic {
       description "PICs that will be used before applying redundancy";
       status deprecated;
       type union {
         type string {
           pattern "<.*>|$.*";
         }
         type uint32 {
           range "1 .. 32";
         }
       }
     }
   }
   grouping fbc_qos_control_qos_type {
     leaf name {
       description "Quality of service";
       type enumeration {
         enum "conversational" {
           description "Conversational quality of service";
         }
         enum "streaming" {
           description "Streaming quality of service";
         }
         enum "interactive-1" {
           description "Interactive priority 1 quality of service";
         }
         enum "interactive-2" {
           description "Interactive priority 2 quality of service";
         }
         enum "interactive-3" {
           description "Interactive priority 3 quality of service";
         }
         enum "background" {
           description "Background quality of service";
         }
       }
     }
     uses apply-advanced;
     leaf traffic-class {
       description "Traffic class";
       type enumeration {
         enum "conversational" {
           description "Conversational quality of service";
         }
         enum "streaming" {
           description "Streaming quality of service";
         }
         enum "interactive-1" {
           description "Interactive priority 1 quality of service";
         }
         enum "interactive-2" {
           description "Interactive priority 2 quality of service";
         }
         enum "interactive-3" {
           description "Interactive priority 3 quality of service";
         }
         enum "background" {
           description "Background quality of service";
         }
       }
     }
     leaf policy {
       description "QoS policy";
       default "must";
       type enumeration {
         enum "must" {
           description "Exact QoS required";
         }
         enum "min-required" {
           description "Minimum QoS required";
         }
         enum "max-allowed" {
           description "Maximum QoS allowed";
         }
       }
     }
     leaf maximum-bit-rate-uplink {
       description "Maximum uplink bit rate";
       units "kilobits";
       type union {
         type string {
           pattern "<.*>|$.*";
         }
         type uint32 {
           range "0 .. 8640";
         }
       }
     }
     leaf maximum-bit-rate-downlink {
       description "Maximum downlink bit rate";
       units "kilobits";
       type union {
         type string {
           pattern "<.*>|$.*";
         }
         type uint32 {
           range "0 .. 16000";
         }
       }
     }
     leaf guaranteed-bit-rate-uplink {
       description "Guaranteed uplink bit rate";
       units "kilobits";
       type union {
         type string {
           pattern "<.*>|$.*";
         }
         type uint32 {
           range "0 .. 8640";
         }
       }
     }
     leaf guaranteed-bit-rate-downlink {
       description "Guaranteed downlink bit rate";
       units "kilobits";
       type union {
         type string {
           pattern "<.*>|$.*";
         }
         type uint32 {
           range "0 .. 16000";
         }
       }
     }
     leaf transfer-delay {
       description "Transfer delay";
       units "milliseconds";
       type union {
         type string {
           pattern "<.*>|$.*";
         }
         type uint32 {
           range "10 .. 4000";
         }
       }
     }
   }
   grouping gtp_type {
     description "GTP settings";
     uses apply-advanced;
     leaf keepalive-interval {
       description "Seconds between sending keepalive messages";
       default "60";
       units "seconds";
       type union {
         type string {
           pattern "<.*>|$.*";
         }
         type uint32 {
           range "60 .. 200";
         }
       }
     }
     leaf t3-response-time {
       description "Seconds between control message retries";
       default "20";
       units "seconds";
       type union {
         type string {
           pattern "<.*>|$.*";
         }
         type uint32 {
           range "1 .. 30";
         }
       }
     }
     leaf n3-requests {
       description "Retransmissions allowed for a control message";
       default "5";
       type union {
         type string {
           pattern "<.*>|$.*";
         }
         type uint32 {
           range "1 .. 8";
         }
       }
     }
     leaf diffserv {
       description "DiffServ DSCP for GTP packets";
       default "be";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     choice path-management-choice {
       leaf path-management {
         description "Use path management";
         type empty;
       }
       leaf no-path-management {
         description "Don't use path management";
         type empty;
       }
     }
     leaf gn-routing-instance {
       description "Routing instance for GTP traffic";
       type string {
       }
     }
     leaf-list version-list {
       ordered-by user;
       description "GTP version";
       type enumeration {
         enum "97" {
           description "Use GTP version 97";
         }
         enum "98" {
           description "Use GTP version 98";
         }
         enum "99" {
           description "Use GTP version 99";
         }
       }
     }
     list bandwidth-constraint {
       key name;
       ordered-by user;
       description "SGSN-GGSN bandwidth constraints";
       uses bandconst_type;
     }
     container quality-of-service {
       description "Gn interface quality-of-service mapping";
       presence "enable quality-of-service";
       status deprecated;
       uses qosmap_type;
     }
     container downlink-dscp-remapping {
       description "Gn interface quality-of-service to DSCP remapping";
       presence "enable downlink-dscp-remapping";
       uses dscp_qos_map_type;
     }
     leaf no-n3t3-path-failure {
       description "Disable path failure on N3-T3 timeout";
       type empty;
     }
     leaf no-recovery-path-failure {
       description "Disable path failure on recovery change";
       type empty;
     }
   }
   grouping hcm_tag_rule_object {
     leaf name {
       description "Rule name";
       type string {
         length "1 .. 63";
       }
     }
     uses apply-advanced;
     list term {
       key name;
       ordered-by user;
       description "One or more terms in HCM tag rule";
       leaf name {
         description "Term name";
         type union {
           type string {
             pattern "<.*>|$.*";
           }
           type uint16 {
             range "1 .. 32767";
           }
         }
       }
       uses apply-advanced;
       container from {
         description "Match criteria";
         presence "enable from";
         uses hcm_tag_match_object;
       }
       container then {
         description "Action to take if the 'from' condition is matched";
         uses apply-advanced;
         list tag {
           key name;
           ordered-by user;
           description "One or more terms in HCM tag rule";
           leaf name {
             description "Tag name";
             type string {
               length "1 .. 63";
             }
           }
           uses apply-advanced;
           leaf tag-header {
             description "Tag header string";
             type string {
               length "1 .. 63";
             }
           }
           leaf do-not-rename-existing-tag-header {
             description "Disable renaming of the tag header";
             type empty;
           }
           leaf tag-separator {
             description "Tag separator character";
             type string {
               length 1;
             }
           }
           leaf-list tag-attribute {
             ordered-by user;
             description "One or more tag attributes";
             type enumeration {
               enum "ipv4addr" {
               }
               enum "ipv6addr" {
               }
             }
           }
           container encrypt {
             description "Specify encryption or hashing algorithm";
             uses apply-advanced;
             leaf hash {
               description "Hashing algorithm";
               type enumeration {
                 enum "md5" {
                   description "Md5 hash";
                 }
               }
             }
             leaf prefix {
               description "Hash prefix key";
               type string {
                 length "1 .. 63";
               }
             }
           }
           leaf ipv4-mask {
             description "Specify a logical and mask for the x-forwarded-for address";
             type jt:ipv4addr;
           }
           leaf ipv4-or-value {
             description "Specify a logical or mask for x-forwarded address";
             type jt:ipv4addr;
           }
           leaf ipv6-mask {
             description "Specify a logical and mask for the x-forwarded-for address";
             type jt:ipv6addr;
           }
           leaf ipv6-or-value {
             description "Specify a logical or mask for x-forwarded address";
             type jt:ipv6addr;
           }
         }
         leaf count {
           description "Enable statistics for term";
           type empty;
         }
       }
     }
   }
   grouping hcm_tag_match_object {
     uses apply-advanced;
     list destination-address {
       key name;
       ordered-by user;
       description "Match IP destination address";
       uses sfw_addr_object;
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list destination-ports {
       ordered-by user;
       description "Destination port list specification";
       type union {
         type string {
           pattern "<.*>|$.*";
         }
         type uint32 {
           range "0 .. 65535";
         }
       }
     }
     list destination-port-range {
       key "low high";
       ordered-by user;
       description "Match destination port range";
       leaf low {
         description "Lower limit of port range";
         type union {
           type string {
             pattern "<.*>|$.*";
           }
           type uint32 {
             range "0 .. 65535";
           }
         }
       }
       leaf high {
         description "Upper limit of port range";
         type union {
           type string {
             pattern "<.*>|$.*";
           }
           type uint32 {
             range "0 .. 65535";
           }
         }
       }
     }
   }
   grouping hcm_url_list_object {
     leaf name {
       description "List name";
       type string {
         length "1 .. 63";
       }
     }
     uses apply-advanced;
     list host {
       key name;
       ordered-by user;
       description "One or more host(s)";
       leaf name {
         description "Domain name";
         type string {
           length "1 .. 32";
         }
       }
       uses apply-advanced;
     }
     list request-uri {
       key name;
       ordered-by user;
       description "One or more uri's";
       leaf name {
         description "Uri name";
         type string {
           length "1 .. 40";
         }
       }
       uses apply-advanced;
     }
   }
   grouping hcm_url_rule_object {
     leaf name {
       description "Rule name";
       type string {
         length "1 .. 63";
       }
     }
     uses apply-advanced;
     list term {
       key name;
       ordered-by user;
       description "One or more terms in HCM url_rule";
       leaf name {
         description "Term name";
         type union {
           type string {
             pattern "<.*>|$.*";
           }
           type uint16 {
             range "1 .. 255";
           }
         }
       }
       uses apply-advanced;
       container from {
         description "Match criteria";
         presence "enable from";
         uses hcm_url_match_object;
       }
       container then {
         description "Action to take if the 'from' condition is matched";
         uses apply-advanced;
         leaf count {
           description "Enable statistics for term";
           type empty;
         }
         leaf log-request {
           description "Enable logging for term";
           type empty;
         }
         choice designation {
           case case_1 {
             leaf accept {
               description "Accept the URL";
               type empty;
             }
           }
           case case_2 {
             leaf discard {
               description "Discard the URL";
               type empty;
             }
           }
         }
       }
     }
   }
   grouping hcm_url_match_object {
     uses apply-advanced;
     list url-list {
       key name;
       ordered-by user;
       description "List of Url lists to referance";
       leaf name {
         description "Url list name";
         type string {
           length "1 .. 63";
         }
       }
       uses apply-advanced;
     }
     list url {
       key name;
       ordered-by user;
       description "Rule specific url list";
       leaf name {
         description "Url name";
         type union {
           type string {
             pattern "<.*>|$.*";
           }
           type uint16 {
             range "1 .. 32767";
           }
         }
       }
       uses apply-advanced;
       list host {
         key name;
         ordered-by user;
         description "One or more host(s)";
         leaf name {
           description "Domain name";
           type string {
             length "1 .. 32";
           }
         }
         uses apply-advanced;
       }
       list request-uri {
         key name;
         ordered-by user;
         description "One or more uri's";
         leaf name {
           description "Uri name";
           type string {
             length "1 .. 40";
           }
         }
         uses apply-advanced;
       }
     }
   }
   grouping header-manipulation-message-manipulation-rules-type {
     description "Definition of header manipulation";
     uses apply-advanced;
     list manipulation-rule {
       key name;
       ordered-by user;
       description "Definition of manipulation rules";
       uses header-manipulation-manipulation-rule-type;
     }
   }
   grouping header-manipulation-manipulation-rule-type {
     leaf name {
       description "Header manipulation rule name";
       type string;
     }
     uses apply-advanced;
     container actions {
       description "Header manipulation actions";
       uses header-manipulation-actions-type;
     }
   }
   grouping header-manipulation-actions-type {
     description "Manipulations on sip-headers or request-uri";
     uses apply-advanced;
     list sip-header {
       key name;
       ordered-by user;
       description "Manipulation of the SIP header";
       max-elements 50;
       leaf name {
         description "SIP header field name";
         type string;
       }
       uses apply-advanced;
       container field-value {
         description "Manipulation on the header's field value";
         uses header-manipulation-sip-header-field-value-type;
       }
     }
     container request-uri {
       presence "enable request-uri";
       description "Manipulation of the message request-uri";
       uses apply-advanced;
       container field-value {
         presence "enable field-value";
         description "Manipulation on the request-uri field value";
         uses apply-advanced;
         list modify-regular-expression {
           key name;
           ordered-by user;
           description "Set modify regular expression and patterns";
           max-elements 5;
           uses header-manipulation-modify-type;
         }
       }
     }
   }
   grouping header-manipulation-modify-type {
     description "Modify header using regular expression";
     leaf name {
       description "Regular expression pattern";
       type jt:regular-expression;
     }
     leaf with {
       description "Modification string";
       type string;
     }
   }
   grouping header-manipulation-sip-header-field-value-type {
     uses apply-advanced;
     leaf remove-all {
       description "Remove all headers";
       type empty;
     }
     list remove-regular-expression {
       key name;
       ordered-by user;
       description "Remove field-value";
       max-elements 5;
       uses header-manipulation-remove-type;
     }
     list reject-regular-expression {
       key name;
       ordered-by user;
       description "Reject message using regular expression";
       max-elements 5;
       uses header-manipulation-reject-type;
     }
     list modify-regular-expression {
       key name;
       ordered-by user;
       description "Modify field-value using regular expression";
       max-elements 5;
       uses header-manipulation-modify-type;
     }
     list add {
       key name;
       ordered-by user;
       description "Add field-value to header";
       max-elements 5;
       uses header-manipulation-add-type;
     }
     list add-missing {
       key name;
       ordered-by user;
       description "Add field-value only if header is missing";
       max-elements 5;
       uses header-manipulation-add-missing-type;
     }
     list add-overwrite {
       key name;
       ordered-by user;
       description "Overwrite headers field-value";
       max-elements 5;
       uses header-manipulation-add-overwrite-type;
     }
   }
   grouping header-manipulation-add-missing-type {
     description "Add header only if missing";
     leaf name {
       description "Field-value to add";
       type string;
     }
   }
   grouping header-manipulation-add-overwrite-type {
     description "Overwrite existing header";
     leaf name {
       description "Field-value to add";
       type string;
     }
   }
   grouping header-manipulation-add-type {
     description "Add header";
     leaf name {
       description "Field-value to add";
       type string;
     }
   }
   grouping header-manipulation-reject-type {
     description "Reject messages that match a regular expression";
     leaf name {
       description "Regular expression pattern";
       type jt:regular-expression;
     }
   }
   grouping header-manipulation-remove-type {
     description "Remove headers that match a regular expression";
     leaf name {
       description "Regular expression pattern";
       type jt:regular-expression;
     }
   }
   grouping ids_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to and output from interface";
         }
       }
     }
     list term {
       key name;
       ordered-by user;
       description "Define an IDS term";
       leaf name {
         description "Term name";
         type string {
           length "1 .. 63";
         }
       }
       uses apply-advanced;
       container from {
         description "Define match criteria";
         uses sfw_match_object;
       }
       container then {
         description "Action to take if the 'from' condition is matched";
         uses apply-advanced;
         choice accept_choice {
           case case_1 {
             leaf force-entry {
               description "Force entries in IDS tables for matching traffic";
               type empty;
             }
           }
           case case_2 {
             leaf ignore-entry {
               description "Ignore IDS events for matching traffic";
               type empty;
             }
           }
           case case_3 {
             leaf user-interface {
               description "User-interface trace level";
               default "error";
               type enumeration {
                 enum "trace" {
                   description "Trace functions entering and exiting";
                 }
                 enum "debug" {
                   description "Trace code flow, branching, positive style guide check";
                 }
                 enum "info" {
                   description "Summary logs for normal operations";
                 }
                 enum "warning" {
                   description "Failure-recovery or Failure of an external entity";
                 }
                 enum "error" {
                   description "Failure with short-term affect";
                 }
               }
             }
           }
         }
         container aggregation {
           description "Define aggregation parameters";
           uses apply-advanced;
           leaf source-prefix {
             description "Prefix length for IPv4 source addresses";
             type union {
               type string {
                 pattern "<.*>|$.*";
               }
               type int32 {
                 range "1 .. 32";
               }
             }
           }
           leaf destination-prefix {
             description "Prefix length for IPv4 destination addresses";
             type union {
               type string {
                 pattern "<.*>|$.*";
               }
               type int32 {
                 range "1 .. 32";
               }
             }
           }
           leaf source-prefix-ipv6 {
             description "Prefix length for IPv6 source addresses";
             type union {
               type string {
                 pattern "<.*>|$.*";
               }
               type int32 {
                 range "1 .. 128";
               }
             }
           }
           leaf destination-prefix-ipv6 {
             description "Prefix length for IPv6 destination addresses";
             type union {
               type string {
                 pattern "<.*>|$.*";
               }
               type int32 {
                 range "1 .. 128";
               }
             }
           }
         }
         container logging {
           description "Define system logging parameters";
           uses apply-advanced;
           leaf threshold {
             description "Threshold above which events should be logged";
             type union {
               type int32;
               type string {
                 pattern "<.*>|$.*";
               }
             }
           }
           leaf syslog {
             description "System log information about the packet";
             type empty;
           }
         }
         container syn-cookie {
           description "Define SYN cookie parameters";
           uses apply-advanced;
           leaf threshold {
             description "Threshold above which SYN cookies are enabled";
             type union {
               type int32;
               type string {
                 pattern "<.*>|$.*";
               }
             }
           }
           leaf mss {
             description "MSS value for TCP delayed binding";
             type union {
               type string {
                 pattern "<.*>|$.*";
               }
               type int32 {
                 range "128 .. 8192";
               }
             }
           }
         }
         container session-limit {
           description "Define IDS session limit parameters";
           uses apply-advanced;
           container by-source {
             description "Define IDS session limit parameters by source";
             uses ids_limit_type;
           }
           container by-destination {
             description "Define IDS session limit parameters by destination";
             uses ids_limit_type;
           }
           container by-pair {
             description "Define IDS session limit parameters by source-destination pair";
             presence "enable by-pair";
             uses ids_limit_type;
           }
         }
         leaf-list allow-ip-options {
           ordered-by user;
           type string;
         }
         leaf-list allow-ipv6-extension-header {
           ordered-by user;
           type string;
         }
         leaf tcp-syn-defense {
           description "Enable tcp-syn-defense";
           type empty;
         }
         leaf tcp-syn-fragment-check {
           description "Enable tcp syn fragment check";
           type empty;
         }
         leaf tcp-winnuke-check {
           description "Enable tcp winnuke check";
           type empty;
         }
         leaf icmp-fragment-check {
           description "Enable icmp fragment check";
           type empty;
         }
         leaf icmp-large-packet-check {
           description "Enable icmp large packet check";
           type empty;
         }
         leaf land-attack-check {
           description "Enable land attack checks";
           type enumeration {
             enum "ip-only" {
               description "Land attack check is on IP address only";
             }
             enum "ip-port" {
               description "Land attack check is on both IP and port";
             }
           }
         }
       }
     }
   }
   grouping ids_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
     leaf hold-time {
       description "How long to keep limit information after session is deleted";
       units "second";
       type union {
         type string {
           pattern "<.*>|$.*";
         }
         type int32 {
           range "0 .. 60";
         }
       }
     }
     container by-protocol {
       description "Define IDS session limit parameters";
       uses apply-advanced;
       container tcp {
         description "Define TCP IDS session limits";
         uses ids_proto_limit_type;
       }
       container udp {
         description "Define UDP IDS session limits by source";
         uses ids_proto_limit_type;
       }
       container icmp {
         description "Define ICMP IDS session limits by source";
         uses ids_proto_limit_type;
       }
     }
   }
   grouping ids_proto_limit_type {
     uses apply-advanced;
     leaf maximum {
       description "Maximum number of open sessions allowed simultaneously";
       type string;
     }
     leaf rate {
       description "Maximum number of new sessions allowed per second";
       type string;
     }
     leaf packets {
       description "Maximum number of packets allowed per second";
       type string;
     }
   }
   grouping imsi_charac_type {
     uses apply-advanced;
     leaf-list imsi {
       ordered-by user;
       description "Specify IMSI patterns using regular expressions";
       type jt:regular-expression;
     }
   }
   grouping inband-telemetry-profile-type {
     description "Inband Telemetry Profile";
     leaf name {
       description "Profile Name";
       type string {
         length "1 .. 32";
       }
     }
     uses apply-advanced;
     leaf sample-rate {
       description "Ratio of packets to be sampled (1 out of N)";
       type union {
         type string {
           pattern "<.*>|$.*";
         }
         type uint32 {
           range "1 .. 16777215";
         }
       }
     }
     container collector {
       description "Profile options";
       uses apply-advanced;
       leaf source-address {
         description "Source IP Address";
         type jt:ipv4addr;
       }
       leaf destination-address {
         description "Destination IP Address";
         type jt:ipv4addr;
       }
       leaf destination-port {
         description "Destionation Port";
         type union {
           type string {
             pattern "<.*>|$.*";
           }
           type uint32 {
             range "1 .. 65535";
           }
         }
       }
       leaf maximum-clip-length {
         description "Maximum data packet length for export";
         default "256";
         type union {
           type string {
             pattern "<.*>|$.*";
           }
           type uint32 {
             range "64 .. 9000";
           }
         }
       }
       leaf mtu {
         description "Maximum size of export packet";
         default "9000";
         type union {
           type string {
             pattern "<.*>|$.*";
           }
           type uint32 {
             range "256 .. 9000";
           }
         }
       }
     }
   }
   grouping interface_map_type {
     uses apply-advanced;
     leaf file-specification {
       description "Default file specification";
       type string;
     }
     leaf collector {
       description "Default Collector PIC to be used for flow manipulation";
       type union {
         type jt:interface-device;
         type string {
           pattern "<.*>|$.*";
         }
       }
     }
     list input_intf_to_cpic_map {
       key name;
       uses input_intf_to_cpic_map_type;
     }
   }
   grouping input_intf_to_cpic_map_type {
     leaf name {
       description "Input interface for flow collection";
       type union {
         type jt:interface-name;
         type string {
           pattern "<.*>|$.*";
         }
       }
     }
     uses apply-advanced;
     leaf file-specification {
       description "File specification to use for this interface";
       type string;
     }
     leaf collector {
       description "Collector PIC to be used for flow manipulation";
       type union {
         type jt:interface-device;
         type string {
           pattern "<.*>|$.*";
         }
       }
     }
   }
   grouping interface_type {
     description "Physical interface";
     leaf name {
       type string;
     }
     uses apply-advanced;
     choice queue-statistics-choice {
       leaf queue-statistics {
         description "Enable queue statistics collection";
         status deprecated;
         type empty;
       }
       leaf no-queue-statistics {
         description "Don't enable queue statistics collection";
         status deprecated;
         type empty;
       }
     }
     choice traffic-statistics-choice {
       leaf traffic-statistics {
         description "Enable traffic statistics collection";
         status deprecated;
         type empty;
       }
       leaf no-traffic-statistics {
         description "Don't enable traffic statistics collection";
         status deprecated;
         type empty;
       }
     }
     leaf resource-profile {
       description "Resouce profile name";
       type string {
         length "1 .. 64";
       }
     }
   }
   grouping ipr_profile_object {
     leaf name {
       description "IP-reassembly profile name";
       type string {
         length "1 .. 32";
       }
     }
     uses apply-advanced;
     leaf timeout {
       description "IP-reassembly timeout value";
       type union {
         type string {
           pattern "<.*>|$.*";
         }
         type int32 {
           range "2 .. 60";
         }
       }
     }
     leaf max-reassembly-pending-packets {
       description "IP-reassembly pending packets";
       type union {
         type string {
           pattern "<.*>|$.*";
         }
         type int32 {
           range "100 .. 100000";
         }
       }
     }
   }
   grouping ipr_rule_object {
     leaf name {
       description "Rule name";
       type string {
         length "1 .. 63";
       }
     }
     uses apply-advanced;
     leaf match-direction {
       description "Direction for which the rule match is applied";
       type enumeration {
         enum "input" {
           description "Match on input to interface";
         }
       }
     }
   }
   grouping ipsec-services-traceoptions {
     description "Trace options for key management process";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "timer" {
             description "Trace internal timer events";
           }
           enum "routing-socket" {
             description "Trace routing socket messages";
           }
           enum "parse" {
             description "Trace configuration processing";
           }
           enum "ike" {
             description "Trace IKE module processing";
           }
           enum "policy-manager" {
             description "Trace policy manager processing";
           }
           enum "general" {
             description "Trace general events";
           }
           enum "database" {
             description "Trace security associations database events";
           }
           enum "certificates" {
             description "Trace certificate events";
           }
           enum "snmp" {
             description "Trace SNMP operations";
           }
           enum "ams" {
             description "Trace AMS events";
           }
           enum "lic" {
             description "Trace License events";
           }
           enum "all" {
             description "Trace everything";
           }
         }
       }
     }
   }
   grouping ipsec_vpn_rule_object {
     leaf name {
       description "Rule name";
       type string {
         length "1 .. 63";
       }
     }
     uses apply-advanced;
     list term {
       key name;
       ordered-by user;
       description "Define an IPSec term";
       leaf name {
         description "Term name";
         type string {
           length "1 .. 63";
         }
       }
       uses apply-advanced;
       container from {
         description "Define match criteria";
         uses ipsec_vpn_match_object;
       }
       container then {
         presence "enable then";
         description "Action to take if the 'from' condition is matched";
         uses apply-advanced;
         leaf syslog {
           description "System log information about the packet";
           type empty;
         }
         leaf remote-gateway {
           description "Remote gateway address";
           type jt:ipaddr;
         }
         leaf backup-remote-gateway {
           description "Backup remote gateway address";
           type jt:ipaddr;
         }
         choice sa_choice {
           case case_1 {
             container manual {
               description "Define a manual security association";
               uses apply-advanced;
               list direction {
                 key name;
                 ordered-by user;
                 description "Define the direction of the security association";
                 leaf name {
                   type enumeration {
                     enum "inbound" {
                       description "Inbound security association";
                     }
                     enum "outbound" {
                       description "Outbound security association";
                     }
                     enum "bidirectional" {
                       description "Bidirectional security association";
                     }
                   }
                 }
                 uses apply-advanced;
                 leaf protocol {
                   description "Define an IPSec protocol for the security association";
                   type enumeration {
                     enum "ah" {
                       description "Authentication header";
                     }
                     enum "esp" {
                       description "Encapsulated Security Payload header";
                     }
                     enum "bundle" {
                       description "Bundle (AH authentication plus ESP encryption)";
                     }
                   }
                 }
                 leaf spi {
                   description "Define security parameter index";
                   type union {
                     type string {
                       pattern "<.*>|$.*";
                     }
                     type uint32 {
                       range "256 .. 16639";
                     }
                   }
                 }
                 leaf auxiliary-spi {
                   description "ESP security parameter index for IPSec SA bundle";
                   type union {
                     type string {
                       pattern "<.*>|$.*";
                     }
                     type uint32 {
                       range "256 .. 16639";
                     }
                   }
                 }
                 container authentication {
                   description "Define authentication parameters";
                   uses apply-advanced;
                   leaf algorithm {
                     description "Define authentication algorithm";
                     type enumeration {
                       enum "hmac-md5-96" {
                         description "HMAC-MD5-96 authentication algorithm";
                       }
                       enum "hmac-sha1-96" {
                         description "HMAC-SHA1-96 authentication algorithm";
                       }
                       enum "hmac-sha2-256" {
                         description "HMAC-SHA2-256 authentication algorithm";
                       }
                       enum "hmac-sha-256-128" {
                         description "HMAC-SHA-256-128 authentication algorithm";
                       }
                     }
                   }
                   container key {
                     description "Define an authentication key";
                     choice key-choice {
                       case case_1 {
                         leaf ascii-text {
                           description "Format as text";
                           type string {
                             length "1 .. 255";
                           }
                         }
                       }
                       case case_2 {
                         leaf hexadecimal {
                           description "Format as hexadecimal";
                           type string {
                             length "1 .. 255";
                           }
                         }
                       }
                     }
                   }
                 }
                 container encryption {
                   description "Define encryption parameters";
                   uses apply-advanced;
                   leaf algorithm {
                     description "Define encryption algorithm";
                     type enumeration {
                       enum "des-cbc" {
                         description "DES-CBC encryption algorithm";
                       }
                       enum "3des-cbc" {
                         description "3DES-CBC encryption algorithm";
                       }
                       enum "aes-128-cbc" {
                         description "AES-CBC 128-bit encryption algorithm";
                       }
                       enum "aes-192-cbc" {
                         description "AES-CBC 192-bit encryption algorithm";
                       }
                       enum "aes-256-cbc" {
                         description "AES-CBC 256-bit encryption algorithm";
                       }
                     }
                   }
                   container key {
                     description "Define an encryption key";
                     choice key-choice {
                       case case_1 {
                         leaf ascii-text {
                           description "Format as text";
                           type string {
                             length "1 .. 255";
                           }
                         }
                       }
                       case case_2 {
                         leaf hexadecimal {
                           description "Format as hexadecimal";
                           type string {
                             length "1 .. 255";
                           }
                         }
                       }
                     }
                   }
                 }
               }
             }
           }
           case case_2 {
             container dynamic {
               description "Define a dynamic security association";
               uses apply-advanced;
               leaf ike-policy {
                 description "Name of the IKE policy";
                 type string {
                   length "1 .. 32";
                 }
               }
               leaf ipsec-policy {
                 description "Name of the IPSec policy";
                 type string {
                   length "1 .. 32";
                 }
               }
               leaf natt-install-interval {
                 description "Installation interval of the IPSEC SA in NAT-T scenario";
                 default "0";
                 units "seconds";
                 type union {
                   type string {
                     pattern "<.*>|$.*";
                   }
                   type uint32 {
                     range "0 .. 10";
                   }
                 }
               }
             }
           }
         }
         leaf clear-dont-fragment-bit {
           description "Clear the do not fragment bit";
           type empty;
         }
         leaf copy-dont-fragment-bit {
           description "Copy the do not fragment bit";
           type empty;
         }
         leaf set-dont-fragment-bit {
           description "Set the do not fragment bit";
           type empty;
         }
         leaf no-anti-replay {
           description "Disable the anti-replay check";
           type empty;
         }
         leaf tunnel-mtu {
           description "Maximum transmit packet size";
           type union {
             type string {
               pattern "<.*>|$.*";
             }
             type uint32 {
               range "256 .. 9192";
             }
           }
         }
         leaf copy-ttl-from-inner-ip-header {
           description "Copy the inner ip ttl value to outer ip header";
           type empty;
         }
         leaf ttl {
           description "TTL value to be used for outer IP header";
           default "64";
           type union {
             type string {
               pattern "<.*>|$.*";
             }
             type uint32 {
               range "1 .. 254";
             }
           }
         }
         leaf copy-tos-from-inner-ip-header {
           description "Copy the inner ip tos value to outer ip header";
           type empty;
         }
         leaf tos {
           description "ToS value to be used for outer IP header";
           default "0";
           type union {
             type string {
               pattern "<.*>|$.*";
             }
             type uint32 {
               range "0 .. 255";
             }
           }
         }
         leaf initiate-dead-peer-detection {
           description "Initiate dead peer detection";
           type empty;
         }
         container dead-peer-detection {
           presence "enable dead-peer-detection";
           description "Dead peer detection options";
           uses apply-advanced;
           leaf interval {
             description "Interval at which the DPD messages should be sent";
             default "10";
             units "seconds";
             type union {
               type string {
                 pattern "<.*>|$.*";
               }
               type uint32 {
                 range "1 .. 180";
               }
             }
           }
           leaf threshold {
             description "Maximum number of DPD messages";
             default "3";
             type union {
               type string {
                 pattern "<.*>|$.*";
               }
               type uint32 {
                 range "1 .. 10";
               }
             }
           }
         }
         leaf anti-replay-window-size {
           description "Size of the anti-replay window";
           type union {
             type string {
               pattern "<.*>|$.*";
             }
             type uint32 {
               range "64 .. 4096";
             }
           }
         }
       }
     }
     leaf match-direction {
       description "Direction for which the rule match is applied";
       type enumeration {
         enum "input" {
           description "Match on input to interface";
         }
         enum "output" {
           description "Match on output from interface";
         }
       }
     }
   }
   grouping ipsec_vpn_match_object {
     uses apply-advanced;
     list source-address {
       key name;
       ordered-by user;
       description "Match IP source address";
       max-elements 1;
       uses ipsec_vpn_addr_object;
     }
     list destination-address {
       key name;
       ordered-by user;
       description "Match IP destination address";
       max-elements 1;
       uses ipsec_vpn_addr_object;
     }
     leaf ipsec-inside-interface {
       description "IPSec interface to internal network";
       type union {
         type jt:interface-unit;
         type string {
           pattern "<.*>|$.*";
         }
       }
     }
   }
   grouping ipsec_vpn_addr_object {
     leaf name {
       description "Prefix to match";
       type jt:ipprefix-only;
     }
   }
   grouping ipv6_name_server_type {
     leaf name {
       description "IPv6 DNS name server address";
       type jt:ipv6addr;
     }
     uses apply-advanced;
     leaf ipv6-proxy-cscf {
       description "Proxy CSCF address";
       status deprecated;
       type jt:ipv6addr;
     }
   }
   grouping juniper-pic-services-logging-options {
     uses apply-advanced;
     container traceoptions {
       description "Fsad trace options";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "init" {
               description "Trace initialization events";
             }
             enum "bookkeeping" {
               description "Trace bookkeeping events";
             }
             enum "connections" {
               description "Trace connection-specific events";
             }
             enum "charging" {
               description "Trace charging-specific events";
             }
             enum "flow-collector" {
               description "Trace flow collector specific events";
             }
             enum "all" {
               description "Trace everything";
             }
           }
         }
       }
     }
   }
   grouping juniper-services-captive-portal {
     uses apply-advanced;
     leaf authentication-profile-name {
       description "Access profile name to use for authentication";
       type string {
         length "1 .. 63";
       }
     }
     container traceoptions {
       description "Trace options for CAPTIVE PORTAL";
       status deprecated;
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "dot1x-debug" {
               description "Trace dot1x events";
             }
             enum "parse" {
               description "Trace configuration parsing";
             }
             enum "esw-if" {
               description "Trace ESW Interactions";
             }
             enum "config-internal" {
               description "Trace configuration internals";
             }
             enum "normal" {
               description "Trace normal events";
             }
             enum "general" {
               description "Trace general events";
             }
             enum "state" {
               description "Trace state transitions";
             }
             enum "task" {
               description "Trace task processing";
             }
             enum "timer" {
               description "Trace task timer processing";
             }
             enum "all" {
               description "Trace everything";
             }
             enum "dot1x-ipc" {
               description "Trace dot1x IPC interactions";
             }
             enum "dot1x-event" {
               description "Trace dot1x events";
             }
           }
         }
         leaf disable {
           description "Disable this trace flag";
           type empty;
         }
       }
     }
     list interface {
       key name;
       description "Captive Portal interface specific options";
       leaf name {
         type string;
       }
       uses apply-advanced;
       leaf supplicant {
         description "Set supplicant mode for this interface";
         type enumeration {
           enum "single" {
             description "Allow multiple clients; authenticate first client only";
           }
           enum "single-secure" {
             description "Allow and authenticate only a single client";
           }
           enum "multiple" {
             description "Allow multiple clients; authenticate each individually";
           }
         }
       }
       leaf retries {
         description "Number of retries after which port is placed into wait state";
         type union {
           type string {
             pattern "<.*>|$.*";
           }
           type uint32 {
             range "1 .. 10";
           }
         }
       }
       leaf quiet-period {
         description "Time to wait after an authentication failure";
         units "seconds";
         type union {
           type string {
             pattern "<.*>|$.*";
           }
           type uint32 {
             range "0 .. 65535";
           }
         }
       }
       leaf server-timeout {
         description "Authentication server timeout interval";
         units "seconds";
         type union {
           type string {
             pattern "<.*>|$.*";
           }
           type uint32 {
             range "1 .. 60";
           }
         }
       }
       leaf session-expiry {
         description "Session Expiry Timeout";
         units "seconds";
         type union {
           type string {
             pattern "<.*>|$.*";
           }
           type uint32 {
             range "1 .. 65535";
           }
         }
       }
       leaf user-keepalive {
         description "Session keepalive after mac-flush";
         units "minutes";
         type union {
           type string {
             pattern "<.*>|$.*";
           }
           type uint32 {
             range "7 .. 65535";
           }
         }
       }
     }
     leaf secure-authentication {
       description "Set secure authentication using encrypted HTTPS or insecure authentication using plain-text HTTP";
       default "http";
       type enumeration {
         enum "http" {
           description "Insecure plain-text HTTP will be used for Captive Portal authentication, username and password can be sniffed";
         }
         enum "https" {
           description "Encrypted HTTPS will be used for Captive Portal authentication";
         }
       }
     }
     container custom-options {
       presence "enable custom-options";
       description "Captive Portal html user interface customization options";
       uses apply-advanced;
       leaf header-logo {
         description "Path to logo image file";
         type string {
           length "1 .. 255";
         }
       }
       leaf header-bgcolor {
         description "Background color of the html header in hex html format";
         type string {
           length 7;
         }
       }
       leaf header-text-color {
         description "Text color of the html header in hex html format";
         type string {
           length 7;
         }
       }
       leaf header-message {
         description "Message to be displayed in the html header";
         type string {
           length "1 .. 2047";
         }
       }
       leaf banner-message {
         description "Terms and Conditions of usage message";
         type string {
           length "1 .. 2047";
         }
       }
       leaf form-header-message {
         description "Message to be displayed in the login form header";
         type string {
           length "1 .. 255";
         }
       }
       leaf form-header-bgcolor {
         description "Background color of the login form header in hex html format";
         type string {
           length 7;
         }
       }
       leaf form-header-text-color {
         description "Text color of the login form header in hex html format";
         type string {
           length 7;
         }
       }
       leaf form-submit-label {
         description "Label to be displayed for the login form submit button";
         type string {
           length "1 .. 255";
         }
       }
       leaf form-reset-label {
         description "Label to be displayed for the login form reset button";
         type string {
           length "1 .. 255";
         }
       }
       leaf footer-message {
         description "Message to be displayed in the html footer";
         type string {
           length "1 .. 2047";
         }
       }
       leaf footer-bgcolor {
         description "Background color of the html footer in hex html format";
         type string {
           length 7;
         }
       }
       leaf footer-text-color {
         description "Text color of the footer in hex html format";
         type string {
           length 7;
         }
       }
       leaf post-authentication-url {
         description "Post authentication redirection URL";
         type string {
           length "1 .. 255";
         }
       }
     }
   }
   grouping l2tp_access_line_object {
     uses apply-advanced;
     leaf connection-speed-update {
       description "Support connection speed updates";
       type empty;
     }
   }
   grouping l2tp_destination_object {
     uses apply-advanced;
     leaf lockout-timeout {
       description "The lockout timeout in seconds";
       default "300";
       type union {
         type string {
           pattern "<.*>|$.*";
         }
         type uint16 {
           range "60 .. 3600";
         }
       }
     }
     list lockout-result-code {
       key name;
       ordered-by user;
       description "The lockout result code";
       leaf name {
         description "The lockout result code";
         type enumeration {
           enum "1" {
             description "Clear control connection or Loss of carrier";
           }
           enum "2" {
             description "Reason indicated in error code";
           }
           enum "3" {
             description "Control Channel exists or Administrator reasons";
           }
           enum "4" {
             description "Unauthorized for channel or Temporary facilities unavailable";
           }
           enum "5" {
             description "Version unsupported or Permanent facilities unavailable";
           }
           enum "6" {
             description "Requester shut down or Invalid destination";
           }
           enum "7" {
             description "FSM error or No carrier detected";
           }
           enum "8" {
             description "Busy signal";
           }
           enum "9" {
             description "Lack of dial tone";
           }
           enum "10" {
             description "Unable to established within time";
           }
           enum "11" {
             description "No framing was detected";
           }
         }
       }
       uses apply-advanced;
       list error-code {
         key name;
         ordered-by user;
         description "The lockout error code";
         leaf name {
           description "The lockout error code";
           type enumeration {
             enum "1" {
               description "No control connection";
             }
             enum "2" {
               description "Length is wrong";
             }
             enum "3" {
               description "Field value out of order or Reserved field non-zero";
             }
             enum "4" {
               description "Insufficient resources";
             }
             enum "5" {
               description "The Session ID is invalid";
             }
             enum "6" {
               description "Vendor-specific error";
             }
             enum "7" {
               description "Try another LNS destination";
             }
             enum "8" {
               description "Session or tunnel was shutdown";
             }
           }
         }
         uses apply-advanced;
       }
     }
     list address {
       key name;
       ordered-by user;
       leaf name {
         description "Address of remote system";
         type jt:ipv4addr;
       }
       container access-line-information {
         presence "enable access-line-information";
         description "Enable sending access-line attributes";
         uses apply-advanced;
         leaf connection-speed-update {
           description "Support connection speed updates";
           type empty;
         }
       }
       list routing-instance {
         key name;
         ordered-by user;
         description "Routing instance in which destination exists";
         leaf name {
           description "Routing instance in which destination exists";
           type string {
           }
         }
         leaf drain {
           description "Prevents creation of tunnels and sessions at destination";
           type empty;
         }
       }
       leaf drain {
         description "Prevents creation of tunnels and sessions at destination";
         type empty;
       }
     }
     list name {
       key name;
       ordered-by user;
       leaf name {
         description "Locally assigned name of the destination";
         type string {
           length "1 .. 63";
         }
       }
       leaf drain {
         description "Prevents tunnels and sessions at destination";
         type empty;
       }
     }
   }
   grouping l2tp_interface_traceoptions {
     leaf name {
       description "Name of Layer 2 Tunneling Protocol service interface";
       type union {
         type jt:interface-device;
         type string {
           pattern "<.*>|$.*";
         }
       }
     }
     uses apply-advanced;
     list flag {
       key name;
       ordered-by user;
       description "Tracing parameters";
       leaf name {
         type enumeration {
           enum "ipc" {
             description "Trace L2TP IPC messages between PIC and Routing Engine";
           }
           enum "protocol" {
             description "Trace L2TP, PPP, and multilink handling";
           }
           enum "packet-dump" {
             description "Dump each packet content based on debug level";
           }
           enum "system" {
             description "Trace packet processing on the PIC";
           }
           enum "all" {
             description "Trace everything";
           }
         }
       }
     }
     leaf debug-level {
       description "Trace level for PIC";
       default "error";
       type enumeration {
         enum "error" {
           description "Errors";
         }
         enum "detail" {
           description "Detailed debug information";
         }
         enum "extensive" {
           description "All PIC debug information";
         }
       }
     }
   }
   grouping l2tp_tunnel_group_object {
     leaf name {
       description "Name of Layer 2 Tunneling Protocol profile";
       type string {
         length "1 .. 63";
       }
     }
     uses apply-advanced;
     leaf l2tp-access-profile {
       description "Tunnel profile name";
       type string {
         length "1 .. 63";
       }
     }
     leaf ppp-access-profile {
       description "User profile name";
       type string {
         length "1 .. 63";
       }
     }
     leaf aaa-access-profile {
       description "AAA profile name";
       type string {
         length "1 .. 63";
       }
     }
     leaf receive-window {
       description "Maximum receive window size";
       default "16";
       units "bytes";
       type union {
         type uint16;
         type string {
           pattern "<.*>|$.*";
         }
       }
     }
     leaf maximum-send-window {
       description "Limits the other end receive window size";
       default "32";
       units "bytes";
       type union {
         type uint16;
         type string {
           pattern "<.*>|$.*";
         }
       }
     }
     leaf retransmit-interval {
       description "Retransmit interval";
       default "30";
       units "seconds";
       type union {
         type uint16;
         type string {
           pattern "<.*>|$.*";
         }
       }
     }
     leaf hello-interval {
       description "Hello interval for tunnel keepalive";
       default "60";
       units "seconds";
       type union {
         type string {
           pattern "<.*>|$.*";
         }
         type uint16 {
           range "0 .. 3600";
         }
       }
     }
     leaf hide-avps {
       description "Hide L2TP AVPs";
       type empty;
     }
     leaf no-tos-reflect {
       description "Disable ToS bit reflect onto outer L2TP header";
       type empty;
     }
     leaf tos-reflect {
       description "Enable ToS bit reflect onto outer L2TP header";
       type empty;
     }
     leaf tunnel-timeout {
       description "Time to tear down tunnel when a connection is lost";
       default "120";
       units "seconds";
       type union {
         type uint16;
         type string {
           pattern "<.*>|$.*";
         }
       }
     }
     container local-gateway {
       presence "enable local-gateway";
       uses apply-advanced;
       leaf address {
         description "L2TP network server IP address";
         type jt:ipv4addr;
       }
       leaf gateway-name {
         description "L2TP network server name for use with remote host";
         type string;
       }
     }
     choice anchor-points {
       case case_1 {
         leaf service-interface {
           description "Services interface to use";
           type string;
         }
       }
       case case_2 {
         leaf service-device-pool {
           description "Service interface pool name to use";
           type string {
             length "1 .. 63";
           }
         }
       }
     }
     leaf dynamic-profile {
       description " dynamic profile for interface to use";
       type string {
         length "1 .. 80";
       }
     }
     leaf tunnel-switch-profile {
       description "Tunnel switch profile name";
       type string {
         length "1 .. 63";
       }
     }
     container syslog {
       description "Define system logging parameters";
       uses log-object;
     }
     leaf maximum-sessions {
       description "Maximum number of sessions per tunnel-group";
       type union {
         type uint32;
         type string {
           pattern "<.*>|$.*";
         }
       }
     }
     leaf service-profile {
       description "Dynamic service profile(s) to be applied to this session";
       type string;
     }
   }
   grouping li_policy_addr6_simple_object {
     uses apply-advanced;
     leaf address {
       description "Prefix to match";
       type jt:ipv6prefix;
     }
   }
   grouping li_policy_addr_simple_object {
     uses apply-advanced;
     leaf address {
       description "Prefix to match";
       type jt:ipv4prefix;
     }
   }
   grouping lns_server_type {
     leaf name {
       description "L2TP network server address";
       type jt:ipv4addr;
     }
     choice lns-port {
       case case_1 {
         leaf use-default-port {
           description "Use default port";
           type empty;
         }
       }
       case case_2 {
         leaf port {
           description "L2TP network server destination port";
           type union {
             type uint16;
             type string {
               pattern "<.*>|$.*";
             }
           }
         }
       }
     }
   }
   grouping log-object {
     description "Configure auditable security logs";
     uses apply-advanced;
     list exclude {
       key name;
       ordered-by user;
       description "List of security log criteria to exclude from the audit log";
       status deprecated;
       leaf name {
         description "Exclude criteria name";
         type string;
       }
       uses apply-advanced;
       leaf destination-address {
         description "Destination address";
         type jt:ipaddr;
       }
       leaf destination-port {
         description "Destination port";
         type union {
           type uint32;
           type string {
             pattern "<.*>|$.*";
           }
         }
       }
       leaf event-id {
         description "Event ID filter";
         type string;
       }
       leaf failure {
         description "Event was a failure";
         type empty;
       }
       leaf interface-name {
         description "Name of interface";
         type string;
       }
       leaf policy-name {
         description "Policy name filter";
         type string;
       }
       leaf process {
         description "Process that generated the event";
         type string;
       }
       leaf protocol {
         description "Protocol filter";
         type string;
       }
       leaf source-address {
         description "Source address";
         type jt:ipaddr;
       }
       leaf source-port {
         description "Source port";
         type union {
           type uint32;
           type string {
             pattern "<.*>|$.*";
           }
         }
       }
       leaf success {
         description "Event was successful";
         type empty;
       }
       leaf username {
         description "Username filter";
         type string;
       }
     }
     leaf limit {
       description "Limit number of security log entries to keep in memory";
       status deprecated;
       default "10000";
       type union {
         type uint32;
         type string {
           pattern "<.*>|$.*";
         }
       }
     }
     container cache {
       presence "enable cache";
       description "Cache security log events in the audit log buffer";
       uses apply-advanced;
       list exclude {
         key name;
         ordered-by user;
         description "List of security log criteria to exclude from the audit log";
         leaf name {
           description "Exclude criteria name";
           type string;
         }
         uses apply-advanced;
         leaf destination-address {
           description "Destination address";
           type jt:ipaddr;
         }
         leaf destination-port {
           description "Destination port";
           type union {
             type uint32;
             type string {
               pattern "<.*>|$.*";
             }
           }
         }
         leaf event-id {
           description "Event ID filter";
           type string;
         }
         leaf failure {
           description "Event was a failure";
           type empty;
         }
         leaf interface-name {
           description "Name of interface";
           type string;
         }
         leaf policy-name {
           description "Policy name filter";
           type string;
         }
         leaf process {
           description "Process that generated the event";
           type string;
         }
         leaf protocol {
           description "Protocol filter";
           type string;
         }
         leaf source-address {
           description "Source address";
           type jt:ipaddr;
         }
         leaf source-port {
           description "Source port";
           type union {
             type uint32;
             type string {
               pattern "<.*>|$.*";
             }
           }
         }
         leaf success {
           description "Event was successful";
           type empty;
         }
         leaf username {
           description "Username filter";
           type string;
         }
       }
       leaf limit {
         description "Limit number of security log entries to keep in memory";
         default "10000";
         type union {
           type uint32;
           type string {
             pattern "<.*>|$.*";
           }
         }
       }
     }
     list host {
       key name;
       ordered-by user;
       max-elements 10;
       leaf name {
         description "Name of host to notify";
         type string {
         }
       }
       uses apply-advanced;
       list contents {
         key name;
         leaf name {
           description "Facility type";
           type enumeration {
             enum "services" {
               description "Adaptive Services PIC";
             }
           }
         }
         choice level {
           case case_1 {
             leaf any {
               description "All levels";
               type empty;
             }
           }
           case case_2 {
             leaf emergency {
               description "Panic conditions";
               type empty;
             }
           }
           case case_3 {
             leaf alert {
               description "Conditions that should be corrected immediately";
               type empty;
             }
           }
           case case_4 {
             leaf critical {
               description "Critical conditions";
               type empty;
             }
           }
           case case_5 {
             leaf error {
               description "Error conditions";
               type empty;
             }
           }
           case case_6 {
             leaf warning {
               description "Warning messages";
               type empty;
             }
           }
           case case_7 {
             leaf notice {
               description "Conditions that should be handled specially";
               type empty;
             }
           }
           case case_8 {
             leaf info {
               description "Informational messages";
               type empty;
             }
           }
           case case_9 {
             leaf none {
               description "No messages";
               type empty;
             }
           }
         }
       }
       leaf facility-override {
         description "Alternate facility for logging to remote host";
         type enumeration {
           enum "authorization" {
             description "Authorization system";
           }
           enum "daemon" {
             description "Various system processes";
           }
           enum "ftp" {
             description "FTP process";
           }
           enum "kernel" {
             description "Kernel";
           }
           enum "user" {
             description "User processes";
           }
           enum "local0" {
             description "Local logging option number 0";
           }
           enum "local1" {
             description "Local logging option number 1";
           }
           enum "local2" {
             description "Local logging option number 2";
           }
           enum "local3" {
             description "Local logging option number 3";
           }
           enum "local4" {
             description "Local logging option number 4";
           }
           enum "local5" {
             description "Local logging option number 5";
           }
           enum "local6" {
             description "Local logging option number 6";
           }
           enum "local7" {
             description "Local logging option number 7";
           }
         }
       }
       leaf log-prefix {
         description "Prefix for all logging to this host";
         type string {
         }
       }
       leaf port {
         description "UDP port for syslogd on the host";
         type union {
           type string {
             pattern "<.*>|$.*";
           }
           type uint16 {
             range "1 .. 65535";
           }
         }
       }
       container class {
         description "Syslog messages classes";
         uses apply-advanced;
         container session-logs {
           presence "enable session-logs";
           description "Allow syslog messages for session events";
           uses apply-advanced;
           container open {
             presence "enable open";
             description "Allow syslog messages for session open events";
           }
           container close {
             presence "enable close";
             description "Allow syslog messages for session close events";
           }
         }
         container packet-logs {
           presence "enable packet-logs";
           description "Allow syslog messages for packet related events";
         }
         container stateful-firewall-logs {
           presence "enable stateful-firewall-logs";
           description "Allow syslog messages for stateful firewall events";
         }
         container alg-logs {
           presence "enable alg-logs";
           description "Allow syslog messages for ALG events";
         }
         container nat-logs {
           presence "enable nat-logs";
           description "Allow syslog messages for NAT events";
           uses apply-advanced;
           container deterministic-nat-configuration-log {
             presence "enable deterministic-nat-configuration-log";
             description "Allow syslog messages for Determinisitic NAT config events";
           }
         }
         container ids-logs {
           presence "enable ids-logs";
           description "Allow syslog messages for IDS events";
         }
         container pcp-logs {
           presence "enable pcp-logs";
           description "PCP logs";
           container map {
             presence "enable map";
             description "Allow syslog messages for PCP";
           }
           container debug {
             presence "enable debug";
             description "Allow PCP debug syslogs";
           }
         }
         container ha-logs {
           description "Stateful high availability logs";
           uses apply-advanced;
           container open-synchronized {
             presence "enable open-synchronized";
             description "Allow syslog message for session open events";
           }
           container close-synchronized {
             presence "enable close-synchronized";
             description "Allow syslog message for session close events";
           }
         }
         container urlf-logs {
           presence "enable urlf-logs";
           description "Allow syslog messages for URLF events";
         }
       }
       leaf source-address {
         description "Use specified address as source address";
         type jt:ipv4addr;
       }
       container tcp-log {
         presence "enable tcp-log";
         description "Enable tcp log for this service-set";
         uses apply-advanced;
         leaf source-address {
           description "Source address for tcp logging";
           type jt:ipaddr;
         }
         leaf vrf-name {
           description "Routing instance name for tcp logging";
           type string;
         }
         leaf ssl-profile {
           description "SSL profile name for tcp logging";
           type string {
             length "1 .. 63";
           }
         }
       }
     }
     leaf message-rate-limit {
       description "Maximum syslog messages per second allowed from this interface. Applies per member if set at aggregate level";
       units "messages per second";
       type union {
         type string {
           pattern "<.*>|$.*";
         }
         type uint32 {
           range "0 .. 2147483647";
         }
       }
     }
   }
   grouping logapn_type {
     leaf name {
       description "Logical access point name identifier";
       type string {
       }
     }
     uses apply-advanced;
     leaf access-type {
       description "User access to the APN";
       status deprecated;
       default "restricted";
       type enumeration {
         enum "public" {
           description "User does not need to be subscribed for APN";
           status deprecated;
         }
         enum "from-user" {
           description "Can choose which APN to connect";
           status deprecated;
         }
         enum "from-sgsn" {
           description "Can connect to default APN for the SGSN";
           status deprecated;
         }
         enum "restricted" {
           description "Admit only users subscribed for APN";
           status deprecated;
         }
       }
     }
     container access-restrictions {
       description "Settings for APN access restrictions. ";
       uses apply-advanced;
       leaf selection-mode {
         description "User access to the APN";
         default "restricted";
         type enumeration {
           enum "public" {
             description "User does not need to be subscribed for APN";
           }
           enum "from-user" {
             description "Can choose which APN to connect";
           }
           enum "from-sgsn" {
             description "Can connect to default APN for the SGSN";
           }
           enum "restricted" {
             description "Admit only users subscribed for APN";
           }
         }
       }
       container radius-assisted-apn-selection {
         presence "enable radius-assisted-apn-selection";
         description "Enable RADIUS assisted APN selection";
         uses apply-advanced;
         leaf default {
           description "Default APN name for radius assisted APN selection";
           type string {
           }
         }
       }
     }
     container apn {
       description "APN selection configuration";
       uses apply-advanced;
       leaf default {
         description "APN used when not using username-based selection";
         type string {
         }
       }
       list selectable {
         key name;
         ordered-by user;
         description "APNs that may be selected by the user";
         uses logical_to_apn_reference_type;
       }
     }
   }
   grouping logical_to_apn_reference_type {
     leaf name {
       description "Name of APN";
       type string {
       }
     }
     uses apply-advanced;
   }
   grouping lrf-profile-object {
     leaf name {
       description "Name of profile";
       type string {
         length "1 .. 63";
       }
     }
     uses apply-advanced;
     leaf policy-based-logging {
       description "Set rule based on policy";
       type empty;
     }
     leaf http-log-multiple-transactions {
       description "Log http multiple transactions";
       type empty;
     }
     list rule {
       key name;
       ordered-by user;
       description "One or more LRF rules";
       max-elements 32;
       uses lrf_rule_object;
     }
     list collector {
       key name;
       ordered-by user;
       description "One or more LRF collectors";
       max-elements 8;
       uses lrf_collector_object;
     }
     leaf-list vendor-support {
       ordered-by user;
       description "LRF 3rd party vendor support sub-template";
       type enumeration {
         enum "ibm" {
           description "IBM supported sub-template";
         }
       }
     }
     list template {
       key name;
       ordered-by user;
       description "LRF template";
       max-elements 16;
       uses lrf-template-object;
     }
     container performance-mode {
       description "Enable performance mode knob for LRF performance";
       uses lrf_perf_object;
     }
   }
   grouping lrf-template-object {
     leaf name {
       description "Name of template";
       type string {
         length "1 .. 32";
       }
     }
     uses apply-advanced;
     leaf format {
       description "Template format";
       type enumeration {
         enum "ipfix" {
           description "IPFIX template";
         }
       }
     }
     leaf-list template-type {
       ordered-by user;
       description "Template type";
       type enumeration {
         enum "ipv4" {
           description "IPv4 type";
         }
         enum "ipv4-extended" {
           description "IPv4 Extended type";
         }
         enum "ipv6" {
           description "IPv6 type";
         }
         enum "ipv6-extended" {
           description "IPv6 Extended type";
         }
         enum "transport-layer" {
           description "Transport Layer type";
         }
         enum "flow-id" {
           description "Flow ID type";
         }
         enum "ipflow" {
           description "IPFlow type";
         }
         enum "ipflow-ts" {
           description "IPFlow TS type";
         }
         enum "ipflow-extended" {
           description "IPFlow Extended type";
         }
         enum "device-data" {
           description "Device Data type";
         }
         enum "l7-app" {
           description "L7 APP type";
         }
         enum "http" {
           description "HTTP type";
         }
         enum "subscriber-data" {
           description "Subscriber data type";
         }
         enum "mobile-subscriber" {
           description "Mobile subscriber type";
         }
         enum "ifl-subscriber" {
           description "IFL based subscriber type";
         }
         enum "wireline-subscriber" {
           description "Wireline subscriber type";
         }
         enum "ipflow-tcp-ts" {
           description "IPFlow TCP TS type (IBM specific)";
         }
         enum "ipflow-tcp" {
           description "IPFlow TCP type";
         }
         enum "video" {
           description "Video fields type";
         }
         enum "dns" {
           description "DNS fields type";
         }
         enum "status-code-distribution" {
           description "Status code distribution for HTTP and DNS";
         }
         enum "pcc" {
           description "PCC type";
         }
       }
     }
     leaf-list trigger-type {
       ordered-by user;
       description "Trigger type";
       type enumeration {
         enum "session-close" {
           description "Session close trigger";
         }
         enum "volume" {
           description "Volume trigger";
         }
         enum "time" {
           description "Time limit trigger";
         }
       }
     }
     leaf template-tx-interval {
       description "Template export interval";
       default "60";
       units "seconds";
       type union {
         type string {
           pattern "<.*>|$.*";
         }
         type uint32 {
           range "10 .. 600";
         }
       }
     }
   }
   grouping lrf_collector_object {
     leaf name {
       description "Name of collector";
       type string {
         length "1 .. 32";
       }
     }
     uses apply-advanced;
     container destination {
       presence "enable destination";
       description "Destination collector configuration";
       uses apply-advanced;
       leaf address {
         description "Destination IPv4 address of collector";
         type jt:ipv4addr;
       }
       leaf port {
         description "Destination port of collector";
         type union {
           type uint16;
           type string {
             pattern "<.*>|$.*";
           }
         }
       }
     }
     leaf source-address {
       description "Source address to be used in the export packets";
       type jt:ipv4addr;
     }
   }
   grouping lrf_perf_object {
     uses apply-advanced;
     leaf packet-count {
       description "Max packet inspection threshold including both c2s and s2c direction packets ";
       default "20";
       type union {
         type string {
           pattern "<.*>|$.*";
         }
         type uint32 {
           range "20 .. 1000";
         }
       }
     }
   }
   grouping lrf_rule_object {
     leaf name {
       description "Name of rule";
       type string {
         length "1 .. 63";
       }
     }
     uses apply-advanced;
     leaf match-direction {
       description "Match direction";
       default "both";
       type enumeration {
         enum "client-to-server" {
           description "Client to server";
         }
         enum "server-to-client" {
           description "Server to client";
         }
         enum "both" {
           description "Both client-to-server and server-to-client";
         }
       }
     }
     container from {
       description "Match criteria";
       presence "enable from";
       uses lrf_match_object;
     }
     container then {
       description "Action to take for matched condition";
       uses apply-advanced;
       container report {
         description "Report action";
         presence "enable report";
         uses lrf_report_object;
       }
     }
   }
   grouping lrf_match_object {
     uses apply-advanced;
     list source-prefix-list {
       key name;
       ordered-by user;
       description "One or more named lists of source prefixes to match";
       leaf name {
         description "Name of prefix list to match against";
         type string;
       }
       leaf except {
         description "Name of prefix list not to match against";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list source-ports {
       ordered-by user;
       description "Source port list specification";
       type union {
         type string {
           pattern "<.*>|$.*";
         }
         type uint32 {
           range "0 .. 65535";
         }
       }
     }
     leaf-list destination-ports {
       ordered-by user;
       description "Destination port list specification";
       type union {
         type string {
           pattern "<.*>|$.*";
         }
         type uint32 {
           range "0 .. 65535";
         }
       }
     }
     leaf app-unknown {
       description "Use to specify unknown application as the match criteria";
       type empty;
     }
     list application-names {
       key name;
       ordered-by user;
       description "Match one or more applications";
       leaf name {
         description "Name of application";
         type string {
           length "1 .. 63";
         }
       }
       uses apply-advanced;
     }
     list application-groups {
       key name;
       ordered-by user;
       description "Match one or more application groups";
       leaf name {
         description "Name of application group";
         type string {
           length "1 .. 63";
         }
       }
       uses apply-advanced;
     }
   }
   grouping lrf_report_object {
     uses apply-advanced;
     leaf volume-limit {
       description "Volume limit";
       units "megabytes";
       type union {
         type string {
           pattern "<.*>|$.*";
         }
         type uint16 {
           range "1 .. 1024";
         }
       }
     }
     leaf time-limit {
       description "Time limit";
       default "300";
       units "seconds";
       type union {
         type string {
           pattern "<.*>|$.*";
         }
         type uint32 {
           range "60 .. 1800";
         }
       }
     }
     leaf template {
       description "Template to be used for export";
       type string;
     }
     leaf-list collector {
       ordered-by user;
       description "List of collectors that receive the export packets";
       type string {
         length "1 .. 63";
       }
       max-elements 3;
     }
   }
   grouping macro-data-type {
     leaf name {
       description "Keyword part of the keyword-value pair";
       type string;
     }
     leaf value {
       description "Value part of the keyword-value pair";
       type string;
     }
   }
   grouping mape_object {
     leaf name {
       description "MAP-E softwire concentrator name";
       type string {
         length "1 .. 63";
       }
     }
     uses apply-advanced;
     leaf softwire-address {
       description "Softwire concentrator IPV6 Address";
       type jt:ipv6addr;
     }
     leaf ipv4-prefix {
       description "MAP-E domains's rule IPv4 prefix/len";
       type jt:ipv4prefix;
     }
     leaf mape-prefix {
       description "MAP-E domain's rule IPV6 prefix/len";
       type jt:ipv6prefix;
     }
     leaf ea-bits-len {
       description "MAP-E domain's rule EA (Embedded Address) len";
       type union {
         type string {
           pattern "<.*>|$.*";
         }
         type uint32 {
           range "0 .. 48";
         }
       }
     }
     leaf psid-offset {
       description "MAP-E domain's PSID offset";
       default "4";
       type union {
         type string {
           pattern "<.*>|$.*";
         }
         type uint32 {
           range "0 .. 16";
         }
       }
     }
     leaf psid-length {
       description "MAP-E domain's PSID length";
       type union {
         type string {
           pattern "<.*>|$.*";
         }
         type uint32 {
           range "0 .. 16";
         }
       }
     }
     leaf mtu-v6 {
       description "MTU for the MAP-E softwire tunnel";
       default "9192";
       type union {
         type string {
           pattern "<.*>|$.*";
         }
         type int32 {
           range "1280 .. 9192";
         }
       }
     }
     leaf version-03 {
       description "MAP-E map-03 support";
       type empty;
     }
     leaf v4-reassembly {
       description "MAP-E IPv4 reassembly support";
       type empty;
     }
     leaf v6-reassembly {
       description "MAP-E IPv6 reassembly support";
       type empty;
     }
     leaf disable-auto-route {
       description "MAP-E Disable Auto Route";
       type empty;
     }
     leaf v4-partial-reassembly {
       description "For higher number of fragments/reassembled packet size";
       type empty;
     }
   }
   grouping mapt_object {
     leaf name {
       description "MAP-T softwire concentrator name";
       type string {
         length "1 .. 63";
       }
     }
     uses apply-advanced;
     leaf dmr-prefix {
       description "Softwire DMR IPV6 Address";
       type jt:ipv6prefix;
     }
     leaf ipv4-prefix {
       description "MAP-T domains's rule IPv4 prefix/len";
       type jt:ipv4prefix;
     }
     leaf mapt-prefix {
       description "MAP-T domain's rule IPV6 prefix/len";
       type jt:ipv6prefix;
     }
     leaf ea-bits-len {
       description "MAP-T domain's rule EA (Embedded Address) len";
       type union {
         type string {
           pattern "<.*>|$.*";
         }
         type uint8 {
           range "0 .. 48";
         }
       }
     }
     leaf psid-offset {
       description "MAP-T domain's PSID offset";
       default "4";
       type union {
         type string {
           pattern "<.*>|$.*";
         }
         type uint8 {
           range "0 .. 16";
         }
       }
     }
     leaf psid-length {
       description "MAP-T domain's PSID length";
       type union {
         type string {
           pattern "<.*>|$.*";
         }
         type uint8 {
           range "0 .. 16";
         }
       }
     }
     leaf mtu-v6 {
       description "MTU for the MAP-T softwire tunnel";
       default "9192";
       type union {
         type string {
           pattern "<.*>|$.*";
         }
         type uint16 {
           range "1280 .. 9192";
         }
       }
     }
   }
   grouping match_li_simple_dscp_value {
     uses apply-advanced;
     leaf value_keyword {
       type string;
     }
   }
   grouping match_li_simple_port_value {
     uses apply-advanced;
     leaf value_keyword {
       type string;
     }
   }
   grouping match_li_simple_protocol_value {
     uses apply-advanced;
     leaf value_keyword {
       type string;
     }
   }
   grouping monitor-threshold {
     leaf normal {
       description "Usage under normal conditions";
       type union {
         type string {
           pattern "<.*>|$.*";
         }
         type uint8 {
           range "1 .. 100";
         }
       }
     }
     leaf threshold {
       description "Threshold upon which alarm is raised";
       type union {
         type string {
           pattern "<.*>|$.*";
         }
         type uint8 {
           range "1 .. 100";
         }
       }
     }
   }
   grouping name-resolution-cache-type {
     description "Configuration of DNS responses cache";
     uses apply-advanced;
     container maximum-time-in-cache {
       presence "enable maximum-time-in-cache";
       description "Maximum time a DNS response may be held in the cache";
       choice maximum-time-in-cache {
         case case_1 {
           leaf unlimited {
             description "Cache according to TTL";
             type empty;
           }
         }
         case case_2 {
           leaf time {
             description "Seconds";
             type union {
               type string {
                 pattern "<.*>|$.*";
               }
               type uint32 {
                 range "0 .. 604800";
               }
             }
           }
         }
       }
     }
     leaf maximum-records-in-cache {
       description "Maximum number of DNS responses that may be held in the cache";
       default "5000";
       type union {
         type string {
           pattern "<.*>|$.*";
         }
         type uint32 {
           range "0 .. 50000";
         }
       }
     }
     leaf blacklist-period {
       description "Time (in seconds) a record will be held in the blacklist";
       default "600";
       type union {
         type string {
           pattern "<.*>|$.*";
         }
         type uint32 {
           range "0 .. 86400";
         }
       }
     }
     container accelerations {
       presence "enable accelerations";
       description "Mechanisms for accelerating DNS resolving";
       uses apply-advanced;
       leaf no-refresh-before-ttl-expiry {
         description "Don't send a new query for records that are about to expire";
         type empty;
       }
       leaf initiate-next-queries {
         description "Immediately initiate queries for referenced entries (e.g A entries referenced from SRV ones)";
         type empty;
       }
       leaf initiate-alternative-queries {
         description "Initiate NAPTR, SRV and A record queries, in parallel, for every new SIP URI";
         type empty;
       }
     }
   }
   grouping name_server_type {
     leaf name {
       description "IPv4 DNS name server address";
       type jt:ipv4addr;
     }
     uses apply-advanced;
   }
   grouping nat-object {
     description "Configure Network Address Translation";
     uses apply-advanced;
     list pool {
       key name;
       ordered-by user;
       description "Define a NAT pool";
       uses nat_pool_object;
     }
     list ipv6-multicast-interfaces {
       key name;
       ordered-by user;
       description "Enable IPv6 multicast filter for IPv6 NAT";
       leaf name {
         description "Interface name";
         type string;
       }
       uses apply-advanced;
       leaf disable {
         description "Disable IPv6 multicast filter for IPv6 NAT";
         type empty;
       }
     }
     leaf allow-overlapping-nat-pools {
       description "Allow usage of overlapping and same nat pools in multiple service sets";
       type empty;
     }
     list rule {
       key name;
       ordered-by user;
       description "Define a NAT rule";
       uses nat_rule_object;
     }
     list port-forwarding {
       key name;
       ordered-by user;
       description "Define a port-forwarding pool";
       uses pf_mapping;
     }
     list rule-set {
       key name;
       ordered-by user;
       description "Defines a set of NAT rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping nat_pool_object {
     leaf name {
       description "Pool name";
       type string {
         length "1 .. 63";
       }
     }
     uses apply-advanced;
     container pgcp {
       presence "enable pgcp";
       description "NAT pool should be used exclusive by the pgcp service";
       uses apply-advanced;
       leaf remotely-controlled {
         description "Remotely controlled NAT pool allocation";
         type empty;
       }
       leaf ports-per-session {
         description "Number of ports to allocate in each call setup";
         default "2";
         type union {
           type uint8;
           type string {
             pattern "<.*>|$.*";
           }
         }
       }
       list hint {
         key name;
         ordered-by user;
         description "NAT-hint list (Any string available up to 3 characters, not mandatory field)";
         max-elements 5;
         uses nat_pgcp_hint_list_object;
       }
       leaf-list transport {
         ordered-by user;
         description "NAT pool transport types list";
         type enumeration {
           enum "tcp" {
             description "TCP";
           }
           enum "udp" {
             description "UDP";
           }
           enum "rtp-avp" {
             description "RTP/AVP";
           }
         }
       }
     }
     list address {
       key name;
       ordered-by user;
       description "Address or address prefix for NAT";
       leaf name {
         type jt:ipprefix-only;
       }
       uses apply-advanced;
     }
     container interface {
       description "Interface for nat pool";
       leaf interface-name {
         type union {
           type jt:interface-unit;
           type string {
             pattern "<.*>|$.*";
           }
         }
       }
     }
     leaf address-overload {
       description "Nat pool address overload with JunOS";
       type empty;
     }
     list address-range {
       key "low high";
       ordered-by user;
       description "Range of addresses for NAT";
       leaf low {
         description "Lower limit of address range";
         type jt:ipaddr;
       }
       leaf high {
         description "Upper limit of address range";
         type jt:ipaddr;
       }
     }
     container port {
       description "Specify ports for NAT";
       uses apply-advanced;
       choice port_choice {
         case case_1 {
           container automatic {
             presence "enable automatic";
             uses apply-advanced;
             choice automatic_choice {
               case case_1 {
                 leaf auto {
                   description "Automatically choose ports";
                   status deprecated;
                   type empty;
                 }
               }
               case case_2 {
                 leaf sequential {
                   description "Allocate ports in sequence";
                   type empty;
                 }
               }
               case case_3 {
                 leaf random-allocation {
                   description "Allocate ports randomly";
                   type empty;
                 }
               }
             }
           }
         }
         case case_2 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
             leaf random-allocation {
               description "Allocate ports randomly";
               type empty;
             }
           }
         }
       }
       choice block-allocation-choice {
         case case_1 {
           container secured-port-block-allocation {
             presence "enable secured-port-block-allocation";
             description "Secured Port block allocation";
             leaf block-size {
               description "Number of port per block.";
               default "128";
               type union {
                 type string {
                   pattern "<.*>|$.*";
                 }
                 type uint16 {
                   range "1 .. 64512";
                 }
               }
             }
             leaf max-blocks-per-address {
               description "Max block per address";
               default "8";
               type union {
                 type string {
                   pattern "<.*>|$.*";
                 }
                 type uint16 {
                   range "1 .. 512";
                 }
               }
             }
             leaf active-block-timeout {
               description "Active block timeout";
               default "120";
               type union {
                 type string {
                   pattern "<.*>|$.*";
                 }
                 type uint32 {
                   range "0 .. 86400";
                 }
               }
             }
           }
         }
         case case_2 {
           container deterministic-port-block-allocation {
             presence "enable deterministic-port-block-allocation";
             description "Deterministic Port Block Allocation";
             leaf block-size {
               description "Number of ports per block";
               default "512";
               type union {
                 type string {
                   pattern "<.*>|$.*";
                 }
                 type uint16 {
                   range "0 .. 64512";
                 }
               }
             }
             leaf include-boundary-addresses {
               description "Include network and broadcast in 'from' src-addresses";
               type empty;
             }
           }
         }
       }
       leaf preserve-parity {
         description "Allocate port with same parity as original port";
         type empty;
       }
       leaf preserve-range {
         description "Preserve privileged port range after NAT";
         type empty;
       }
     }
     container address-allocation {
       presence "enable address-allocation";
       description "Address allocation method for NAPT";
       uses apply-advanced;
       leaf round-robin {
         description "Round robin method of allocation";
         type empty;
       }
     }
     leaf mapping-timeout {
       description "Address-pooling paired and endpoint-independent mapping timeout (120..86400)";
       default "300";
       units "second";
       type union {
         type int32;
         type string {
           pattern "<.*>|$.*";
         }
       }
     }
     leaf flow-timeout {
       description "Default flow timeout for NAT flows";
       default "300";
       units "second";
       type union {
         type string {
           pattern "<.*>|$.*";
         }
         type int32 {
           range "30 .. 86400";
         }
       }
     }
     leaf ei-mapping-timeout {
       description "Endpoint-independent mapping timeout (120..86400)";
       units "second";
       type union {
         type int32;
         type string {
           pattern "<.*>|$.*";
         }
       }
     }
     leaf app-mapping-timeout {
       description "Address-pooling paired mapping timeout (120..86400)";
       units "second";
       type union {
         type int32;
         type string {
           pattern "<.*>|$.*";
         }
       }
     }
     leaf limit-ports-per-address {
       description "Limit number of ports allocated per host (IP address)";
       units "connections";
       type union {
         type string {
           pattern "<.*>|$.*";
         }
         type int32 {
           range "2 .. 65435";
         }
       }
     }
     container snmp-trap-thresholds {
       presence "enable snmp-trap-thresholds";
       description "Define snmp traps for service sets";
       uses apply-advanced;
       container address-port {
         presence "enable address-port";
         description "Nat pool address and port usage trap threshold range";
         leaf low {
           description "Lower limit of pool trap threshold";
           units "percent";
           type union {
             type string {
               pattern "<.*>|$.*";
             }
             type uint16 {
               range "0 .. 100";
             }
           }
         }
         leaf high {
           description "Upper limit of pool trap threshold";
           units "percent";
           type union {
             type string {
               pattern "<.*>|$.*";
             }
             type uint16 {
               range "0 .. 100";
             }
           }
         }
       }
     }
   }
   grouping nat_pgcp_hint_list_object {
     description "NAT hints";
     leaf name {
       description "NAT-hint string list";
       type string {
         length "1 .. 4";
       }
     }
   }
   grouping nat_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match an input to or output from on interface";
         }
       }
     }
     list term {
       key name;
       ordered-by user;
       description "Define a NAT term";
       leaf name {
         description "Term name";
         type string {
           length "1 .. 63";
         }
       }
       uses apply-advanced;
       leaf nat-type {
         description "NAT type (symmetric/full-cone)";
         type enumeration {
           enum "symmetric" {
             description "Symmetric NAT";
           }
           enum "full-cone" {
             description "Full Cone NAT";
           }
         }
       }
       container from {
         description "Define match criteria";
         uses sfw_match_object;
       }
       container then {
         description "Action to take if the 'from' condition is matched";
         uses apply-advanced;
         choice designation {
           case case_1 {
             leaf no-translation {
               description "Do not perform translation";
               type empty;
             }
           }
         }
         choice port-forwarding {
           case case_1 {
             leaf port-forwarding-mappings {
               description "Port forwarding mappings";
               type string {
                 length "1 .. 63";
               }
             }
           }
         }
         container translated {
           description "Define translation parameters";
           uses apply-advanced;
           choice source-pool-choice {
             case case_1 {
               leaf source-pool {
                 description "NAT pool for source translation";
                 type string {
                   length "1 .. 63";
                 }
               }
             }
             case case_2 {
               leaf source-prefix {
                 description "NAT prefix for source translation";
                 type jt:ipprefix-only;
               }
             }
           }
           leaf clat-prefix {
             description "Clat-prefix to be used for 464 translation type";
             type jt:ipprefix-only;
           }
           leaf clat-ipv6-prefix-length {
             description "The ipv6 prefix length for CLAT source address";
             default "64";
             type enumeration {
               enum "32" {
                 description "The ipv6 prefix length of 32";
               }
               enum "40" {
                 description "The ipv6 prefix length of 40";
               }
               enum "48" {
                 description "The ipv6 prefix length of 48";
               }
               enum "56" {
                 description "The ipv6 prefix length of 56";
               }
               enum "64" {
                 description "The ipv6 prefix length of 64";
               }
               enum "96" {
                 description "The ipv6 prefix length of 96";
               }
             }
           }
           choice destination-pool-choice {
             case case_1 {
               leaf destination-pool {
                 description "NAT pool for destination translation";
                 type string {
                   length "1 .. 63";
                 }
               }
             }
             case case_2 {
               leaf destination-prefix {
                 description "NAT prefix for destination translation";
                 type jt:ipprefix-only;
               }
             }
           }
           choice dns-alg-pool-choice {
             case case_1 {
               leaf dns-alg-pool {
                 description "NAT pool for dns alg mappings";
                 type string {
                   length "1 .. 63";
                 }
               }
             }
             case case_2 {
               leaf dns-alg-prefix {
                 description "DNS ALG 96 bit prefix for mapping IPv4 addresses to IPv6 addresses";
                 type jt:ipprefix-only;
               }
             }
           }
           choice dns-map-address-for-destination-translation-choice {
             case case_1 {
               leaf use-dns-map-for-destination-translation {
                 description "Use dns alg address map for destination translation";
                 status deprecated;
                 type empty;
               }
             }
           }
           choice overload-pool-choice {
             case case_1 {
               leaf overload-pool {
                 description "NAT pool to be used when source pool is overloaded";
                 type string {
                   length "1 .. 63";
                 }
               }
             }
             case case_2 {
               leaf overload-prefix {
                 description "NAT prefix to be used when source pool is overloaded";
                 type jt:ipprefix-only;
               }
             }
           }
           container translation-type {
             description "Type of translation to perform";
             uses apply-advanced;
             leaf source {
               description "Type of source translation";
               status deprecated;
               type enumeration {
                 enum "static" {
                   description "Static translation";
                   status deprecated;
                 }
                 enum "dynamic" {
                   description "Dynamic translation";
                   status deprecated;
                 }
               }
             }
             leaf destination {
               description "Type of destination translation";
               status deprecated;
               type enumeration {
                 enum "static" {
                   description "Static translation";
                   status deprecated;
                 }
               }
             }
             container basic-nat44 {
               presence "enable basic-nat44";
               description "Static source address (IPv4 to IPv4) translation";
             }
             container dynamic-nat44 {
               presence "enable dynamic-nat44";
               description "Dynamic source address only (IPv4 to IPv4) translation";
             }
             container napt-44 {
               presence "enable napt-44";
               description "Source address (IPv4 to IPv4) and port translation";
             }
             container dnat-44 {
               presence "enable dnat-44";
               description "Static Destination address (IPv4 to IPv4) translation";
             }
             container stateful-nat64 {
               presence "enable stateful-nat64";
               description "Dynamic source address (IPv6 to IPv4) and prefix removal for destination address (IPv6 to IPv4)translation";
             }
             container stateful-nat464 {
               presence "enable stateful-nat464";
               description "Prefix removal for Src and Dest address (IPv6 to IPv4) translation";
             }
             container basic-nat-pt {
               presence "enable basic-nat-pt";
               description "NAT-PT (static source address (IPv6 to IPv4) and prefix removal for destination address (IPv6 to IPv4) translation)";
             }
             container napt-pt {
               presence "enable napt-pt";
               description "NAT-PT (source address (IPv6 to IPv4) and source port and prefix removal for destination address (IPv6 to IPv4) translation)";
             }
             container basic-nat66 {
               presence "enable basic-nat66";
               description "Static source address (IPv6 to IPv6) translation [same as basic-nat44 but for IPv6 address family]";
             }
             container nptv6 {
               presence "enable nptv6";
               description "Stateless source address (IPv6 to IPv6) translation";
             }
             container napt-66 {
               presence "enable napt-66";
               description "Source address (IPv6 to IPv6) and port translation [same as napt-44 but for IPv6 address family]";
             }
             container twice-napt-44 {
               presence "enable twice-napt-44";
               description "Source NAPT and destination static translation for IPv4 address family";
             }
             container twice-basic-nat-44 {
               presence "enable twice-basic-nat-44";
               description "Source static and destination static translation for IPv4 address family";
             }
             container twice-dynamic-nat-44 {
               presence "enable twice-dynamic-nat-44";
               description "Source dynamic and destination static translation for IPv4 address family";
             }
             container deterministic-napt44 {
               presence "enable deterministic-napt44";
               description "Deterministic source NAPT for IPv4 family";
               uses apply-advanced;
             }
             container deterministic-napt64 {
               presence "enable deterministic-napt64";
               description "Deterministic source NAPT for IPv6 family";
             }
           }
           leaf mapping-type {
             description "Source NAT mapping type";
             type enumeration {
               enum "endpoint-independent" {
                 description "Endpoint independent mapping";
               }
             }
           }
           leaf flow-type {
             description "Source NAT flow type";
             type enumeration {
               enum "endpoint-independent" {
                 description "Endpoint independent flow";
               }
             }
           }
           leaf ignore-dst-nat-1to1-limitation {
             description "Ignore destination NAT 1:1 limitation";
             type empty;
           }
           container secure-nat-mapping {
             presence "enable secure-nat-mapping";
             description "Mapping options for enhanced security";
             uses apply-advanced;
             leaf eif-flow-limit {
               description "Number of inbound flows to be allowed for a EIF mapping";
               type union {
                 type string {
                   pattern "<.*>|$.*";
                 }
                 type uint16 {
                   range "0 .. 65534";
                 }
               }
             }
             leaf mapping-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
             leaf flow-refresh {
               description "Enable timer refresh option";
               type enumeration {
                 enum "inbound" {
                   description "Enable timer refresh for inbound connections only";
                 }
                 enum "outbound" {
                   description "Enable timer refresh for outbound connections only";
                 }
                 enum "inbound-outbound" {
                   description "Enable timer refresh for inbound & outbound connections";
                 }
               }
             }
           }
           container filtering-type {
             description "Source NAT filtering type";
             uses apply-advanced;
             container endpoint-independent {
               presence "enable endpoint-independent";
               description "Endpoint independent filtering";
               uses apply-advanced;
               list prefix-list {
                 key name;
                 ordered-by user;
                 description "One or more named lists of source prefixes to match";
                 leaf name {
                   description "Name of prefix list to match against";
                   type string;
                 }
                 leaf except {
                   description "Name of prefix list not to match against";
                   type empty;
                 }
               }
             }
           }
           leaf address-pooling {
             description "Address pooling behavior for source NAT";
             type enumeration {
               enum "paired" {
                 description "Address pooling behavior of paired";
               }
             }
           }
         }
         leaf syslog {
           description "System log information about the packet";
           type empty;
         }
       }
     }
   }
   grouping new_call_then_type {
     uses apply-advanced;
     leaf trace {
       description "Trace messages accepted on this policy";
       type empty;
     }
     container media-policy {
       description "Media policy parameters";
       uses apply-advanced;
       choice anchoring-policy {
         case case_1 {
           leaf no-anchoring {
             description "Setting this would bypass media packet gateway processing";
             type empty;
           }
         }
         case case_2 {
           leaf media-release {
             description "Release media - media will not be anchored";
             type empty;
           }
         }
       }
       container nat-traversal {
         presence "enable nat-traversal";
         description "Choose when to perform NAT traversal";
         uses apply-advanced;
         leaf nat-traversal-strategy {
           description "Choose when to perform NAT traversal";
           type enumeration {
             enum "never" {
               description "Never perform NAT traversal";
             }
             enum "always" {
               description "Always perform NAT traversal";
             }
             enum "same-as-signaling" {
               description "Perform NAT traversal according to signaling";
             }
           }
         }
         leaf force-bidirectional-media {
           description "Force bidirectional media";
           type empty;
         }
       }
       container data-inactivity-detection {
         description "Configuration of data inactivity indicators";
         uses apply-advanced;
         leaf inactivity-duration {
           description "The amount of time in seconds a stream is inactive before a notification is sent to the SPDF";
           units "seconds";
           type union {
             type string {
               pattern "<.*>|$.*";
             }
             type uint16 {
               range "30 .. 3600";
             }
           }
         }
       }
       leaf service-class {
         description "Rate limiting and dscp marking based on the media type";
         type string {
           length "1 .. 63";
         }
       }
     }
   }
   grouping new_call_usage_set_type {
     leaf name {
       description "Policy set name";
       type string;
     }
     uses apply-advanced;
     leaf-list policy-name {
       ordered-by user;
       description "Policy name";
       type string;
       max-elements 500;
     }
   }
   grouping new_registration_set_type {
     leaf name {
       description "Policy set name";
       type string;
     }
     uses apply-advanced;
     leaf-list policy-name {
       ordered-by user;
       description "Policy name";
       type string;
       max-elements 500;
     }
   }
   grouping new_transaction_set_type {
     leaf name {
       description "Policy set name";
       type string;
     }
     uses apply-advanced;
     leaf-list policy-name {
       ordered-by user;
       description "Policy name";
       type string;
       max-elements 500;
     }
   }
   grouping p_cscf_apn_type {
     uses apply-advanced;
     list server {
       key name;
       ordered-by user;
       description "IPv4 or IPv6 P-CSCF server";
       max-elements 10;
       leaf name {
         description "IPv4 or IPv6 P-CSCF server address";
         type jt:ipaddr;
       }
       uses apply-advanced;
     }
     list filtering-server {
       key name;
       ordered-by user;
       description "IPv4 P-CSCF filtering server";
       max-elements 10;
       leaf name {
         description "IPv4 filtering server address";
         type jt:ipv4addr;
       }
       uses apply-advanced;
     }
     leaf no-general-purpose {
       description "No general purpose contexts allowed";
       type empty;
     }
     leaf no-dedicated-signaling {
       description "No dedicated signaling contexts allowed";
       type empty;
     }
     leaf no-general-signaling-indication {
       description "No signaling indication for general purpose contexts allowed";
       type empty;
     }
     leaf no-dedicated-signaling-indication {
       description "No signaling indication for dedicated signaling contexts allowed";
       type empty;
     }
     leaf address-format {
       description "Settings for address format in GTP response";
       type enumeration {
         enum "no-ipv4" {
           description "Don't send ipv4 address";
         }
         enum "no-ipv4-compatible-ipv6" {
           description "Don't send ipv4 address compatible ipv6 address";
         }
       }
     }
   }
   grouping pcp-object {
     description "Configure Port Control Protocol";
     uses apply-advanced;
     container traceoptions {
       description "Trace options for PCP-LOG";
       uses apply-advanced;
       leaf no-remote-trace {
         description "Disable remote tracing";
         type empty;
       }
       container file {
         description "Trace file information";
         leaf filename {
           description "Name of file in which to write trace information";
           type string {
             length "1 .. 1024";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       list flag {
         key name;
         ordered-by user;
         description "Tracing parameters";
         leaf name {
           type enumeration {
             enum "configuration" {
               description "Trace configuration events";
             }
             enum "flow" {
               description "Trace flow events";
             }
             enum "all" {
               description "Trace everything";
             }
           }
         }
       }
     }
     list server {
       key name;
       ordered-by user;
       description "Define a PCP server";
       uses pcp-server-object;
     }
     list rule {
       key name;
       ordered-by user;
       description "Define a PCP rule";
       uses pcp-rule-object;
     }
     list rule-set {
       key name;
       ordered-by user;
       description "Defines a set of PCP rules";
       max-elements 16960;
       leaf name {
         description "Name of the rule set";
         type string {
           length "1 .. 63";
         }
       }
       uses apply-advanced;
       list rule {
         key name;
         ordered-by user;
         description "Rule to be included in this rule set";
         max-elements 16960;
         leaf name {
           description "Rule name";
           type string {
           }
         }
         uses apply-advanced;
       }
     }
   }
   grouping pcp-rule-object {
     leaf name {
       description "Rule name";
       type string {
         length "1 .. 63";
       }
     }
     uses apply-advanced;
     leaf match-direction {
       description "Define direction for which the rule match is applied";
       type enumeration {
         enum "input" {
           description "Match on input to interface";
         }
         enum "output" {
           description "Match on output from interface";
         }
       }
     }
     list term {
       key name;
       ordered-by user;
       description "Define a PCP term";
       leaf name {
         description "Term name";
         type string {
           length "1 .. 63";
         }
       }
       uses apply-advanced;
       container from {
         description "Define match criteria";
         uses sfw_match_object;
       }
       container then {
         description "Action to take if the 'from' condition is matched";
         uses apply-advanced;
         leaf pcp-server {
           description "Define PCP server";
           type string {
             length "1 .. 63";
           }
         }
       }
     }
     container match {
       description "Define match criteria";
       uses sfw_match_object;
     }
     container then {
       description "Action to take if the 'from' condition is matched";
       uses apply-advanced;
       leaf pcp-server {
         description "Define PCP server";
         type string {
           length "1 .. 63";
         }
       }
     }
   }
   grouping pcp-server-object {
     leaf name {
       description "Name of PCP server";
       type string {
         length "1 .. 63";
       }
     }
     uses apply-advanced;
     leaf ipv4-address {
       description "Configure IPv4 address for this PCP server";
       type jt:ipv4addr;
     }
     leaf ipv6-address {
       description "Configure IPv6 address for this PCP server";
       type jt:ipv6addr;
     }
     leaf softwire-concentrator {
       description "Softwire ds-lite concentrator";
       type string {
         length "1 .. 63";
       }
     }
     leaf softwire-concentrator-name {
       description "Softwire ds-lite concentrator";
       type string {
         length "1 .. 63";
       }
     }
     leaf mapping-lifetime-minimum {
       description "Configure the minimum lifetime for any mapping";
       default "120";
       units "second";
       type union {
         type string {
           pattern "<.*>|$.*";
         }
         type uint16 {
           range "120 .. 3600";
         }
       }
     }
     leaf mapping-lifetime-maximum {
       description "Configure the maximum lifetime for any mapping";
       default "86400";
       units "second";
       type union {
         type string {
           pattern "<.*>|$.*";
         }
         type uint32 {
           range "120 .. 4294667";
         }
       }
     }
     leaf short-lifetime-error {
       description "Configure duration of a short-lifetime error";
       default "30";
       units "second";
       type union {
         type string {
           pattern "<.*>|$.*";
         }
         type uint16 {
           range "15 .. 300";
         }
       }
     }
     leaf long-lifetime-error {
       description "Configure duration of a long-lifetime error";
       default "1800";
       units "second";
       type union {
         type string {
           pattern "<.*>|$.*";
         }
         type uint16 {
           range "900 .. 18000";
         }
       }
     }
     leaf max-mappings-per-client {
       description "Configure maximum mappings permitted per client";
       default "32";
       type union {
         type string {
           pattern "<.*>|$.*";
         }
         type uint16 {
           range "1 .. 128";
         }
       }
     }
     container pcp-options {
       description "Configure PCP options supported by this server";
       leaf third-party {
         description "Enable Third Party option";
         type empty;
       }
       leaf prefer-failure {
         description "Enable Prefer Failure option";
         type empty;
       }
     }
     container nat-options {
       description "NAT options of this PCP server";
       uses apply-advanced;
       list pool {
         key name;
         ordered-by user;
         description "NAT pool name";
         uses nat_pool_list_object;
       }
     }
     container nat-option {
       description "NAT option of this PCP server";
       uses apply-advanced;
       list pool {
         key name;
         ordered-by user;
         description "NAT pool name";
         uses nat_pool_list_object_usf;
       }
     }
   }
   grouping nat_pool_list_object {
     description "One or more nat pools";
     leaf name {
       type string {
         length "1 .. 63";
       }
     }
   }
   grouping nat_pool_list_object_usf {
     description "One or more nat pools";
     leaf name {
       type string {
         length "1 .. 63";
       }
     }
   }
   grouping pdp_context_type {
     uses apply-advanced;
     leaf creation {
       description "PDP context creation state";
       type enumeration {
         enum "unblocked" {
           description "No restrictions on PDP context creation";
         }
         enum "blocked" {
           description "New PDP context creation fully blocked";
         }
       }
     }
     leaf pdp-type {
       description "PDP context type";
       status deprecated;
       type enumeration {
         enum "ipv4" {
           description "IPv4 PDP context type";
           status deprecated;
         }
         enum "ipv6" {
           description "IPv6 PDP context type";
           status deprecated;
         }
         enum "ipv4+ipv6" {
           description "IPv4 and IPv6 PDP contexts";
           status deprecated;
         }
       }
     }
     leaf limit {
       description "Maximum active PDP contexts";
       type union {
         type string {
           pattern "<.*>|$.*";
         }
         type uint32 {
           range "1 .. 4294967295";
         }
       }
     }
     leaf ipv6-limit {
       description "Maximum active IPv6 PDP contexts";
       type union {
         type string {
           pattern "<.*>|$.*";
         }
         type uint32 {
           range "1 .. 4294967295";
         }
       }
     }
     leaf l2tp-sessions {
       description "Maximum L2TP sessions";
       default "50000";
       type union {
         type string {
           pattern "<.*>|$.*";
         }
         type uint32 {
           range "0 .. 65000";
         }
       }
     }
     leaf tft-ratio {
       description "Number of PDP contexts subject to TFT handling";
       units "percent";
       type union {
         type string {
           pattern "<.*>|$.*";
         }
         type uint32 {
           range "0 .. 100";
         }
       }
     }
     leaf payload-limit {
       description "Maximum active payload";
       default "50000";
       units "pps";
       type union {
         type string {
           pattern "<.*>|$.*";
         }
         type uint32 {
           range "10000 .. 4200000";
         }
       }
     }
     leaf reserved-secondary-capacity {
       description "Reserved secondary PDP context capacity";
       units "percent";
       type union {
         type string {
           pattern "<.*>|$.*";
         }
         type uint32 {
           range "0 .. 5";
         }
       }
     }
     leaf service-based-charging-ratio {
       description "Service-based-charging ratio";
       units "percent";
       type union {
         type string {
           pattern "<.*>|$.*";
         }
         type uint32 {
           range "0 .. 100";
         }
       }
     }
     leaf service-based-charging-uplink-ratio {
       description "Service-based-charging uplink traffic";
       default "30";
       units "percent";
       type union {
         type string {
           pattern "<.*>|$.*";
         }
         type uint32 {
           range "0 .. 100";
         }
       }
     }
     leaf service-classes-user-mean {
       description "Average number of service classes assigned to SBCC user";
       type union {
         type string {
           pattern "<.*>|$.*";
         }
         type uint32 {
           range "0 .. 64";
         }
       }
     }
     leaf service-classes-cdr-mean {
       description "Average number of service classes accessed per SBCC context";
       type union {
         type string {
           pattern "<.*>|$.*";
         }
         type uint32 {
           range "0 .. 64";
         }
       }
     }
     leaf service-identifier-cdr-mean {
       description "Average number of service identifier accessed per SBCC context";
       type union {
         type string {
           pattern "<.*>|$.*";
         }
         type uint32 {
           range "0 .. 64";
         }
       }
     }
     leaf allow-secondary {
       description "Allow secondary contexts";
       type empty;
     }
     container policing {
       description "Policing settings";
       uses policing_type;
     }
     container session-management {
       description "Session management settings";
       status deprecated;
       uses apply-advanced;
       leaf idle-timeout {
         description "Maximum consecutive idle minutes for a context";
         units "minutes";
         type union {
           type string {
             pattern "<.*>|$.*";
           }
           type uint32 {
             range "1 .. 525600";
           }
         }
       }
       leaf session-timeout {
         description "Maximum duration for a context";
         units "minutes";
         type union {
           type string {
             pattern "<.*>|$.*";
           }
           type uint32 {
             range "15 .. 1440";
           }
         }
       }
       leaf measurement-type {
         description "Point of reference for idle time and duration measurement";
         type enumeration {
           enum "since-creation" {
             description "Relative to the PDP context creation time";
           }
           enum "since-update" {
             description "Relative to the last PDP context update time";
           }
         }
       }
     }
     container session-control {
       description "Session control settings";
       uses session_management_type;
     }
     leaf shared-msisdn {
       description "Multiple mobiles may use same MSISDN";
       type empty;
     }
     list interfaces {
       key name;
       ordered-by user;
       description "Interface-specific PDP context creation settings";
       uses ggsn_interface_pdpcontrol_type;
     }
     container signaling {
       description "PDP context signaling settings";
       leaf ggsn-deletes-per-second {
         description "GGSN-initiated deletions per second per session controller";
         type union {
           type string {
             pattern "<.*>|$.*";
           }
           type uint32 {
             range "1 .. 5000";
           }
         }
       }
       leaf sgsn-creates-per-second {
         description "Maximum SGSN creates per second per session controller";
         type union {
           type string {
             pattern "<.*>|$.*";
           }
           type uint32 {
             range "0 .. 5000";
           }
         }
       }
       leaf sgsn-create-request-window-size {
         description "Maximum number of outstanding create requests";
         type union {
           type string {
             pattern "<.*>|$.*";
           }
           type uint32 {
             range "0 .. 5000";
           }
         }
       }
     }
   }
   grouping ggsn_interface_pdpcontrol_type {
     leaf name {
       description "Interface name";
       type union {
         type jt:interface-device;
         type string {
           pattern "<.*>|$.*";
         }
       }
     }
     leaf creation {
       description "PDP context creation state";
       type enumeration {
         enum "unblocked" {
           description "No restrictions on PDP context creation";
         }
         enum "blocked" {
           description "New PDP context creation fully blocked";
         }
       }
     }
     leaf limit {
       description "Maximum active PDP contexts";
       status deprecated;
       type union {
         type string {
           pattern "<.*>|$.*";
         }
         type uint32 {
           range "1 .. 4294967295";
         }
       }
     }
   }
   grouping pf_mapping {
     leaf name {
       description "Port Forwarding name";
       type string {
         length "1 .. 63";
       }
     }
     uses apply-advanced;
     list destined-port {
       key "port translated-port";
       ordered-by user;
       description "Port forwarding mappings";
       max-elements 32;
       leaf port {
         description "Destination port";
         type union {
           type string {
             pattern "<.*>|$.*";
           }
           type uint16 {
             range "1 .. 65535";
           }
         }
       }
       leaf translated-port {
         description "Translated port";
         type union {
           type string {
             pattern "<.*>|$.*";
           }
           type uint16 {
             range "1 .. 65535";
           }
         }
       }
     }
   }
   grouping pfcp-traceoptions-type {
     description "Trace options for SAEGW PFCP";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "configuration" {
             description "Trace configuration events";
           }
           enum "decode" {
             description "Trace PFCP protocol decode events";
           }
           enum "encode" {
             description "Trace PFCP protocol encode events";
           }
           enum "general" {
             description "Trace PFCP general events";
           }
           enum "heartbeat" {
             description "Trace PFCP heart beat management events";
           }
           enum "request-cache" {
             description "Trace PFCP request-cache events";
           }
           enum "operational-commands" {
             description "Trace PFCP events related to operational-commands";
           }
           enum "all" {
             description "Trace everything";
           }
         }
       }
     }
   }
   grouping pgcp_gateway_object {
     description "One or more Packet Gateways";
     leaf name {
       description "Gateway Name";
       type string {
         length "1 .. 63";
       }
     }
     uses apply-advanced;
     leaf gateway-address {
       description "Local Gateway IP address";
       type jt:ipv4addr;
     }
     leaf routing-instance {
       description "Routing instance";
       default "inet.0";
       type string;
     }
     leaf gateway-port {
       description "Local Gateway transport port";
       default "2944";
       type union {
         type uint16;
         type string {
           pattern "<.*>|$.*";
         }
       }
     }
     leaf cleanup-timeout {
       description "When expires the PG will clean its gate state (Applicable in disconnections)";
       units "seconds";
       type union {
         type string {
           pattern "<.*>|$.*";
         }
         type uint16 {
           range "5 .. 65535";
         }
       }
     }
     leaf service-state {
       description "Service state";
       type enumeration {
         enum "in-service" {
           description "Gateway is operational";
         }
         enum "out-of-service-forced" {
           description "Gateway is nonoperational";
         }
         enum "out-of-service-graceful" {
           description "Gateway becomes nonoperational by draining";
         }
       }
     }
     container h248-timers {
       presence "enable h248-timers";
       uses pgcp_h248_timers_object;
     }
     container h248-properties {
       presence "enable h248-properties";
       uses pgcp_h248_properties_object;
     }
     container h248-options {
       presence "enable h248-options";
       uses pgcp_h248_options_object;
     }
     leaf max-concurrent-calls {
       description "Maximum number of concurrent calls";
       default "0";
       type union {
         type string {
           pattern "<.*>|$.*";
         }
         type uint32 {
           range "0 .. 20000";
         }
       }
     }
     list gateway-controller {
       key name;
       ordered-by user;
       max-elements 32;
       uses pgcp_controller_object;
     }
     container monitor {
       description "Monitor voice traffic";
       uses apply-advanced;
       container media {
         presence "enable media";
         description "Monitor media traffic";
         uses apply-advanced;
         leaf rtp {
           description "Monitor RTP traffic";
           type empty;
         }
         leaf rtcp {
           description "Monitor RTCP traffic";
           type empty;
         }
       }
     }
     container graceful-restart {
       presence "enable graceful-restart";
       uses apply-advanced;
       leaf maximum-synchronization-time {
         description "Maximum time for synchronization procedure with the PIC";
         status deprecated;
         default "720";
         units "seconds";
         type union {
           type string {
             pattern "<.*>|$.*";
           }
           type uint16 {
             range "0 .. 720";
           }
         }
       }
       leaf maximum-synchronization-mismatches {
         description "Maximum number of mismatches for synchronization procedure with the PIC";
         default "250";
         type union {
           type string {
             pattern "<.*>|$.*";
           }
           type uint32 {
             range "0 .. 20000";
           }
         }
       }
       leaf no-synchronization {
         description "Disable the synchronization procedure with the PIC";
         type empty;
       }
       leaf catchup-replication-delay {
         description "Delay between replication of new updates and catch-up";
         default "300";
         type union {
           type string {
             pattern "<.*>|$.*";
           }
           type uint16 {
             range "0 .. 600";
           }
         }
       }
     }
     container fast-update-filters {
       presence "enable fast-update-filters";
       uses apply-advanced;
       leaf maximum-terms {
         description "Maximum gate rate-limit terms to install at PFE";
         default "2000";
         type union {
           type string {
             pattern "<.*>|$.*";
           }
           type uint64 {
             range "0 .. 20000";
           }
         }
       }
       leaf maximum-term-percentage {
         description "Maximum percentage of gates with rate-limit terms at PFE";
         default "10";
         type union {
           type string {
             pattern "<.*>|$.*";
           }
           type uint8 {
             range "0 .. 100";
           }
         }
       }
     }
     container session-mirroring {
       presence "enable session-mirroring";
       uses pgcp_gateway_session_mirroring_object;
     }
     container data-inactivity-detection {
       uses apply-advanced;
       leaf inactivity-delay {
         description "Delay before data inactivity detection starts";
         default "0";
         units "seconds";
         type union {
           type string {
             pattern "<.*>|$.*";
           }
           type uint16 {
             range "0 .. 3600";
           }
         }
       }
       leaf latch-deadlock-delay {
         description "Delay value used for gates employing NAPT traversal";
         default "0";
         units "seconds";
         type union {
           type string {
             pattern "<.*>|$.*";
           }
           type uint16 {
             range "0 .. 3600";
           }
         }
       }
       leaf send-notification-on-delay {
         description "Send inactivity notification when delay expires";
         type empty;
       }
       leaf inactivity-duration {
         description "Default data inactivity duration (Q-MI)";
         default "15";
         units "seconds";
         type union {
           type string {
             pattern "<.*>|$.*";
           }
           type uint32 {
             range "5 .. 86400";
           }
         }
       }
       leaf stop-detection-on-drop {
         description "Stop detection when gate action is set to drop";
         type empty;
       }
       leaf no-rtcp-check {
         description "Do not detect data inactivity on rtcp stream";
         type empty;
       }
       container report-service-change {
         description "Configure the data-inactivity service-change behavior";
         uses apply-advanced;
         leaf service-change-type {
           description "Configure the service-change type to be sent upon data-inactivity";
           type enumeration {
             enum "forced-910" {
               description "Send FO/910 service change";
             }
             enum "forced-906" {
               description "Send FO/906 service change";
             }
           }
         }
       }
     }
     container overload-control {
       presence "enable overload-control";
       uses apply-advanced;
       leaf queue-limit-percentage {
         description "Overload control queue limit percentage";
         default "70";
         type union {
           type string {
             pattern "<.*>|$.*";
           }
           type uint8 {
             range "0 .. 100";
           }
         }
       }
       leaf reject-new-calls-threshold {
         description "Overload control reject new calls threshold";
         default "80";
         type union {
           type string {
             pattern "<.*>|$.*";
           }
           type uint8 {
             range "0 .. 100";
           }
         }
       }
       leaf reject-all-commands-threshold {
         description "Overload control reject all commands threshold";
         default "90";
         type union {
           type string {
             pattern "<.*>|$.*";
           }
           type uint8 {
             range "0 .. 100";
           }
         }
       }
       leaf queue-maximum-length {
         description "Overload control queue maximum length";
         default "100";
         type union {
           type string {
             pattern "<.*>|$.*";
           }
           type uint16 {
             range "10 .. 1000";
           }
         }
       }
       leaf error-code {
         description "Overload control error code";
         default "511";
         type union {
           type string {
             pattern "<.*>|$.*";
           }
           type uint16 {
             range "510 .. 511";
           }
         }
       }
     }
     container platform {
       presence "enable platform";
       description "Define the platform on which the gateway should be activated";
       uses apply-advanced;
       choice values {
         case case_1 {
           leaf routing-engine {
             description "The gateway should be activated on the RE";
             type empty;
           }
         }
         case case_2 {
           leaf device {
             description "The gateway should be activated on a services device";
             type union {
               type jt:interface-device;
               type string {
                 pattern "<.*>|$.*";
               }
             }
           }
         }
       }
     }
     leaf ipsec-transport-security-association {
       description "IPsec transport security association name";
       type string {
         length "1 .. 63";
       }
     }
   }
   grouping pgcp_controller_object {
     leaf name {
       description "PGCP Controller Name";
       type string {
         length "1 .. 63";
       }
     }
     uses apply-advanced;
     leaf controller-address {
       description "Gateway controller IP address";
       type jt:ipv4addr;
     }
     leaf controller-port {
       description "Gateway controller port";
       default "2944";
       type union {
         type uint16;
         type string {
           pattern "<.*>|$.*";
         }
       }
     }
     container interim-ah-scheme {
       presence "enable interim-ah-scheme";
       uses pgcp_interim_ah_scheme_object;
     }
     choice controller-type {
       case case_1 {
         leaf remote-controller {
           description "The gateway controller is remote";
           type empty;
         }
       }
       case case_2 {
         leaf local-controller {
           description "The gateway controller is local";
           type string {
             length "1 .. 63";
           }
         }
       }
     }
   }
   grouping pgcp_gateway_session_mirroring_object {
     description "Gateway session mirroring properties";
     uses apply-advanced;
     list delivery-function {
       key name;
       ordered-by user;
       description "Interface for delivering mirrored packets";
       max-elements 1;
       uses pgcp_delivery_function_list_object;
     }
     leaf disable-session-mirroring {
       description "Disable session mirroring for this gateway";
       type empty;
     }
   }
   grouping pgcp_delivery_function_list_object {
     description "Session-mirroring delivery functions";
     leaf name {
       type string {
         length "1 .. 63";
       }
     }
   }
   grouping pgcp_h248_options_object {
     uses apply-advanced;
     container service-change {
       presence "enable service-change";
       uses pgcp-h248-service-change-object;
     }
     leaf audit-observed-events-returns {
       description "Activation of history buffer for audit observed events";
       type empty;
     }
     container encoding {
       presence "enable encoding";
       uses apply-advanced;
       leaf no-octet-string-bit-mirroring {
         description "No octet string bit mirroring";
         type empty;
       }
       leaf no-dscp-bit-mirroring {
         description "No DSCP bit mirroring";
         status deprecated;
         type empty;
       }
       leaf use-lower-case {
         description "Encode H248 message in lower case";
         type empty;
       }
     }
     container h248-profile {
       uses apply-advanced;
       leaf profile-name {
         description "The H.248 profile declared by the BGF";
         type string {
           length "1 .. 64";
         }
       }
       leaf profile-version {
         description "The H.248 profile-version declared by the BGF";
         type union {
           type string {
             pattern "<.*>|$.*";
           }
           type uint32 {
             range "1 .. 99";
           }
         }
       }
     }
     leaf accept-emergency-calls-while-graceful {
       description "Accept emergency calls while BGF is in OOS gracefull state";
       type empty;
     }
     leaf implicit-tcp-latch {
       description "Latch implicitly upon TCP transport usage";
       type empty;
     }
     leaf implicit-tcp-source-filter {
       description "Implicitly filter TCP source addresses";
       type empty;
     }
   }
   grouping pgcp-h248-service-change-object {
     uses apply-advanced;
     container control-association-indications {
       description "Control association indications";
       presence "enable control-association-indications";
       uses control-association-indications-object;
     }
     container virtual-interface-indications {
       description "Virtual interface indications";
       presence "enable virtual-interface-indications";
       uses virtual-interface-indications-object;
     }
     container context-indications {
       description "Context indications";
       presence "enable context-indications";
       uses context-indications-object;
     }
     leaf use-wildcard-response {
       description "Request short response to service-change messages";
       type empty;
     }
   }
   grouping context-indications-object {
     description "Context indications";
     uses apply-advanced;
     leaf state-loss {
       description "Configure state loss service change";
       type enumeration {
         enum "forced-915" {
           description "State loss";
         }
         enum "forced-910" {
           description "State loss reason fo/910";
         }
         enum "none" {
           description "Suppress state loss 918 service change";
         }
       }
     }
   }
   grouping control-association-indications-object {
     description "Control association indications";
     uses apply-advanced;
     container up {
       presence "enable up";
       uses pgcp-association-up-object;
     }
     container down {
       presence "enable down";
       uses pgcp-association-down-object;
     }
     container disconnect {
       presence "enable disconnect";
       uses pgcp-association-disconnect-object;
     }
   }
   grouping pgcp-association-disconnect-object {
     description "Control association disconnect";
     uses apply-advanced;
     leaf reconnect {
       description "Configure reconnect service change";
       type enumeration {
         enum "disconnected-900" {
           description "Service restored";
         }
         enum "restart-902" {
           description "Warm boot";
         }
       }
     }
     leaf controller-failure {
       description "Configure controller failure service change";
       type enumeration {
         enum "restart-902" {
           description "Warm boot";
         }
         enum "failover-909" {
           description "Gateway controller impending failure";
         }
       }
     }
   }
   grouping pgcp-association-down-object {
     description "Control association down";
     uses apply-advanced;
     leaf administrative {
       description "Configure administrative service change";
       type enumeration {
         enum "forced-905" {
           description "Termination taken out of service";
         }
         enum "forced-908" {
           description "Gateway impending failure";
         }
         enum "none" {
           description "Suppress service change";
         }
       }
     }
     leaf failure {
       description "Configure failure service change";
       type enumeration {
         enum "forced-904" {
           description "Termination malfunctioning";
         }
         enum "forced-908" {
           description "Gateway impending failure";
         }
         enum "none" {
           description "Suppress service change";
         }
       }
     }
     leaf graceful {
       description "Configure graceful service change";
       type enumeration {
         enum "none" {
           description "Suppress graceful-905 service change";
         }
         enum "graceful-905" {
           description "Termination taken out of service";
         }
       }
     }
   }
   grouping pgcp-association-up-object {
     description "Control association up";
     uses apply-advanced;
     leaf failover-cold {
       description "Configure failover-cold service change";
       type enumeration {
         enum "restart-901" {
           description "Cold boot";
         }
         enum "failover-920" {
           description "Cold failover";
         }
       }
     }
     leaf failover-warm {
       description "Configure failover-warm service change";
       type enumeration {
         enum "restart-902" {
           description "Warm boot";
         }
         enum "failover-919" {
           description "Warm failover";
         }
       }
     }
     leaf cancel-graceful {
       description "Configure cancel-graceful service change";
       type enumeration {
         enum "none" {
           description "Suppress restart-918 service change";
         }
         enum "restart-918" {
           description "Cancel graceful";
         }
       }
     }
   }
   grouping pgcp_h248_properties_object {
     description "Gateway H248 properties";
     uses apply-advanced;
     container base-root {
       description "Setting H248 mg-mgc transaction time values";
       presence "enable base-root";
       uses pgcp_h248_base_root_object;
     }
     container segmentation {
       presence "enable segmentation";
       uses pgcp_h248_segmentation_object;
     }
     container diffserv {
       presence "enable diffserv";
       uses pgcp_h248_diffserv_object;
     }
     container hanging-termination-detection {
       description "Enabling Hanging termination detection";
       presence "enable hanging-termination-detection";
       uses pgcp-h248-hangterm-object;
     }
     container traffic-management {
       description "Setting of h248 traffic management default values";
       presence "enable traffic-management";
       uses pgcp_h248_traffic_management_object;
     }
     container notification-behavior {
       description "Setting of h248 Notify behavior values";
       presence "enable notification-behavior";
       uses pgcp-h248-notification-behavior-object;
     }
     container application-data-inactivity-detection {
       description "Setting application data inactivity detection";
       presence "enable application-data-inactivity-detection";
       uses pgcp-h248-application-data-inactivity-detection-object;
     }
     container event-timestamp-notification {
       description "Setting event timestamp notification";
       presence "enable event-timestamp-notification";
       uses pgcp-h248-event-timestamp-notification-object;
     }
     container inactivity-timer {
       description "Default values for inactivity timeout";
       presence "enable inactivity-timer";
       uses pgcp-h248-inactivity-timer-object;
     }
   }
   grouping pgcp-h248-application-data-inactivity-detection-object {
     description "Application data inactivity detection";
     uses apply-advanced;
     leaf ip-flow-stop-detection {
       description "Setting ip flow stop detection";
       type enumeration {
         enum "immediate-notify" {
           description "Report all notifications";
         }
         enum "regulated-notify" {
           description "Suppress notification according to notification-count";
         }
       }
     }
   }
   grouping pgcp-h248-event-timestamp-notification-object {
     description "Event timestamp notification";
     uses apply-advanced;
     leaf request-timestamp {
       description "Notification timestamp";
       type enumeration {
         enum "requested" {
           description "Send event timestamp";
         }
         enum "suppressed" {
           description "Dont send event timestamp";
         }
         enum "autonomous" {
           description "Show timestamp at notify request";
         }
       }
     }
   }
   grouping pgcp-h248-hangterm-object {
     description "Hanging termination detection timer";
     uses apply-advanced;
     leaf timerx {
       description "Setting timerx value";
       default "0";
       units "seconds";
       type union {
         type string {
           pattern "<.*>|$.*";
         }
         type uint32 {
           range "0 .. 2147480";
         }
       }
     }
   }
   grouping pgcp-h248-inactivity-timer-object {
     description "A timer to verify PGC connectivity";
     uses apply-advanced;
     container inactivity-timeout {
       presence "enable inactivity-timeout";
       uses apply-advanced;
       leaf detect {
         description "Enable/Disable inactivity timer detection";
         type empty;
       }
       container maximum-inactivity-time {
         uses apply-advanced;
         leaf default {
           description "Default maximum inactivity timeout";
           default "12000";
           units "10-milliseconds";
           type union {
             type string {
               pattern "<.*>|$.*";
             }
             type uint16 {
               range "100 .. 65535";
             }
           }
         }
         leaf minimum {
           description "Minimum range for maximum inactivity timeout";
           default "100";
           units "10-milliseconds";
           type union {
             type string {
               pattern "<.*>|$.*";
             }
             type uint16 {
               range "100 .. 65535";
             }
           }
         }
         leaf maximum {
           description "Maximum range for maximum inactivity timeout";
           default "65535";
           units "10-milliseconds";
           type union {
             type string {
               pattern "<.*>|$.*";
             }
             type uint16 {
               range "100 .. 65535";
             }
           }
         }
       }
     }
   }
   grouping pgcp-h248-notification-behavior-object {
     description "Notify behavior parameters";
     uses apply-advanced;
     container notification-regulation {
       presence "enable notification-regulation";
       uses apply-advanced;
       leaf default {
         description "Default suppression percentage of Notification behavior Regulation ";
         type string {
         }
       }
     }
   }
   grouping pgcp_h248_base_root_object {
     uses apply-advanced;
     container normal-mg-execution-time {
       presence "enable normal-mg-execution-time";
       description "MG transaction response time expected by MGC.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mg-provisional-response-timer-value {
       presence "enable mg-provisional-response-timer-value";
       description "MG pending response time upon incomplete transaction.";
       uses apply-advanced;
       leaf default {
         default "2000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timer value";
         default "30000";
         units "milliseconds";
         type union {
           type string {
             pattern "<.*>|$.*";
           }
           type uint16 {
             range "500 .. 30000";
           }
         }
       }
     }
     container mg-originated-pending-limit {
       presence "enable mg-originated-pending-limit";
       description "Max MG TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
     container normal-mgc-execution-time {
       presence "enable normal-mgc-execution-time";
       description "MGC transaction response time expected by MG.";
       uses apply-advanced;
       leaf default {
         default "500";
         units "milliseconds";
         type union {
           type string {
             pattern "<.*>|$.*";
           }
           type uint16 {
             range "500 .. 29000";
           }
         }
       }
       leaf minimum {
         description "Minimum range of execution time value";
         default "500";
         units "milliseconds";
         type union {
           type string {
             pattern "<.*>|$.*";
           }
           type uint16 {
             range "500 .. 29000";
           }
         }
       }
       leaf maximum {
         description "Maximum range of execution time value";
         default "29000";
         units "milliseconds";
         type union {
           type string {
             pattern "<.*>|$.*";
           }
           type uint16 {
             range "500 .. 29000";
           }
         }
       }
     }
     container mgc-provisional-response-timer-value {
       presence "enable mgc-provisional-response-timer-value";
       description "MGC pending response time upon incomplete transaction.";
       uses apply-advanced;
       leaf default {
         default "4000";
         units "milliseconds";
         type union {
           type string {
             pattern "<.*>|$.*";
           }
           type uint16 {
             range "500 .. 30000";
           }
         }
       }
       leaf minimum {
         description "Minimum range of timers value";
         default "500";
         units "milliseconds";
         type union {
           type string {
             pattern "<.*>|$.*";
           }
           type uint16 {
             range "500 .. 30000";
           }
         }
       }
       leaf maximum {
         description "Maximum range of timers value";
         default "30000";
         units "milliseconds";
         type union {
           type string {
             pattern "<.*>|$.*";
           }
           type uint16 {
             range "500 .. 30000";
           }
         }
       }
     }
     container mgc-originated-pending-limit {
       presence "enable mgc-originated-pending-limit";
       description "Max MGC TransactionPendings num recieved.";
       uses apply-advanced;
       leaf default {
         default "4";
         type union {
           type string {
             pattern "<.*>|$.*";
           }
           type uint16 {
             range "1 .. 512";
           }
         }
       }
       leaf minimum {
         description "Minimum range of pending limit value";
         default "1";
         type union {
           type string {
             pattern "<.*>|$.*";
           }
           type uint16 {
             range "1 .. 512";
           }
         }
       }
       leaf maximum {
         description "Maximum range of pending limit value";
         default "512";
         type union {
           type string {
             pattern "<.*>|$.*";
           }
           type uint16 {
             range "1 .. 512";
           }
         }
       }
     }
   }
   grouping pgcp_h248_diffserv_object {
     uses apply-advanced;
     container dscp {
       presence "enable dscp";
       description "Differentiated Services Code Point (DSCP)";
       uses apply-advanced;
       leaf default {
         default "be";
         type string;
       }
       leaf ignore-signaled-value {
         description "Ignore property value appearing in H.248 signaling";
         type empty;
       }
     }
   }
   grouping pgcp_h248_segmentation_object {
     uses apply-advanced;
     container mgc-segmentation-timer {
       presence "enable mgc-segmentation-timer";
       description "Time the MG waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mgc-maximum-pdu-size {
       presence "enable mgc-maximum-pdu-size";
       description "Maximum size of the MGC's incoming messages from MG";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
     container mg-segmentation-timer {
       presence "enable mg-segmentation-timer";
       description "Time the MGC waits for remaining segments from MGC";
       uses apply-advanced;
       leaf default {
         default "4000";
         units "milliseconds";
         type union {
           type string {
             pattern "<.*>|$.*";
           }
           type int32 {
             range "500 .. 30000";
           }
         }
       }
       leaf minimum {
         description "Minimum range of timer value";
         default "500";
         units "milliseconds";
         type union {
           type string {
             pattern "<.*>|$.*";
           }
           type int32 {
             range "500 .. 30000";
           }
         }
       }
       leaf maximum {
         description "Maximum range of timer value";
         default "30000";
         units "milliseconds";
         type union {
           type string {
             pattern "<.*>|$.*";
           }
           type int32 {
             range "500 .. 30000";
           }
         }
       }
     }
     container mg-maximum-pdu-size {
       presence "enable mg-maximum-pdu-size";
       description "Maximum size of the MG's incoming messages from MGC";
       uses apply-advanced;
       leaf default {
         default "1472";
         units "bytes";
         type union {
           type string {
             pattern "<.*>|$.*";
           }
           type int32 {
             range "512 .. 65507";
           }
         }
       }
       leaf minimum {
         description "Minimum range of pdu size value";
         default "512";
         units "bytes";
         type union {
           type string {
             pattern "<.*>|$.*";
           }
           type int32 {
             range "512 .. 65507";
           }
         }
       }
       leaf maximum {
         description "Maximum range of pdu size value";
         default "65507";
         units "bytes";
         type union {
           type string {
             pattern "<.*>|$.*";
           }
           type int32 {
             range "512 .. 65507";
           }
         }
       }
     }
   }
   grouping pgcp_h248_timers_object {
     uses apply-advanced;
     leaf maximum-waiting-delay {
       description "Randomly determined delay before retraversing PGC list (MWD)";
       default "2000";
       units "milliseconds";
       type union {
         type string {
           pattern "<.*>|$.*";
         }
         type uint32 {
           range "100 .. 300000";
         }
       }
     }
     leaf tmax-retransmission-delay {
       description "Delay before PGC is considered down (T-MAX)";
       default "25000";
       units "milliseconds";
       type union {
         type string {
           pattern "<.*>|$.*";
         }
         type uint16 {
           range "1000 .. 60000";
         }
       }
     }
     leaf initial-average-ack-delay {
       description "Assumed initial average reply time (for retransmission rate) (I-AAD)";
       default "1000";
       units "milliseconds";
       type union {
         type string {
           pattern "<.*>|$.*";
         }
         type uint16 {
           range "500 .. 4000";
         }
       }
     }
     leaf maximum-net-propagation-delay {
       description "Worst case network propagation delay (M-NPD), used for calculating LONG-TIMER";
       default "5000";
       units "milliseconds";
       type union {
         type string {
           pattern "<.*>|$.*";
         }
         type uint16 {
           range "500 .. 10000";
         }
       }
     }
   }
   grouping pgcp_h248_traffic_management_object {
     uses apply-advanced;
     container sustained-data-rate {
       presence "enable sustained-data-rate";
       description "SDR permitted for the stream";
       uses apply-advanced;
       leaf default {
         description "Default rate value";
         default "10000";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         presence "enable rtcp";
         uses pgcp_h248_rtcp_rate_units_object;
       }
       leaf rtcp-include {
         description "TMAN SDR includes RTCP bandwidth";
         type empty;
       }
     }
     container peak-data-rate {
       presence "enable peak-data-rate";
       description "PDR permitted for the stream";
       uses apply-advanced;
       leaf default {
         description "Default rate value";
         default "0";
         units "bytes-per-second";
         type union {
           type string {
             pattern "<.*>|$.*";
           }
           type uint32 {
             range "0 .. 2147483647";
           }
         }
       }
       leaf minimum {
         description "Minimum range of rate value";
         default "0";
         units "bytes-per-second";
         type union {
           type string {
             pattern "<.*>|$.*";
           }
           type uint32 {
             range "0 .. 2147483647";
           }
         }
       }
       leaf maximum {
         description "Maximum range of rate value";
         default "0x7FFFFFFF";
         units "bytes-per-second";
         type union {
           type string {
             pattern "<.*>|$.*";
           }
           type uint32 {
             range "0 .. 2147483647";
           }
         }
       }
       container rtcp {
         description "Default rtcp rate";
         presence "enable rtcp";
         uses pgcp_h248_rtcp_rate_units_object;
       }
     }
     container max-burst-size {
       presence "enable max-burst-size";
       description "MBS for the stream";
       uses apply-advanced;
       leaf default {
         description "Default rate value";
         default "1000";
         units "bytes-per-second";
         type union {
           type string {
             pattern "<.*>|$.*";
           }
           type uint32 {
             range "20 .. 2147483647";
           }
         }
       }
       leaf minimum {
         description "Minimum range of rate value";
         default "20";
         units "bytes-per-second";
         type union {
           type string {
             pattern "<.*>|$.*";
           }
           type uint32 {
             range "20 .. 2147483647";
           }
         }
       }
       leaf maximum {
         description "Maximum range of rate value";
         default "0x7FFFFFFF";
         units "bytes-per-second";
         type union {
           type string {
             pattern "<.*>|$.*";
           }
           type uint32 {
             range "20 .. 2147483647";
           }
         }
       }
       container rtcp {
         description "Default rtcp rate";
         presence "enable rtcp";
         uses pgcp_h248_rtcp_burst_units_object;
       }
     }
   }
   grouping pgcp_h248_rtcp_burst_units_object {
     description "RTCP burst parameter settings";
     uses apply-advanced;
     choice values {
       case case_1 {
         leaf percentage {
           description "Value entered is percentage of RTP's parallel value";
           default "100";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "20 .. 2147483647";
             }
           }
         }
       }
     }
   }
   grouping pgcp_h248_rtcp_rate_units_object {
     description "RTCP rate parameter settings";
     uses apply-advanced;
     choice values {
       case case_1 {
         leaf percentage {
           description "Value entered is percentage of RTP's parallel value";
           default "5";
           units "percent";
           type union {
             type string {
               pattern "<.*>|$.*";
             }
             type uint32 {
               range "0 .. 1000";
             }
           }
         }
       }
       case case_2 {
         leaf fixed-value {
           description "Value entered is a fixed one";
           units "bytes-per-second";
           type union {
             type string {
               pattern "<.*>|$.*";
             }
             type uint32 {
               range "0 .. 2147483647";
             }
           }
         }
       }
     }
   }
   grouping pgcp_interim_ah_scheme_object {
     uses apply-advanced;
     leaf algorithm {
       description "Define authentication algorithm";
       type enumeration {
         enum "hmac-null" {
           description "NULL authentication algorithm";
         }
       }
     }
   }
   grouping pgcp_media_service_object {
     description "One or more PGCP media service";
     leaf name {
       description "Media Service name";
       type string {
         length "1 .. 63";
       }
     }
     uses apply-advanced;
     leaf nat-pool {
       description "Pool name";
       type string {
         length "1 .. 63";
       }
     }
   }
   grouping pgcp_rule_object {
     description "One or more PGCP rules";
     leaf name {
       description "Rule name";
       type string {
         length "1 .. 63";
       }
     }
     uses apply-advanced;
     leaf gateway {
       description "Gateway Name";
       type string {
         length "1 .. 63";
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
   }
   grouping pgcp_media_service_list_object {
     description "One or more PGCP media service";
     leaf name {
       type string {
         length "1 .. 63";
       }
     }
   }
   grouping pgcp_session_mirroring_object {
     description "PGCP session mirroring properties";
     uses apply-advanced;
     list delivery-function {
       key name;
       ordered-by user;
       description "Interface for delivering mirrored packets";
       max-elements 32;
       uses pgcp_delivery_function_object;
     }
     leaf disable-session-mirroring {
       description "Disable PGCP session mirroring";
       type empty;
     }
   }
   grouping pgcp_delivery_function_object {
     leaf name {
       description "Delivery function name";
       type string {
         length "1 .. 63";
       }
     }
     uses apply-advanced;
     leaf destination-address {
       description "Delivery function destination IP address";
       type jt:ipv4addr;
     }
     leaf destination-port {
       description "Delivery function destination port";
       type union {
         type uint16;
         type string {
           pattern "<.*>|$.*";
         }
       }
     }
     leaf network-operator-id {
       description "Network operator ID";
       type string {
         length 5;
       }
     }
     leaf source-address {
       description "Network-element-id";
       type jt:ipv4addr;
     }
     leaf source-port {
       description "Network-element-port";
       type union {
         type uint16;
         type string {
           pattern "<.*>|$.*";
         }
       }
     }
     container memory-managment {
       description "Measure memory usage";
       presence "enable memory-managment";
       uses pgcp_debug_mem_mgmt_object;
     }
   }
   grouping pgcp_debug_mem_mgmt_object {
     uses apply-advanced;
     leaf operational-mode {
       description "Memory managment operation mode";
       type enumeration {
         enum "fast" {
           description "Fast memory allocation [does not affect performance]";
         }
         enum "type-tracking" {
           description "Track all allocation types [affects performance]";
         }
         enum "location-tracking" {
           description "Track all allocation types and functions [affects performance]";
         }
       }
     }
   }
   grouping pgcp_virtual_interface_object {
     description "One or more Virtual Interfaces";
     leaf name {
       description "Virtual Interface Name";
       type string {
         length "1 .. 4";
       }
     }
     uses apply-advanced;
     leaf routing-instance {
       description "Routing instance of server to which to forward";
       default "inet.0";
       type string;
     }
     leaf service-state {
       description "Service state";
       default "in-service";
       type enumeration {
         enum "in-service" {
           description "Virtual Interface is operational";
         }
         enum "out-of-service-forced" {
           description "Virtual Interface is nonoperational";
         }
         enum "out-of-service-graceful" {
           description "Virtual Interface becomes nonoperational by draining";
         }
       }
     }
     choice media-svc-nat-pool {
       case case_1 {
         list media-service {
           key name;
           ordered-by user;
           status deprecated;
           uses pgcp_media_service_list_object;
         }
       }
       case case_2 {
         list nat-pool {
           key name;
           ordered-by user;
           description "Define a NAT pool";
           uses nat_pool_list_object;
         }
       }
     }
     leaf interface {
       description "Interface name";
       status deprecated;
       type union {
         type jt:interface-name;
         type string {
           pattern "<.*>|$.*";
         }
       }
     }
   }
   grouping plmn_type {
     leaf name {
       description "Name of PLMN";
       type string {
         length "1 .. 20";
       }
     }
     uses apply-advanced;
     list plmn-id {
       key name;
       ordered-by user;
       description "PLMN ID associated with this PLMN";
       uses plmn_id_type;
     }
   }
   grouping plmn_id_type {
     leaf name {
       description "SGSN Public Land Mobile Network identifier";
       type string {
         length "5 .. 6";
       }
     }
     uses apply-advanced;
     leaf home-plmn {
       description "This is home PLMN";
       type empty;
     }
     list sgsn-address {
       key name;
       description "SGSN address associated with this PLMN ID";
       uses sgsn_address_type;
     }
   }
   grouping policing_apn_type {
     uses apply-advanced;
     leaf maximum-bandwidth-uplink {
       description "Maximum bandwidth uplink";
       units "kilobits per second";
       type union {
         type string {
           pattern "<.*>|$.*";
         }
         type uint32 {
           range "64 .. 8640";
         }
       }
     }
     leaf maximum-bandwidth-downlink {
       description "Maximum bandwidth";
       units "kilobits per second";
       type union {
         type string {
           pattern "<.*>|$.*";
         }
         type uint32 {
           range "64 .. 16000";
         }
       }
     }
     leaf no-policing {
       description "Turn policing off";
       type empty;
     }
   }
   grouping policing_type {
     uses apply-advanced;
     leaf burst-time {
       description "Burst time window";
       default "3000";
       units "milliseconds";
       type union {
         type string {
           pattern "<.*>|$.*";
         }
         type uint32 {
           range "500 .. 5000";
         }
       }
     }
     leaf minimum-burst-value {
       description "Minimum burst value";
       default "16000";
       units "bytes";
       type union {
         type string {
           pattern "<.*>|$.*";
         }
         type uint32 {
           range "0 .. 64000";
         }
       }
     }
     leaf maximum-burst-value {
       description "Maximum burst value";
       default "2000";
       units "kilobytes";
       type union {
         type string {
           pattern "<.*>|$.*";
         }
         type uint32 {
           range "128 .. 2000";
         }
       }
     }
     leaf maximum-bandwidth-uplink {
       description "Maximum bandwidth uplink";
       default "2048";
       units "kilobits per second";
       type union {
         type string {
           pattern "<.*>|$.*";
         }
         type uint32 {
           range "64 .. 8640";
         }
       }
     }
     leaf maximum-bandwidth-downlink {
       description "Maximum bandwidth";
       default "2048";
       units "kilobits per second";
       type union {
         type string {
           pattern "<.*>|$.*";
         }
         type uint32 {
           range "64 .. 16000";
         }
       }
     }
     leaf no-policing {
       description "Turn policing off";
       type empty;
     }
   }
   grouping qosmap_type {
     uses apply-advanced;
     leaf-list conversational-1 {
       ordered-by user;
       description "DSCP name for conversational class 1 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list conversational-2 {
       ordered-by user;
       description "DSCP name for conversational class 2 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list streaming-1 {
       ordered-by user;
       description "DSCP name for streaming class 1 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list streaming-2 {
       ordered-by user;
       description "DSCP name for streaming class 2 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list interactive-1 {
       ordered-by user;
       description "DSCP name for interactive class 1 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list interactive-2 {
       ordered-by user;
       description "DSCP name for interactive class 2 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list interactive-3 {
       ordered-by user;
       description "DSCP name for interactive class 3 traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
     leaf-list background {
       ordered-by user;
       description "DSCP name for background traffic";
       type enumeration {
         enum "af11" {
           description "Assured forwarding class 1, low drop precedence";
         }
         enum "af12" {
           description "Assured forwarding class 1, medium drop precedence";
         }
         enum "af13" {
           description "Assured forwarding class 1, high drop precedence";
         }
         enum "af21" {
           description "Assured forwarding class 2, low drop precedence";
         }
         enum "af22" {
           description "Assured forwarding class 2, medium drop precedence";
         }
         enum "af23" {
           description "Assured forwarding class 2, high drop precedence";
         }
         enum "af31" {
           description "Assured forwarding class 3, low drop precedence";
         }
         enum "af32" {
           description "Assured forwarding class 3, medium drop precedence";
         }
         enum "af33" {
           description "Assured forwarding class 3, high drop precedence";
         }
         enum "af41" {
           description "Assured forwarding class 4, low drop precedence";
         }
         enum "af42" {
           description "Assured forwarding class 4, medium drop precedence";
         }
         enum "af43" {
           description "Assured forwarding class 4, high drop precedence";
         }
         enum "ef" {
           description "Expedited forwarding";
         }
         enum "be" {
           description "Best effort forwarding";
         }
       }
     }
   }
   grouping radius_shared_type {
     leaf name {
       description "Name of server";
       type string {
         length "1 .. 64";
       }
     }
     uses apply-advanced;
     leaf-list address {
       ordered-by user;
       description "RADIUS server addresses";
       type jt:ipv4addr;
     }
     leaf routing-instance {
       description "Routing instance for server";
       type string {
       }
     }
     choice address-range-choice {
       case case_1 {
         leaf address-range {
           description "Address range used in routing instance";
           status deprecated;
           type jt:ipv4prefix;
         }
       }
       case case_2 {
         leaf gi-address-range {
           description "Address range used in routing instance";
           type jt:ipv4prefix;
         }
       }
     }
     leaf timeout {
       description "Request timeout period";
       default "3";
       units "seconds";
       type union {
         type string {
           pattern "<.*>|$.*";
         }
         type uint32 {
           range "1 .. 90";
         }
       }
     }
     leaf retry {
       description "Retry attempts";
       default "3";
       type union {
         type string {
           pattern "<.*>|$.*";
         }
         type uint32 {
           range "1 .. 10";
         }
       }
     }
     leaf port {
       description "Port number for RADIUS messages";
       type union {
         type uint16;
         type string {
           pattern "<.*>|$.*";
         }
       }
     }
     leaf secret {
       description "Shared secret with the RADIUS server";
       type jt:unreadable;
     }
     leaf serverdown-timeout {
       description "Time before retrying requests to a down server";
       default "60";
       units "seconds";
       type union {
         type string {
           pattern "<.*>|$.*";
         }
         type uint32 {
           range "0 .. 1800";
         }
       }
     }
     leaf multicast-servers {
       description "Number of enabled RADIUS multicast servers";
       default "0";
       type union {
         type string {
           pattern "<.*>|$.*";
         }
         type uint32 {
           range "0 .. 9";
         }
       }
     }
     leaf no-accounting-on {
       description "Don't send accounting on and off messages";
       type empty;
     }
   }
   grouping radius_type {
     leaf name {
       description "RADIUS server address";
       type jt:ipv4addr;
     }
     uses apply-advanced;
     leaf timeout {
       description "Request timeout period";
       default "3";
       units "seconds";
       type union {
         type string {
           pattern "<.*>|$.*";
         }
         type uint32 {
           range "1 .. 90";
         }
       }
     }
     leaf retry {
       description "Retry attempts";
       default "3";
       type union {
         type string {
           pattern "<.*>|$.*";
         }
         type uint32 {
           range "1 .. 10";
         }
       }
     }
     leaf port {
       description "Port number for RADIUS messages";
       type union {
         type uint16;
         type string {
           pattern "<.*>|$.*";
         }
       }
     }
     leaf secret {
       description "Shared secret with the RADIUS server";
       type jt:unreadable;
     }
     leaf serverdown-timeout {
       description "Time before retrying requests to a down server";
       default "60";
       units "seconds";
       type union {
         type string {
           pattern "<.*>|$.*";
         }
         type uint32 {
           range "0 .. 1800";
         }
       }
     }
     leaf multicast {
       description "Allow server to participate in RADIUS multicast";
       type empty;
     }
   }
   grouping registration_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         presence "enable from";
         uses new_transaction_from_type;
       }
       container then {
         description "Action";
         presence "enable then";
         uses new_registration_then_type;
       }
     }
   }
   grouping new_registration_then_type {
     uses apply-advanced;
     container nat-traversal {
       description "How to traverse NAT devices";
       uses nat_traversal_action;
     }
   }
   grouping nat_traversal_action {
     uses apply-advanced;
     leaf nat-traversal-strategy {
       description "Choose when to perform NAT traversal";
       type enumeration {
         enum "never" {
           description "Never perform NAT traversal";
         }
         enum "always" {
           description "Always perform NAT traversal";
         }
         enum "by-via" {
           description "Perform NAT traversal only if transport source address does not match VIA header";
         }
       }
     }
     leaf keepalive-interval {
       description "Keepalive interval";
       default "45";
       units "seconds";
       type union {
         type string {
           pattern "<.*>|$.*";
         }
         type uint32 {
           range "15 .. 86400";
         }
       }
     }
     leaf minimum-registration-interval {
       description "Minimum registration interval allowed in register packet";
       default "1";
       units "seconds";
       type union {
         type string {
           pattern "<.*>|$.*";
         }
         type uint32 {
           range "1 .. 86400";
         }
       }
     }
     container keepalive-mechanisms {
       description "A prioritized list of keepalive mechanisms";
       uses apply-advanced;
       leaf register-fast-expiration {
         description "Reduce the expiration interval in REGISTER responses";
         type empty;
       }
     }
   }
   grouping new_transaction_from_type {
     uses apply-advanced;
     leaf-list source-address {
       ordered-by user;
       description "Source addresses and masks";
       type jt:ipaddr;
       max-elements 5;
     }
     list method {
       key name;
       ordered-by user;
       description "Methods";
       uses transaction-method-type;
     }
     container request-uri {
       description "Request URI field";
       leaf-list regular-expression {
         ordered-by user;
         description "Regular expression matched on incoming Request-URI";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
     container contact {
       description "Contact field";
       leaf-list regular-expression {
         ordered-by user;
         description "Regular expression matched on incoming contact";
         type jt:regular-expression;
         max-elements 5;
       }
       leaf registration-state {
         description "Registration state";
         type enumeration {
           enum "registered" {
           }
           enum "not-registered" {
           }
         }
       }
       leaf uri-hiding {
         description "URI hidden";
         type enumeration {
           enum "hidden-uri" {
           }
           enum "not-hidden-uri" {
           }
         }
       }
     }
   }
   grouping rmps-clnt-traceoptions-type {
     description "Trace options for Resource Management and Packet Steering Client";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Client to trace";
       leaf name {
         type enumeration {
           enum "infra" {
             description "Trace FSM and Infra code";
           }
           enum "memory" {
             description "Trace Memory Management Code";
           }
           enum "communication" {
             description "Trace IPC code";
           }
           enum "resource-tables" {
             description "Trace Resource Table Code";
           }
           enum "info-tables" {
             description "Trace Information Table Code";
           }
           enum "redundancy" {
             description "Trace GRES Code";
           }
           enum "all" {
             description "Trace All Resource Client Code";
           }
         }
       }
     }
   }
   grouping rmpsd-traceoptions-type {
     description "Trace options for Resource Management and Packet Steering Daemon";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Resource Management Packet Steering Area to trace";
       leaf name {
         type enumeration {
           enum "config" {
             description "Trace configuration code";
           }
           enum "gres" {
             description "Trace GRES code";
           }
           enum "init" {
             description "Trace initialization code";
           }
           enum "memory" {
             description "Trace memory management code";
           }
           enum "communication" {
             description "Trace Infra code";
           }
           enum "license-management" {
             description "Trace license management code";
           }
           enum "signal" {
             description "Trace signal handling code";
           }
           enum "state" {
             description "Trace state handling code";
           }
           enum "timer" {
             description "Trace timer code";
           }
           enum "ui" {
             description "Trace user interface code";
           }
           enum "resource-manager" {
             description "Trace Resource Management Code";
           }
           enum "info-manager" {
             description "Trace Information Management Code";
           }
           enum "packet-steering" {
             description "Trace packet-steering code";
           }
           enum "all" {
             description "Trace all areas of code";
           }
         }
       }
     }
   }
   grouping roaming_type {
     uses apply-advanced;
     list roaming-class {
       key name;
       description "Roaming class";
       uses roaming_class_type;
     }
     container default {
       presence "enable default";
       description "Default roaming class";
       uses apply-advanced;
       list rat-type {
         key name;
         description "Radio Access Type";
         uses roaming_default_type;
       }
       leaf roaming-class {
         description "Roaming class for any radio access type";
         type union {
           type string {
             pattern "<.*>|$.*";
           }
           type uint32 {
             range "1 .. 24";
           }
         }
       }
     }
   }
   grouping roaming_class_type {
     leaf name {
       description "Roaming class identifier";
       type union {
         type string {
           pattern "<.*>|$.*";
         }
         type uint32 {
           range "1 .. 24";
         }
       }
     }
     uses apply-advanced;
     list plmn {
       key name;
       ordered-by user;
       description "Public Land Mobile Network name";
       leaf name {
         description "Public Land Mobile Network name";
         type string {
           length "1 .. 20";
         }
       }
       uses apply-advanced;
       list plmn-id {
         key name;
         ordered-by user;
         description "Public Land Mobile Network identifier";
         uses roaming_plmn_id_type;
       }
     }
   }
   grouping roaming_default_type {
     leaf name {
       description "Radio access type (RAT) identifier";
       type enumeration {
         enum "unknown" {
           description "Unknown or missing";
         }
         enum "utran" {
           description "WCDMA/UMTS Terrestrial radio access network";
         }
         enum "geran" {
           description "GSM/EDGE radio access network";
         }
         enum "wlan" {
           description "Wireless local area network";
         }
       }
     }
     uses apply-advanced;
     leaf roaming-class {
       description "Roaming class";
       type union {
         type string {
           pattern "<.*>|$.*";
         }
         type uint32 {
           range "1 .. 24";
         }
       }
     }
   }
   grouping roaming_plmn_id_type {
     leaf name {
       description "SGSN Public Land Mobile Network identifier";
       type string {
         length "5 .. 6";
       }
     }
     uses apply-advanced;
     leaf-list rat-types {
       description "Radio access type (RAT) global defaults";
       type enumeration {
         enum "unknown" {
           description "Unknown or missing";
         }
         enum "utran" {
           description "WCDMA/UMTS Terrestrial radio access network";
         }
         enum "geran" {
           description "GSM/EDGE radio access network";
         }
         enum "wlan" {
           description "Wireless local area network";
         }
       }
     }
   }
   grouping routing-destinations {
     uses apply-advanced;
     leaf default-availability-check-profile {
       description "Profile that will be used if no other profile was attached to a server";
       type string {
         length "1 .. 256";
       }
     }
     list availability-check-profiles {
       key name;
       ordered-by user;
       description "Definitions of servers availability check profiles";
       max-elements 100;
       uses availability-check-profile;
     }
     list servers {
       key name;
       ordered-by user;
       description "Servers definitions";
       max-elements 5000;
       uses routing-destination-server;
     }
     list clusters {
       key name;
       ordered-by user;
       description "Clusters definitions";
       max-elements 1000;
       uses routing-destination-cluster;
     }
   }
   grouping availability-check-profile {
     leaf name {
       type string {
         length "1 .. 256";
       }
     }
     uses apply-advanced;
     container keepalive-method {
       description "How will availability check be done";
       choice ping-method {
         case case_1 {
           leaf sip-options {
             description "Check availability by sending a SIP OPTIONS message";
             type empty;
           }
         }
       }
     }
     container keepalive-strategy {
       presence "enable keepalive-strategy";
       description "When will the server be checked for availability";
       choice keepalive-strategy {
         case case_1 {
           container send-always {
             presence "enable send-always";
             description "Always check the server availability";
             uses apply-advanced;
             leaf failures-before-unavailable {
               description "A server is assumed to be unavailable when a keepalive message was not answered this number of times";
               default "1";
               type union {
                 type string {
                   pattern "<.*>|$.*";
                 }
                 type uint32 {
                   range "1 .. 10";
                 }
               }
             }
             leaf successes-before-available {
               description "A server is assumed to be available when a keepalive message was successfully answered this number of times";
               default "1";
               type union {
                 type string {
                   pattern "<.*>|$.*";
                 }
                 type uint32 {
                   range "1 .. 10";
                 }
               }
             }
           }
         }
         case case_2 {
           container send-when-unavailable {
             presence "enable send-when-unavailable";
             description "Check the server availability only when it is marked as unavailable";
             leaf successes-before-available {
               description "A server is assumed to be available when a keepalive message was successfully answered this number of times";
               default "1";
               type union {
                 type string {
                   pattern "<.*>|$.*";
                 }
                 type uint32 {
                   range "1 .. 10";
                 }
               }
             }
           }
         }
         case case_3 {
           container do-not-send {
             presence "enable do-not-send";
             description "Never perform availability checks of the server";
             leaf blackout-period {
               description "Time a server will be considered unavailable";
               default "600";
               units "seconds";
               type union {
                 type string {
                   pattern "<.*>|$.*";
                 }
                 type uint32 {
                   range "0 .. 86400";
                 }
               }
             }
           }
         }
       }
     }
     container keepalive-interval {
       description "How often should the server be checked for availability";
       uses apply-advanced;
       leaf available-server {
         description "How often should a server that is marked as available be checked for availablility";
         default "32";
         units "seconds";
         type union {
           type string {
             pattern "<.*>|$.*";
           }
           type uint32 {
             range "10 .. 86400";
           }
         }
       }
       leaf unavailable-server {
         description "How often should a server that is marked as unavailable be checked for availablility";
         default "32";
         units "seconds";
         type union {
           type string {
             pattern "<.*>|$.*";
           }
           type uint32 {
             range "10 .. 86400";
           }
         }
       }
     }
     leaf transaction-timeout {
       description "A server is assumed to be unavailable when a keepalive message was not answered in this time";
       default "32";
       units "seconds";
       type union {
         type string {
           pattern "<.*>|$.*";
         }
         type uint32 {
           range "10 .. 32";
         }
       }
     }
   }
   grouping routing-destination-cluster {
     leaf name {
       type string {
         length "1 .. 256";
       }
     }
     uses apply-advanced;
     list server {
       key name;
       ordered-by user;
       max-elements 25;
       leaf name {
         description "Server name";
         type string {
           length "1 .. 256";
         }
       }
       uses apply-advanced;
       leaf priority {
         description "Defines the redundency order";
         default "1";
         type union {
           type uint16;
           type string {
             pattern "<.*>|$.*";
           }
         }
       }
       leaf weight {
         description "Defines the load balancing ratio";
         default "1";
         type union {
           type uint16;
           type string {
             pattern "<.*>|$.*";
           }
         }
       }
     }
   }
   grouping routing-destination-server {
     leaf name {
       type string {
         length "1 .. 256";
       }
     }
     uses apply-advanced;
     container address {
       description "Server's address";
       presence "enable address";
       uses routing-destination-address;
     }
     leaf service-point {
       description "Exit point";
       type string;
     }
     leaf admission-control {
       description "Admission control profile for the server";
       type string;
     }
     leaf availability-check-profile {
       description "Availability check profile for the server";
       type string {
         length "1 .. 256";
       }
     }
   }
   grouping routing-destination-address {
     leaf ip4-address {
       description "IP address";
       type jt:ipaddr;
     }
     leaf port {
       description "Port number";
       default "5060";
       type union {
         type string {
           pattern "<.*>|$.*";
         }
         type uint32 {
           range "0 .. 65535";
         }
       }
     }
     container transport-protocol {
       description "Transport protocol";
       uses transport_protocol;
     }
   }
   grouping rule_space_type {
     leaf name {
       description "Rule space name";
       type string {
         length "1 .. 63";
       }
     }
     uses apply-advanced;
     leaf service-set {
       description "The service-set correlating to the rule-space";
       type string {
       }
     }
     container buffer-pending-authorization {
       presence "enable buffer-pending-authorization";
       description "Settings for buffering packets pending authorization";
       uses apply-advanced;
       leaf-list service-identifiers {
         ordered-by user;
         description "List of service identifiers for which payload will be buffered while waiting for authorization";
         type string {
           length "1 .. 21";
         }
         max-elements 1000;
       }
       leaf buffer-limit {
         description "Maximum number of packets to buffer";
         default "5";
         type union {
           type string {
             pattern "<.*>|$.*";
           }
           type uint32 {
             range "0 .. 100";
           }
         }
       }
     }
     leaf-list drop-pending-authorization {
       ordered-by user;
       description "List of service identifiers for which payload will dropped while waiting for authorization";
       type string {
         length "1 .. 21";
       }
       max-elements 1000;
     }
     container pass-through-pending-authorization {
       presence "enable pass-through-pending-authorization";
       description "Settings for passing through packets pending authorization";
       uses apply-advanced;
       leaf-list service-identifiers {
         ordered-by user;
         description "List of service identifiers for which limited payload will pass while waiting for credit";
         type string {
           length "1 .. 21";
         }
         max-elements 1000;
       }
       leaf pass-through-limit {
         description "Maximum number of packets to pass through";
         default "5";
         type union {
           type string {
             pattern "<.*>|$.*";
           }
           type uint32 {
             range "1 .. 254";
           }
         }
       }
     }
     list redirect-map {
       key name;
       ordered-by user;
       description "Mapping service identifiers to redirect sets";
       leaf name {
         description "A redirect set";
         type string {
           length "1 .. 63";
         }
       }
       leaf-list service-id {
         ordered-by user;
         description "Service identifier to redirect for the given redirect set";
         type string {
           length "1 .. 21";
         }
         max-elements 1000;
       }
     }
     container time-based-charging {
       description "Rating group related configuration";
       uses apply-advanced;
       container measurement {
         presence "enable measurement";
         description "Default active time settings";
         uses apply-advanced;
         leaf resolution {
           description "Time measurement resolution for active usage";
           default "1";
           units "seconds";
           type union {
             type string {
               pattern "<.*>|$.*";
             }
             type uint32 {
               range "1 .. 86400";
             }
           }
         }
         leaf inactivity {
           description "Time measurement inactivity for active usage";
           default "60";
           units "seconds";
           type union {
             type string {
               pattern "<.*>|$.*";
             }
             type uint32 {
               range "1 .. 86400";
             }
           }
         }
         leaf reporting {
           description "Reporting method for time-based-charging";
           default "no-reporting";
           type enumeration {
             enum "no-reporting" {
               description "Do not report active usage";
             }
             enum "timestamp" {
               description "Report start and stop timestamps for each period of active usage";
             }
             enum "timestamp-and-volume" {
               description "Reports timestamps and used volume for each period of active usage";
             }
           }
         }
         leaf method {
           description "Method to use for measurement of active usage";
           default "duration";
           type enumeration {
             enum "inactivity" {
               description "Use inactivity period but do not included it in usage";
             }
             enum "inactivity-included" {
               description "Use inactivity period and include it in usage";
             }
             enum "duration" {
               description "Measure the duration of the session";
             }
             enum "active-periods" {
               description "Each resolution period with traffic is counted as active usage";
             }
           }
         }
       }
       list rating-group-cluster {
         key name;
         ordered-by user;
         description "Common time base definitions for clusters of rating groups";
         max-elements 256;
         uses rating_group_cluster_type;
       }
     }
     container quota-handling {
       presence "enable quota-handling";
       description "Quota handling preferences";
       uses apply-advanced;
       choice holding-time-choice {
         case case_1 {
           leaf holding-time-period {
             description "Period of inactivity after which to report the quota";
             default "180";
             units "seconds";
             type union {
               type string {
                 pattern "<.*>|$.*";
               }
               type uint32 {
                 range "5 .. 86400";
               }
             }
           }
         }
         case case_2 {
           leaf holding-time-infinity {
             description "Infinite holding time";
             type empty;
           }
         }
       }
       leaf-list no-quota-handling {
         ordered-by user;
         description "Rating group for which quota shall not be requested";
         type string {
           length "1 .. 21";
         }
         max-elements 4095;
       }
       leaf user-denied-time {
         description "Time to wait before requesting new quota after a request has been denied";
         default "180";
         units "seconds";
         type union {
           type string {
             pattern "<.*>|$.*";
           }
           type uint32 {
             range "5 .. 86400";
           }
         }
       }
       container re-authorization-triggers {
         presence "enable re-authorization-triggers";
         description "Default triggers for quota re-authorization";
         uses apply-advanced;
         leaf sgsn-address {
           description "Trigger re-authorization if sgsn address has changed for the PDP context";
           type empty;
         }
         leaf sgsn-plmn-id {
           description "Trigger re-authorization if PLMN id has changed for the PDP context";
           type empty;
         }
         leaf rat-type {
           description "Trigger re-authorization if RAT has changed for the PDP context";
           type empty;
         }
         leaf qos {
           description "Trigger re-authorization if QoS has changed for the PDP context";
           type empty;
         }
       }
     }
     container rating-group {
       presence "enable rating-group";
       description "Classification of service-identifiers to Rating Groups, and explicit barring of services";
       uses apply-advanced;
       container default {
         presence "enable default";
         description "Default rating group";
         uses apply-advanced;
         choice default-classification {
           case case_1 {
             leaf default-rating-group {
               description "Use this rating group if not found in map table";
               type union {
                 type string {
                   pattern "<.*>|$.*";
                 }
                 type uint32 {
                   range "1 .. 4294967295";
                 }
               }
             }
           }
           case case_2 {
             leaf use-service-id {
               description "Use the service-id as a rating-group";
               type empty;
             }
           }
         }
       }
       list map {
         key name;
         description "Map of service ids to rating groups";
         max-elements 4095;
         uses sid_to_rg_map_type;
       }
       leaf-list not-allowed {
         ordered-by user;
         description "Access to rating group not allowed";
         type string {
           length "1 .. 21";
         }
         max-elements 4095;
       }
     }
     leaf enable-access-control-rules {
       description "Access control rules enabled using service-id as access-control-rule id";
       type empty;
     }
     leaf-list always-allowed-service-identifiers {
       ordered-by user;
       description "Always allowed service identifiers";
       type string {
         length "1 .. 21";
       }
       max-elements 64;
     }
     list access-control-group {
       key name;
       ordered-by user;
       description "Access control group settings";
       max-elements 64;
       uses access_control_group_type;
     }
     leaf initial-redirect {
       description "Redirect services at first access";
       type empty;
     }
     container local-policy-control {
       presence "enable local-policy-control";
       description "Local policy control settings";
       uses apply-advanced;
       choice local_policy_control_authorization {
         case case_1 {
           list activation-time {
             key name;
             description "Activation time for authorization settings";
             max-elements 24;
             leaf name {
               description "Activation time (hh:mm)";
               type string {
               }
             }
             uses apply-advanced;
             list roaming-class {
               key name;
               ordered-by user;
               description "Authorization settings for roaming class";
               leaf name {
                 description "Roaming class identifier";
                 type union {
                   type string {
                     pattern "<.*>|$.*";
                   }
                   type uint32 {
                     range "1 .. 24";
                   }
                 }
               }
               uses apply-advanced;
               list quality-of-service {
                 key name;
                 ordered-by user;
                 description "Authorization settings for quality of service";
                 leaf name {
                   description "Authorized traffic class";
                   type enumeration {
                     enum "conversational" {
                       description "Conversational quality of service";
                     }
                     enum "streaming" {
                       description "Streaming quality of service";
                     }
                     enum "interactive-1" {
                       description "Interactive priority 1 quality of service";
                     }
                     enum "interactive-2" {
                       description "Interactive priority 2 quality of service";
                     }
                     enum "interactive-3" {
                       description "Interactive priority 3 quality of service";
                     }
                     enum "background" {
                       description "Background quality of service";
                     }
                   }
                 }
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
               container default-quality-of-service {
                 presence "enable default-quality-of-service";
                 description "Default authorization settings for quality of service";
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
             }
             container default-roaming-class {
               description "Default authorization settings to use on no match";
               uses apply-advanced;
               list quality-of-service {
                 key name;
                 ordered-by user;
                 description "Authorization settings for quality of service";
                 leaf name {
                   description "Authorized traffic class";
                   type enumeration {
                     enum "conversational" {
                       description "Conversational quality of service";
                     }
                     enum "streaming" {
                       description "Streaming quality of service";
                     }
                     enum "interactive-1" {
                       description "Interactive priority 1 quality of service";
                     }
                     enum "interactive-2" {
                       description "Interactive priority 2 quality of service";
                     }
                     enum "interactive-3" {
                       description "Interactive priority 3 quality of service";
                     }
                     enum "background" {
                       description "Background quality of service";
                     }
                   }
                 }
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
               container default-quality-of-service {
                 presence "enable default-quality-of-service";
                 description "Default authorization settings for quality of service";
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
             }
           }
         }
         case case_2 {
           container all-time {
             presence "enable all-time";
             description "Time-independent authorization settings";
             uses apply-advanced;
             list roaming-class {
               key name;
               ordered-by user;
               description "Authorization settings for roaming class ";
               leaf name {
                 description "Roaming class identifier";
                 type union {
                   type string {
                     pattern "<.*>|$.*";
                   }
                   type uint32 {
                     range "1 .. 24";
                   }
                 }
               }
               uses apply-advanced;
               list quality-of-service {
                 key name;
                 ordered-by user;
                 description "Authorization settings for quality of service";
                 leaf name {
                   description "Authorized traffic class";
                   type enumeration {
                     enum "conversational" {
                       description "Conversational quality of service";
                     }
                     enum "streaming" {
                       description "Streaming quality of service";
                     }
                     enum "interactive-1" {
                       description "Interactive priority 1 quality of service";
                     }
                     enum "interactive-2" {
                       description "Interactive priority 2 quality of service";
                     }
                     enum "interactive-3" {
                       description "Interactive priority 3 quality of service";
                     }
                     enum "background" {
                       description "Background quality of service";
                     }
                   }
                 }
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
               container default-quality-of-service {
                 presence "enable default-quality-of-service";
                 description "Default authorization settings for quality of service";
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
             }
             container default-roaming-class {
               presence "enable default-roaming-class";
               description "Default authorization settings for roaming class ";
               uses apply-advanced;
               list quality-of-service {
                 key name;
                 ordered-by user;
                 description "Authorization settings for quality of service";
                 leaf name {
                   description "Authorized traffic class";
                   type enumeration {
                     enum "conversational" {
                       description "Conversational quality of service";
                     }
                     enum "streaming" {
                       description "Streaming quality of service";
                     }
                     enum "interactive-1" {
                       description "Interactive priority 1 quality of service";
                     }
                     enum "interactive-2" {
                       description "Interactive priority 2 quality of service";
                     }
                     enum "interactive-3" {
                       description "Interactive priority 3 quality of service";
                     }
                     enum "background" {
                       description "Background quality of service";
                     }
                   }
                 }
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
               container default-quality-of-service {
                 presence "enable default-quality-of-service";
                 description "Default authorization settings for quality of service";
                 uses apply-advanced;
                 list access-control-rule {
                   key name;
                   ordered-by user;
                   description "Authorization settings for access control rule identifier";
                   leaf name {
                     description "Access control rule identifier";
                     type union {
                       type string {
                         pattern "<.*>|$.*";
                       }
                       type uint32 {
                         range "0 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
                 list access-control-group {
                   key name;
                   ordered-by user;
                   description "Authorization settings for access control group";
                   leaf name {
                     description "Access control group identifier";
                     type union {
                       type string {
                         pattern "<.*>|$.*";
                       }
                       type uint32 {
                         range "1 .. 4294967295";
                       }
                     }
                   }
                   uses apply-advanced;
                   leaf authorization-code {
                     description "Authorization code";
                     type enumeration {
                       enum "authorized" {
                         description "Authorized";
                       }
                       enum "denied-roaming" {
                         description "Deny access because of roaming class";
                       }
                       enum "denied-calendar-time" {
                         description "Deny access because of time of day";
                       }
                       enum "denied-quality-of-service" {
                         description "Deny access because of quality of service";
                       }
                       enum "denied-user-defined-reason-1" {
                         description "Deny access due to proprietery operator definition (1)";
                       }
                       enum "denied-user-defined-reason-2" {
                         description "Deny access due to proprietery operator definition (2)";
                       }
                       enum "denied-user-defined-reason-3" {
                         description "Deny access due to proprietery operator definition (3)";
                       }
                       enum "denied-user-defined-reason-4" {
                         description "Deny access due to proprietery operator definition (4)";
                       }
                       enum "denied-user-defined-reason-5" {
                         description "Deny access due to proprietery operator definition (5)";
                       }
                       enum "denied-blacklisted" {
                         description "Deny access because rating group is blacklisted";
                       }
                       enum "denied-unknown" {
                         description "Deny access for unknown reason";
                       }
                       enum "denied-terminal" {
                         description "Deny access due to terminal limitations";
                       }
                     }
                   }
                 }
               }
             }
           }
         }
       }
     }
     container bandwidth-control {
       presence "enable bandwidth-control";
       description "Bandwidth control settings";
       uses apply-advanced;
       list throughput-limitation {
         key name;
         ordered-by user;
         description "Throughput limitation per context and service-id";
         max-elements 64;
         leaf name {
           description "Identifier of the throughput-limitation profile";
           type string;
         }
         uses apply-advanced;
         leaf uplink-limitation {
           description "Uplink throughput limitation per context and service-id";
           units "kbps";
           type union {
             type string {
               pattern "<.*>|$.*";
             }
             type uint32 {
               range "1 .. 8640";
             }
           }
         }
         leaf downlink-limitation {
           description "Downlink throughput limitation per context and service-id";
           units "kbps";
           type union {
             type string {
               pattern "<.*>|$.*";
             }
             type uint32 {
               range "1 .. 16000";
             }
           }
         }
         leaf-list service-id {
           ordered-by user;
           description "Service-identifier for which to apply the throughput limitation";
           type string {
             length "1 .. 21";
           }
           max-elements 1000;
         }
       }
     }
     container redirect-with-acknowledgement {
       presence "enable redirect-with-acknowledgement";
       description "Settings for redirect with acknowledgement";
       uses apply-advanced;
       leaf acknowledgement-label {
         description "Acknowledgement label used to identify successfull redirect with user acknowledgement";
         type string {
           length "1 .. 10";
         }
       }
       container remove-acknowledgement {
         presence "enable remove-acknowledgement";
         description "Settings for removal of acknowledgement parameter from request URI";
         uses apply-advanced;
         choice remove_option_choice {
           case case_1 {
             leaf-list remove-for-service-identifiers {
               ordered-by user;
               description "Remove acknowledgement parameter for Service identifiers";
               type string {
                 length "1 .. 21";
               }
               max-elements 1000;
             }
           }
           case case_2 {
             leaf-list no-remove-for-service-identifiers {
               ordered-by user;
               description "Do not remove acknowledgement parameter for Service identifiers";
               type string {
                 length "1 .. 21";
               }
               max-elements 1000;
             }
           }
         }
       }
     }
   }
   grouping access_control_group_type {
     leaf name {
       description "Access control group identifier for access control group";
       type union {
         type string {
           pattern "<.*>|$.*";
         }
         type uint32 {
           range "1 .. 4294967295";
         }
       }
     }
     uses apply-advanced;
     leaf-list access-control-rule {
       ordered-by user;
       description "Access control rule included in the access control group";
       type string {
         length "1 .. 21";
       }
       max-elements 512;
     }
   }
   grouping rating_group_cluster_type {
     description "Rating groups with common time-based configuration";
     leaf name {
       description "Unique id for the rating-group cluster";
       type union {
         type string {
           pattern "<.*>|$.*";
         }
         type uint32 {
           range "1 .. 4095";
         }
       }
     }
     uses apply-advanced;
     container measurement {
       presence "enable measurement";
       description "Default active time settings";
       uses apply-advanced;
       leaf resolution {
         description "Time measurement resolution for active usage";
         default "1";
         units "seconds";
         type union {
           type string {
             pattern "<.*>|$.*";
           }
           type uint32 {
             range "1 .. 86400";
           }
         }
       }
       leaf inactivity {
         description "Time measurement inactivity for active usage";
         default "60";
         units "seconds";
         type union {
           type string {
             pattern "<.*>|$.*";
           }
           type uint32 {
             range "1 .. 86400";
           }
         }
       }
       leaf reporting {
         description "Reporting method for time-based-charging";
         default "no-reporting";
         type enumeration {
           enum "no-reporting" {
             description "Do not report active usage";
           }
           enum "timestamp" {
             description "Report start and stop timestamps for each period of active usage";
           }
           enum "timestamp-and-volume" {
             description "Reports timestamps and used volume for each period of active usage";
           }
         }
       }
       leaf method {
         description "Method to use for measurement of active usage";
         default "duration";
         type enumeration {
           enum "inactivity" {
             description "Use inactivity period but do not included it in usage";
           }
           enum "inactivity-included" {
             description "Use inactivity period and include it in usage";
           }
           enum "duration" {
             description "Measure the duration of the session";
           }
           enum "active-periods" {
             description "Each resolution period with traffic is counted as active usage";
           }
         }
       }
     }
     leaf-list rating-group {
       ordered-by user;
       description "Rating group belonging to this cluster";
       type string {
         length "1 .. 21";
       }
       max-elements 256;
     }
   }
   grouping saegw-names {
     description "SAE gateway name";
     leaf name {
       description "SAE gateway Name";
       type string {
         length "1 .. 64";
       }
     }
     uses apply-advanced;
     container system {
       description "System resource configuration";
       uses apply-advanced;
       container anchor-pfes {
         presence "enable anchor-pfes";
         uses anchor-pfes-type;
       }
       container class-of-service {
         description "System CoS configuration";
         uses apply-advanced;
         container reserved-bandwidth {
           description "CoS bandwidth reservation";
           uses apply-advanced;
           leaf express {
             description "Percentage of bandwidth reserved for express traffic";
             units "percent";
             type union {
               type string {
                 pattern "<.*>|$.*";
               }
               type uint16 {
                 range "1 .. 100";
               }
             }
           }
           leaf gbr {
             description "Percentage of bandwidth reserved for gbr traffic";
             units "percent";
             type union {
               type string {
                 pattern "<.*>|$.*";
               }
               type uint16 {
                 range "1 .. 100";
               }
             }
           }
         }
         container downlink-dscp-to-forwarding-class {
           description "Downlink DSCP to forwarding-class configuration";
           uses apply-advanced;
           list classifier {
             key name;
             ordered-by user;
             description "CoS BA classifier";
             max-elements 16;
             uses classifier-names;
           }
         }
         container downlink-dscp-to-egress-forwarding-class {
           description "Downlink DSCP to egress-forwarding-class configuration";
           uses apply-advanced;
           list classifier {
             key name;
             ordered-by user;
             description "CoS BA classifier";
             max-elements 16;
             uses classifier-names;
           }
         }
       }
       leaf service-mode {
         description "Service mode";
         type enumeration {
           enum "maintenance" {
             description "Maintenance mode";
           }
         }
       }
     }
     container control-plane-peers {
       description "Control plane peers";
       uses apply-advanced;
       leaf-list local-address {
         ordered-by user;
         description "IPv6 or IPv4 or both addresses of the local end of the PFCP connection";
         type jt:ipaddr;
         max-elements 1;
       }
       leaf routing-instance {
         description "Local routing instance of the PFCP";
         type string {
         }
       }
       leaf heartbeat-interval {
         description "Time between two successive heartbeat requests";
         units "seconds";
         type union {
           type string {
             pattern "<.*>|$.*";
           }
           type uint16 {
             range "60 .. 255";
           }
         }
       }
       leaf path-management {
         description "Enable/disable origination of heartbeat message requests to control peers";
         type enumeration {
           enum "enable" {
             description "Enable parameter";
           }
           enum "disable" {
             description "Disable parameter";
           }
         }
       }
       leaf n3-requests {
         description "Number of retries of PFCP request messages upon t3-response timeout";
         type union {
           type string {
             pattern "<.*>|$.*";
           }
           type uint16 {
             range "1 .. 255";
           }
         }
       }
       leaf t3-response {
         description "Waiting time of gateway before retrying a PFCP signaling-request upon response timeout";
         units "seconds";
         type union {
           type string {
             pattern "<.*>|$.*";
           }
           type uint16 {
             range "1 .. 255";
           }
         }
       }
       leaf response-cache-timeout {
         description "Configure the timeout for the PFCP response cache";
         units "seconds";
         type union {
           type string {
             pattern "<.*>|$.*";
           }
           type uint16 {
             range "0 .. 255";
           }
         }
       }
       container apn-services {
         description "Access point name services name";
         uses apply-advanced;
         list apns {
           key name;
           ordered-by user;
           max-elements 512;
           uses apn-services-names;
         }
       }
       list peer-groups {
         key name;
         ordered-by user;
         description "Peer groups name";
         max-elements 256;
         uses control-peer-groups;
       }
     }
     container access-network-peers {
       description "Data plane peers";
       uses apply-advanced;
       leaf-list local-address {
         ordered-by user;
         description "IPv4 address of the local end of the GTP-U connection";
         type jt:ipv4addr;
         max-elements 1;
       }
       leaf routing-instance {
         description "Local routing instance of the GTP-U";
         type string {
         }
       }
       leaf echo-interval {
         description "Time between origination of two successive echo requests";
         units "seconds";
         type union {
           type string {
             pattern "<.*>|$.*";
           }
           type uint16 {
             range "60 .. 255";
           }
         }
       }
       leaf path-management {
         description "Enable/disable origination of echo requests to access peers";
         type enumeration {
           enum "enable" {
             description "Enable parameter";
           }
           enum "disable" {
             description "Disable parameter";
           }
         }
       }
       leaf n3-requests {
         description "Number of retries of peer management request messages upon t3-response timeout";
         type union {
           type string {
             pattern "<.*>|$.*";
           }
           type uint16 {
             range "1 .. 5";
           }
         }
       }
       leaf t3-response {
         description "Waiting time of gateway before retrying peer management request upon response timeout";
         units "seconds";
         type union {
           type string {
             pattern "<.*>|$.*";
           }
           type uint16 {
             range "1 .. 5";
           }
         }
       }
       list peer-groups {
         key name;
         ordered-by user;
         description "Peer groups name";
         max-elements 4000;
         uses access-peer-groups;
       }
     }
     container core-network-peers {
       description "Core-side GTP-U peers";
       uses apply-advanced;
       leaf-list local-address {
         ordered-by user;
         description "IPv4 address of the local end of the GTP-U connection";
         type jt:ipv4addr;
         max-elements 1;
       }
       leaf routing-instance {
         description "Local routing instance of the GTP-U connection";
         type string {
         }
       }
       leaf echo-interval {
         description "Time between origination of two echo requests";
         units "seconds";
         type union {
           type string {
             pattern "<.*>|$.*";
           }
           type uint16 {
             range "60 .. 255";
           }
         }
       }
       leaf path-management {
         description "Enable/disable origination of echo requests to core peers";
         type enumeration {
           enum "enable" {
             description "Enable parameter";
           }
           enum "disable" {
             description "Disable parameter";
           }
         }
       }
       leaf n3-requests {
         description "Number of unanswered echo requests for path failure";
         type union {
           type string {
             pattern "<.*>|$.*";
           }
           type uint16 {
             range "1 .. 5";
           }
         }
       }
       leaf t3-response {
         description "Time between resending unanswered echo requests";
         units "seconds";
         type union {
           type string {
             pattern "<.*>|$.*";
           }
           type uint16 {
             range "1 .. 5";
           }
         }
       }
       list peer-groups {
         key name;
         ordered-by user;
         description "Peer groups name";
         max-elements 4000;
         uses core-peer-groups;
       }
     }
   }
   grouping access-peer-groups {
     description "Peer-group name";
     leaf name {
       description "Peer group name";
       type string {
         length "1 .. 64";
       }
     }
     uses apply-advanced;
     container peer {
       presence "enable peer";
       uses apply-advanced;
       leaf-list address {
         ordered-by user;
         description "IPv4 address or prefix value of access network peer";
         type jt:ipv4prefix;
       }
       leaf hostname {
         description "Name of the access network peer";
         type string {
           length "1 .. 256";
         }
       }
     }
     leaf routing-instance {
       description "Routing-instance of GPT-U connection";
       type string {
       }
     }
   }
   grouping anchor-pfes-type {
     description "Anchor PFE's configuration";
     uses apply-advanced;
     list interface {
       key name;
       ordered-by user;
       description "Anchor PFE interface configuration";
       leaf name {
         description "Interface name";
         type string {
           length "1 .. 60";
         }
       }
       uses apply-advanced;
     }
   }
   grouping apn-services-names {
     description "APN services configuration";
     leaf name {
       description "APN Services Name";
       type string {
       }
     }
     uses apply-advanced;
     leaf mobile-interface {
       description "Mobile interface name";
       type string {
         length "1 .. 60";
       }
     }
   }
   grouping classifier-names {
     description "CoS BA classifier";
     leaf name {
       description "Name of classifier to be applied";
       type string {
         length "1 .. 64";
       }
     }
     uses apply-advanced;
     list routing-instance {
       key name;
       ordered-by user;
       leaf name {
         description "Routing instance the classifier applies to";
         type string {
         }
       }
       uses apply-advanced;
     }
   }
   grouping control-peer-groups {
     description "Peer-group name";
     leaf name {
       description "Peer group name";
       type string {
         length "1 .. 64";
       }
     }
     uses apply-advanced;
     container peer {
       presence "enable peer";
       description "Peer address and hostname";
       uses apply-advanced;
       leaf-list address {
         ordered-by user;
         description "IPv4 or IPv6 address or prefix value of control plane peer";
         type jt:ipprefix;
       }
       leaf hostname {
         description "Name of the control plane peer";
         type string {
           length "1 .. 256";
         }
       }
     }
     leaf initiate-association {
       description "Start node association message to control plane peer";
       type empty;
     }
     leaf routing-instance {
       description "Local routing instance of the PFCP";
       type string {
       }
     }
     leaf heartbeat-interval {
       description "Time between origination of two successive heartbeat requests";
       units "seconds";
       type union {
         type string {
           pattern "<.*>|$.*";
         }
         type uint16 {
           range "60 .. 255";
         }
       }
     }
     leaf path-management {
       description "Enable/disable origination of heartbeat message requests to control peers";
       type enumeration {
         enum "enable" {
           description "Enable parameter";
         }
         enum "disable" {
           description "Disable parameter";
         }
       }
     }
     leaf n3-requests {
       description "Number of retries of PFCP request messages upon t3-response timeout";
       type union {
         type string {
           pattern "<.*>|$.*";
         }
         type uint16 {
           range "1 .. 255";
         }
       }
     }
     leaf t3-response {
       description "Waiting time of gateway before retrying a PFCP signaling-request upon response timeout";
       units "seconds";
       type union {
         type string {
           pattern "<.*>|$.*";
         }
         type uint16 {
           range "1 .. 255";
         }
       }
     }
   }
   grouping core-peer-groups {
     description "Peer-group name";
     leaf name {
       description "Peer group name";
       type string {
         length "1 .. 64";
       }
     }
     uses apply-advanced;
     container peer {
       presence "enable peer";
       uses apply-advanced;
       leaf-list address {
         ordered-by user;
         description "IPv4 address or prefix value of core network peer";
         type jt:ipv4prefix;
       }
       leaf hostname {
         description "Name of the core network peer";
         type string {
           length "1 .. 256";
         }
       }
     }
     leaf routing-instance {
       description "Routing-instance of GPT-U connection";
       type string {
       }
     }
   }
   grouping sbcc_apn_type {
     uses apply-advanced;
     leaf control-context {
       description "Environment definition for service aware charging and control";
       type enumeration {
         enum "single-bucket" {
           description "Charging and control according to Service Aware Charging and Control version 2";
         }
         enum "3gpp" {
           description "Charging and control according to 3gpp standard (supports Ro and Gx interfaces)";
         }
         enum "multi-bucket" {
           description "Charging and control according to CLCI and/or Gx dynamic-services-control";
         }
       }
     }
     container bandwidth-control {
       presence "enable bandwidth-control";
       description "Bandwidth control settings";
       uses apply-advanced;
       list throughput-limitation {
         key name;
         ordered-by user;
         description "Throughput limitation per context and service-id";
         max-elements 64;
         leaf name {
           description "Identifier of the throughput-limitation profile";
           type string;
         }
         uses apply-advanced;
         leaf uplink-limitation {
           description "Uplink throughput limitation per context and service-id";
           units "kbps";
           type union {
             type string {
               pattern "<.*>|$.*";
             }
             type uint32 {
               range "1 .. 8640";
             }
           }
         }
         leaf downlink-limitation {
           description "Downlink throughput limitation per context and service-id";
           units "kbps";
           type union {
             type string {
               pattern "<.*>|$.*";
             }
             type uint32 {
               range "1 .. 16000";
             }
           }
         }
         leaf-list service-id {
           ordered-by user;
           description "Service-identifier for which to apply the throughput limitation";
           type string {
             length "1 .. 21";
           }
           max-elements 1000;
         }
       }
     }
     container prepaid {
       presence "enable prepaid";
       description "Prepaid settings";
       status deprecated;
       uses apply-advanced;
       leaf provider-id {
         description "Provider identifier";
         type union {
           type uint16;
           type string {
             pattern "<.*>|$.*";
           }
         }
       }
       leaf-list subscription-id {
         ordered-by user;
         description "Subscription identifier";
         type enumeration {
           enum "msisdn" {
             description "Use MSISDN as subscription identifier";
           }
           enum "nai" {
             description "Use NAI as subscription identifier";
           }
           enum "imsi" {
             description "Use IMSI as subscription identifier";
           }
           enum "address" {
             description "Use mobile address as subscription identifier";
           }
         }
       }
       leaf apn-identifier {
         description "Include service provider APN name";
         type empty;
       }
       container credit {
         description "Credit settings";
         uses apply-advanced;
         container request {
           description "Proposed values for credit requests";
           uses apply-advanced;
           leaf units {
             description "Units for proposed values";
             type enumeration {
               enum "money" {
                 description "Units are monetary values";
               }
               enum "volume" {
                 description "Units are volume-based";
               }
             }
           }
           leaf currency {
             description "Currency for proposed values";
             status deprecated;
             default "999";
             type string {
             }
           }
           container quota {
             description "Proposed quota to request";
             uses apply-advanced;
             container best-effort {
               description "Quota settings for best effort traffic";
               uses apply-advanced;
               leaf base-quota {
                 description "Requested base quota";
                 type jt:unsigned-float;
               }
               leaf bandwidth-factor {
                 description "Bandwidth scaling factor";
                 default "100";
                 type union {
                   type string {
                     pattern "<.*>|$.*";
                   }
                   type int32 {
                     range "100 .. 200";
                   }
                 }
               }
             }
             container conversational {
               description "Quota settings for conversational traffic";
               uses apply-advanced;
               leaf base-quota {
                 description "Requested base quota";
                 type jt:unsigned-float;
               }
               leaf bandwidth-factor {
                 description "Bandwidth scaling factor";
                 default "100";
                 type union {
                   type string {
                     pattern "<.*>|$.*";
                   }
                   type int32 {
                     range "100 .. 200";
                   }
                 }
               }
             }
             container interactive {
               description "Quota settings for interactive traffic";
               uses apply-advanced;
               leaf base-quota {
                 description "Requested base quota";
                 type jt:unsigned-float;
               }
               leaf bandwidth-factor {
                 description "Bandwidth scaling factor";
                 default "100";
                 type union {
                   type string {
                     pattern "<.*>|$.*";
                   }
                   type int32 {
                     range "100 .. 200";
                   }
                 }
               }
             }
             container streaming {
               description "Quota settings for streaming traffic";
               uses apply-advanced;
               leaf base-quota {
                 description "Requested base quota";
                 type jt:unsigned-float;
               }
               leaf bandwidth-factor {
                 description "Bandwidth scaling factor";
                 default "100";
                 type union {
                   type string {
                     pattern "<.*>|$.*";
                   }
                   type int32 {
                     range "100 .. 200";
                   }
                 }
               }
             }
           }
         }
         leaf threshold {
           description "Low credit threshold";
           default "0";
           units "percent";
           type union {
             type string {
               pattern "<.*>|$.*";
             }
             type uint32 {
               range "0 .. 10";
             }
           }
         }
         leaf duration {
           description "Credit validity duration time";
           default "60";
           units "minutes";
           type union {
             type uint32;
             type string {
               pattern "<.*>|$.*";
             }
           }
         }
         container empty-quota-action {
           description "Action to take when user quota is empty";
           uses apply-advanced;
           choice empty_bucket_choice {
             case case_1 {
               leaf terminate-context {
                 description "Terminate the PDP context";
                 type empty;
               }
             }
             case case_2 {
               leaf free-services {
                 description "Allow context to access free services";
                 type empty;
               }
             }
             case case_3 {
               leaf-list allow-service-class {
                 ordered-by user;
                 description "Allow access to service class";
                 type union {
                   type string {
                     pattern "<.*>|$.*";
                   }
                   type uint16 {
                     range "1 .. 4096";
                   }
                 }
                 max-elements 64;
               }
             }
           }
         }
         leaf empty-quota-redirect {
           description "Redirect non-free services if user quota is empty";
           type empty;
         }
       }
       container failure {
         description "Failure settings";
         uses apply-advanced;
         choice failure_action_choice {
           case case_1 {
             leaf terminate-contexts {
               description "Terminate associated contexts";
               type empty;
             }
           }
           case case_2 {
             leaf free-services {
               description "Allow free services";
               type empty;
             }
           }
           case case_3 {
             leaf post-paid {
               description "Switch to post-paid handling of contexts";
               type empty;
             }
           }
         }
       }
       leaf allow-external-update {
         description "Allow externally initiated update of credit information";
         type empty;
       }
     }
     container packet-inspection {
       description "Packet inspection settings";
       uses apply-advanced;
       container no-inspection {
         description "Service classification without packet inspection";
         uses apply-advanced;
         leaf service-class-default {
           description "Service class applied to all traffic on this APN";
           type union {
             type string {
               pattern "<.*>|$.*";
             }
             type uint16 {
               range "1 .. 4096";
             }
           }
         }
       }
     }
     container block-based-charging {
       description "Block-based charging";
       uses apply-advanced;
       list profile {
         key name;
         description "Block-based charging profile";
         max-elements 16;
         leaf name {
           description "Profile identifier";
           type string {
             length "1 .. 64";
           }
         }
         uses apply-advanced;
         container default-roaming-class {
           description "Default roaming class";
           uses apply-advanced;
           container default-service-class-group {
             description "Default service class settings for block-based charging";
             uses apply-advanced;
             choice bbc-time-volume-choice {
               case case_1 {
                 container active-time {
                   presence "enable active-time";
                   description "Active time block settings";
                   uses apply-advanced;
                   leaf resolution {
                     description "Time measurement resolution for active usage";
                     units "seconds";
                     type union {
                       type string {
                         pattern "<.*>|$.*";
                       }
                       type uint32 {
                         range "1 .. 3600";
                       }
                     }
                   }
                   leaf inactivity {
                     description "Time measurement inactivity for active usage";
                     units "seconds";
                     type union {
                       type string {
                         pattern "<.*>|$.*";
                       }
                       type uint32 {
                         range "1 .. 3600";
                       }
                     }
                   }
                 }
               }
               case case_2 {
                 container volume {
                   presence "enable volume";
                   description "Volume block settings";
                   uses apply-advanced;
                   leaf uplink-resolution {
                     description "Volume measurement resolution for uplink payload";
                     units "bytes";
                     type string;
                   }
                   leaf downlink-resolution {
                     description "Volume measurement resolution for downlink payload";
                     units "bytes";
                     type string;
                   }
                   leaf total-resolution {
                     description "Volume measurement resolution for total payload";
                     units "bytes";
                     type string;
                   }
                 }
               }
             }
           }
           list service-class-group {
             key name;
             description "Service class settings for block-based charging";
             max-elements 32;
             leaf name {
               description "Service class group index";
               type union {
                 type string {
                   pattern "<.*>|$.*";
                 }
                 type uint32 {
                   range "1 .. 32";
                 }
               }
             }
             uses apply-advanced;
             leaf-list service-class {
               ordered-by user;
               description "Service classes and service class ranges";
               type string;
             }
             choice bbc-time-volume-choice {
               case case_1 {
                 container active-time {
                   presence "enable active-time";
                   description "Active time block settings";
                   uses apply-advanced;
                   leaf resolution {
                     description "Time measurement resolution for active usage";
                     units "seconds";
                     type union {
                       type string {
                         pattern "<.*>|$.*";
                       }
                       type uint32 {
                         range "1 .. 3600";
                       }
                     }
                   }
                   leaf inactivity {
                     description "Time measurement inactivity for active usage";
                     units "seconds";
                     type union {
                       type string {
                         pattern "<.*>|$.*";
                       }
                       type uint32 {
                         range "1 .. 3600";
                       }
                     }
                   }
                 }
               }
               case case_2 {
                 container volume {
                   presence "enable volume";
                   description "Volume block settings";
                   uses apply-advanced;
                   leaf uplink-resolution {
                     description "Volume measurement resolution for uplink payload";
                     units "bytes";
                     type string;
                   }
                   leaf downlink-resolution {
                     description "Volume measurement resolution for downlink payload";
                     units "bytes";
                     type string;
                   }
                   leaf total-resolution {
                     description "Volume measurement resolution for total payload";
                     units "bytes";
                     type string;
                   }
                 }
               }
             }
           }
           choice bbc-time-volume-choice {
             case case_1 {
               container duration-time {
                 presence "enable duration-time";
                 description "Duration time block settings";
                 uses apply-advanced;
                 leaf resolution {
                   description "Time measurement resolution for duration";
                   units "seconds";
                   type union {
                     type string {
                       pattern "<.*>|$.*";
                     }
                     type uint32 {
                       range "1 .. 3600";
                     }
                   }
                 }
               }
             }
             case case_2 {
               container volume {
                 presence "enable volume";
                 description "Volume block settings";
                 uses apply-advanced;
                 leaf uplink-resolution {
                   description "Volume measurement resolution for uplink payload";
                   units "bytes";
                   type string;
                 }
                 leaf downlink-resolution {
                   description "Volume measurement resolution for downlink payload";
                   units "bytes";
                   type string;
                 }
                 leaf total-resolution {
                   description "Volume measurement resolution for total payload";
                   units "bytes";
                   type string;
                 }
               }
             }
           }
         }
         list roaming-class {
           key name;
           description "Roaming class";
           max-elements 24;
           leaf name {
             description "Roaming class identifier";
             type union {
               type string {
                 pattern "<.*>|$.*";
               }
               type uint32 {
                 range "1 .. 24";
               }
             }
           }
           uses apply-advanced;
           container default-service-class-group {
             description "Default service class settings for block-based charging";
             uses apply-advanced;
             choice bbc-time-volume-choice {
               case case_1 {
                 container active-time {
                   presence "enable active-time";
                   description "Active time block settings";
                   uses apply-advanced;
                   leaf resolution {
                     description "Time measurement resolution for active usage";
                     units "seconds";
                     type union {
                       type string {
                         pattern "<.*>|$.*";
                       }
                       type uint32 {
                         range "1 .. 3600";
                       }
                     }
                   }
                   leaf inactivity {
                     description "Time measurement inactivity for active usage";
                     units "seconds";
                     type union {
                       type string {
                         pattern "<.*>|$.*";
                       }
                       type uint32 {
                         range "1 .. 3600";
                       }
                     }
                   }
                 }
               }
               case case_2 {
                 container volume {
                   presence "enable volume";
                   description "Volume block settings";
                   uses apply-advanced;
                   leaf uplink-resolution {
                     description "Volume measurement resolution for uplink payload";
                     units "bytes";
                     type string;
                   }
                   leaf downlink-resolution {
                     description "Volume measurement resolution for downlink payload";
                     units "bytes";
                     type string;
                   }
                   leaf total-resolution {
                     description "Volume measurement resolution for total payload";
                     units "bytes";
                     type string;
                   }
                 }
               }
             }
           }
           list service-class-group {
             key name;
             description "Service class settings for block-based charging";
             max-elements 32;
             leaf name {
               description "Service class group index";
               type union {
                 type string {
                   pattern "<.*>|$.*";
                 }
                 type uint32 {
                   range "1 .. 32";
                 }
               }
             }
             uses apply-advanced;
             leaf-list service-class {
               ordered-by user;
               description "Service classes and service class ranges";
               type string;
             }
             choice bbc-time-volume-choice {
               case case_1 {
                 container active-time {
                   presence "enable active-time";
                   description "Active time block settings";
                   uses apply-advanced;
                   leaf resolution {
                     description "Time measurement resolution for active usage";
                     units "seconds";
                     type union {
                       type string {
                         pattern "<.*>|$.*";
                       }
                       type uint32 {
                         range "1 .. 3600";
                       }
                     }
                   }
                   leaf inactivity {
                     description "Time measurement inactivity for active usage";
                     units "seconds";
                     type union {
                       type string {
                         pattern "<.*>|$.*";
                       }
                       type uint32 {
                         range "1 .. 3600";
                       }
                     }
                   }
                 }
               }
               case case_2 {
                 container volume {
                   presence "enable volume";
                   description "Volume block settings";
                   uses apply-advanced;
                   leaf uplink-resolution {
                     description "Volume measurement resolution for uplink payload";
                     units "bytes";
                     type string;
                   }
                   leaf downlink-resolution {
                     description "Volume measurement resolution for downlink payload";
                     units "bytes";
                     type string;
                   }
                   leaf total-resolution {
                     description "Volume measurement resolution for total payload";
                     units "bytes";
                     type string;
                   }
                 }
               }
             }
           }
           choice bbc-time-volume-choice {
             case case_1 {
               container duration-time {
                 presence "enable duration-time";
                 description "Duration time block settings";
                 uses apply-advanced;
                 leaf resolution {
                   description "Time measurement resolution for duration";
                   units "seconds";
                   type union {
                     type string {
                       pattern "<.*>|$.*";
                     }
                     type uint32 {
                       range "1 .. 3600";
                     }
                   }
                 }
               }
             }
             case case_2 {
               container volume {
                 presence "enable volume";
                 description "Volume block settings";
                 uses apply-advanced;
                 leaf uplink-resolution {
                   description "Volume measurement resolution for uplink payload";
                   units "bytes";
                   type string;
                 }
                 leaf downlink-resolution {
                   description "Volume measurement resolution for downlink payload";
                   units "bytes";
                   type string;
                 }
                 leaf total-resolution {
                   description "Volume measurement resolution for total payload";
                   units "bytes";
                   type string;
                 }
               }
             }
           }
         }
       }
     }
     container rating {
       presence "enable rating";
       description "Rating settings";
       status deprecated;
       uses apply-advanced;
       leaf-list subscription-id {
         ordered-by user;
         description "Subscription identifier";
         type enumeration {
           enum "msisdn" {
             description "Use MSISDN as subscription identifier";
           }
           enum "nai" {
             description "Use NAI as subscription identifier";
           }
           enum "imsi" {
             description "Use IMSI as subscription identifier";
           }
           enum "address" {
             description "Use mobile address as subscription identifier";
           }
         }
       }
       container quality-of-service {
         description "Quality-of-service settings";
         uses apply-advanced;
         leaf type {
           description "Quality of service type to include";
           default "3gpp";
           type enumeration {
             enum "diffserv" {
               description "Use DiffServ quality of service";
             }
             enum "3gpp" {
               description "Use 3GPP quality of service";
             }
           }
         }
       }
       container failure {
         description "Failure settings";
         uses apply-advanced;
         choice rating_failure_action_choice {
           case case_1 {
             leaf terminate-contexts {
               description "Terminate associated contexts";
               type empty;
             }
           }
           case case_2 {
             leaf default-service-class {
               description "Use the default service class";
               type empty;
             }
           }
         }
       }
       leaf allow-external-update {
         description "Allow externally initiated update of rating information";
         type empty;
       }
     }
     container policy-control {
       description "Policy control";
       uses apply-advanced;
       container dynamic {
         description "Dynamic policy control";
         uses apply-advanced;
         list profile {
           key name;
           description "Policy control dynamic profile";
           max-elements 32;
           leaf name {
             description "Profile identifier";
             type string {
               length "1 .. 64";
             }
           }
           uses apply-advanced;
           leaf diameter-application-system {
             description "Diameter application system";
             type string {
               length "1 .. 64";
             }
           }
           leaf quality-of-service {
             description "Quality of service settings";
             default "3gpp";
             type enumeration {
               enum "diffserv" {
                 description "Use DiffServ quality of service";
               }
               enum "3gpp" {
                 description "Use 3GPP quality of service";
               }
               enum "3gpp-extended" {
                 description "Use 3GPP extended quality of service";
               }
             }
           }
           leaf-list subscription-id {
             ordered-by user;
             description "Subscription identifier";
             type enumeration {
               enum "msisdn" {
                 description "Use MSISDN as subscription identifier";
               }
               enum "nai" {
                 description "Use NAI as subscription identifier";
               }
               enum "imsi" {
                 description "Use IMSI as subscription identifier";
               }
               enum "address" {
                 description "Use mobile address as subscription identifier";
               }
             }
           }
           leaf failure-action {
             description "Failure settings";
             default "terminate-contexts";
             type enumeration {
               enum "terminate-contexts" {
                 description "Terminate associated contexts";
               }
               enum "use-static" {
                 description "Use the static rating configuration";
               }
             }
           }
         }
         list gx-profile {
           key name;
           description "Settings for standard and enhanced Gx";
           max-elements 32;
           leaf name {
             description "Profile identifier";
             type string {
               length "1 .. 64";
             }
           }
           uses apply-advanced;
           leaf diameter-application-system {
             description "Diameter application system";
             type string {
               length "1 .. 64";
             }
           }
           leaf-list subscription-id {
             ordered-by user;
             description "Subscription identifier";
             type enumeration {
               enum "msisdn" {
                 description "Use MSISDN as subscription identifier";
               }
               enum "nai" {
                 description "Use NAI as subscription identifier";
               }
               enum "imsi" {
                 description "Use IMSI as subscription identifier";
               }
             }
           }
           leaf selection-key {
             description "Set input parameter for selection of PCRF";
             default "ip-address";
             type enumeration {
               enum "msisdn" {
                 description "Select PCRF based on modulo operation on msisdn";
               }
               enum "ip-address" {
                 description "Select PCRF based on modulo operation on ip-address";
               }
             }
           }
           list pcrf-selection {
             key name;
             ordered-by user;
             description "Settings for selection of PCRF and P-CSCF";
             leaf name {
               description "PCRF table entry";
               type union {
                 type string {
                   pattern "<.*>|$.*";
                 }
                 type uint32 {
                   range "0 .. 15";
                 }
               }
             }
             uses apply-advanced;
             leaf primary-pcrf {
               description "Diameter host identifier of primary PCRF";
               type string {
                 length "1 .. 64";
               }
             }
             leaf secondary-pcrf {
               description "Diameter host identifier of secondary PCRF";
               type string {
                 length "1 .. 64";
               }
             }
             leaf primary-pcscf {
               description "Primary P-CSCF IPv4 address";
               type jt:ipv4addr;
             }
             leaf secondary-pcscf {
               description "Secondary P-CSCF IPv4 address";
               type jt:ipv4addr;
             }
           }
           leaf failure-action {
             description "Failure settings";
             default "reject-request";
             type enumeration {
               enum "terminate-contexts" {
                 description "Terminate associated contexts";
               }
               enum "reject-request" {
                 description "Reject PDP context activate and update requests";
               }
               enum "use-local" {
                 description "Use the local policy configuration for the IP session until it terminates";
               }
               enum "use-local-reestablish" {
                 description "Use the local policy configuration and try to reestablish connection periodically ";
               }
             }
           }
           leaf disable-gx-extensions {
             description "Do not allow use of Gx+ extensions";
             type empty;
           }
           leaf access-rule-push {
             description "Allow for (P)CRF to push down access rules";
             status deprecated;
             type empty;
           }
           leaf qos-control {
             description "Enable support of QoS control  over Gx";
             type empty;
           }
           leaf bearer-mapping-control {
             description "Enable support of bearer-mapping and Gating control over Gx";
             status deprecated;
             type empty;
           }
           leaf deny-empty-context {
             description "Deny PDP context activation without authorized services";
             type empty;
           }
           leaf rule-space-negotiation {
             description "Enable rule-space-negotiation over Gx";
             type empty;
           }
           leaf immediate-credit-control {
             description "Immediate credit control for dynamic charging rules";
             type empty;
           }
           leaf disconnect-ip-sessions {
             description "Delete all active IP sessions using a CRF if contact is lost or server has restarted";
             type empty;
           }
         }
         list vf-gx-profile {
           key name;
           description "Settings for standard and enhanced Gx";
           status deprecated;
           max-elements 32;
           leaf name {
             description "Profile identifier";
             type string {
               length "1 .. 64";
             }
           }
           uses apply-advanced;
           leaf diameter-application-system {
             description "Diameter application system";
             type string {
               length "1 .. 64";
             }
           }
           leaf selection-key {
             description "Settings for E-PDF selection";
             default "msisdn";
             type enumeration {
               enum "msisdn" {
                 description "Use MSISDN as key";
               }
               enum "ip-address" {
                 description "Use IP address as key";
               }
             }
           }
           leaf alternative-pcscf {
             description "Enable provision an alternative P-CSCF address to the UE";
             type empty;
           }
           list epdf-selection-table {
             key name;
             ordered-by user;
             description "Settings for E-PDF selection";
             leaf name {
               description "E-PDF selection table identifier";
               type union {
                 type uint32;
                 type string {
                   pattern "<.*>|$.*";
                 }
               }
             }
             uses apply-advanced;
             leaf primary-epdf {
               description "Primary E-PDF host addresses";
               type string;
             }
             leaf secondary-epdf {
               description "Secondary E-PDF host addresses";
               type string;
             }
             container primary-pcscf {
               presence "enable primary-pcscf";
               description "Primary PCSCF addresses";
               uses apply-advanced;
               choice ip-address-choice {
                 case case_1 {
                   leaf ipv4 {
                     description "IPv4 address";
                     type jt:ipv4addr;
                   }
                 }
                 case case_2 {
                   leaf ipv6 {
                     description "IPv6 address";
                     type jt:ipv6addr;
                   }
                 }
               }
             }
             container secondary-pcscf {
               presence "enable secondary-pcscf";
               description "Secondary PCSCF addresses";
               uses apply-advanced;
               choice ip-address-choice {
                 case case_1 {
                   leaf ipv4 {
                     description "IPv4 address";
                     type jt:ipv4addr;
                   }
                 }
                 case case_2 {
                   leaf ipv6 {
                     description "IPv6 address";
                     type jt:ipv6addr;
                   }
                 }
               }
             }
           }
         }
         leaf allow-external-update {
           description "Allow externally initiated update of rating information";
           type empty;
         }
       }
       container static {
         description "Static policy control";
         uses apply-advanced;
         list profile {
           key name;
           description "Policy control static profile";
           max-elements 16;
           uses fbc_static_rating_profile_type;
         }
       }
     }
     container rating-control {
       description "Rating control";
       uses apply-advanced;
       list profile {
         key name;
         description "Rating control profile";
         max-elements 2;
         leaf name {
           description "Profile identifier";
           type string {
             length "1 .. 64";
           }
         }
         uses apply-advanced;
         choice postpaid-choice {
           leaf postpaid {
             description "Activate rating for post-paid subscribers";
             type empty;
           }
           leaf no-postpaid {
             description "Don't activate rating for post-paid subscribers";
             type empty;
           }
         }
       }
     }
     container credit-control {
       description "Credit control";
       uses apply-advanced;
       list profile {
         key name;
         description "Credit control profile";
         max-elements 32;
         leaf name {
           description "Profile identifier";
           type string {
             length "1 .. 64";
           }
         }
         uses apply-advanced;
         leaf diameter-application-system {
           description "Diameter application system";
           type string {
             length "1 .. 64";
           }
         }
         leaf request-duration {
           description "Credit validity duration time";
           default "60";
           units "minutes";
           type union {
             type string {
               pattern "<.*>|$.*";
             }
             type uint32 {
               range "30 .. 300";
             }
           }
         }
         container request-quota {
           description "Proposed quota to request";
           uses apply-advanced;
           container best-effort {
             description "Quota settings for best effort traffic";
             uses apply-advanced;
             leaf base-quota {
               description "Requested base quota";
               type jt:unsigned-float;
             }
             leaf bandwidth-factor {
               description "Bandwidth scaling factor";
               default "100";
               type union {
                 type string {
                   pattern "<.*>|$.*";
                 }
                 type int32 {
                   range "100 .. 200";
                 }
               }
             }
           }
           container conversational {
             description "Quota settings for conversational traffic";
             uses apply-advanced;
             leaf base-quota {
               description "Requested base quota";
               type jt:unsigned-float;
             }
             leaf bandwidth-factor {
               description "Bandwidth scaling factor";
               default "100";
               type union {
                 type string {
                   pattern "<.*>|$.*";
                 }
                 type int32 {
                   range "100 .. 200";
                 }
               }
             }
           }
           container interactive {
             description "Quota settings for interactive traffic";
             uses apply-advanced;
             leaf base-quota {
               description "Requested base quota";
               type jt:unsigned-float;
             }
             leaf bandwidth-factor {
               description "Bandwidth scaling factor";
               default "100";
               type union {
                 type string {
                   pattern "<.*>|$.*";
                 }
                 type int32 {
                   range "100 .. 200";
                 }
               }
             }
           }
           container streaming {
             description "Quota settings for streaming traffic";
             uses apply-advanced;
             leaf base-quota {
               description "Requested base quota";
               type jt:unsigned-float;
             }
             leaf bandwidth-factor {
               description "Bandwidth scaling factor";
               default "100";
               type union {
                 type string {
                   pattern "<.*>|$.*";
                 }
                 type int32 {
                   range "100 .. 200";
                 }
               }
             }
           }
         }
         leaf unit-type {
           description "Unit for proposed values";
           type enumeration {
             enum "money" {
               description "Units are monetary values";
             }
             enum "volume" {
               description "Units are volume-based";
             }
           }
         }
         leaf provider-id {
           description "Provider identifier";
           type union {
             type uint16;
             type string {
               pattern "<.*>|$.*";
             }
           }
         }
         leaf-list subscription-id {
           ordered-by user;
           description "Subscription identifier";
           type enumeration {
             enum "msisdn" {
               description "Use MSISDN as subscription identifier";
             }
             enum "nai" {
               description "Use NAI as subscription identifier";
             }
             enum "imsi" {
               description "Use IMSI as subscription identifier";
             }
             enum "address" {
               description "Use mobile address as subscription identifier";
             }
           }
         }
         leaf apn-identifier {
           description "Include service provider APN name";
           type empty;
         }
         leaf failure-action {
           description "Failure action settings";
           default "terminate-contexts";
           type enumeration {
             enum "terminate-contexts" {
               description "Terminate associated contexts";
             }
             enum "free-services" {
               description "Allow free services";
             }
             enum "post-paid" {
               description "Switch to post-paid handling of contexts";
             }
           }
         }
         container quota-denied-action {
           description "Action to take when user quota is empty";
           uses apply-advanced;
           choice empty_bucket_choice {
             case case_1 {
               leaf terminate-context {
                 description "Terminate the PDP context";
                 type empty;
               }
             }
             case case_2 {
               leaf free-services {
                 description "Allow context to access free services";
                 type empty;
               }
             }
             case case_3 {
               leaf-list allow-service-class {
                 ordered-by user;
                 description "Allow access to service class";
                 type union {
                   type string {
                     pattern "<.*>|$.*";
                   }
                   type uint16 {
                     range "1 .. 4096";
                   }
                 }
                 max-elements 64;
               }
             }
           }
         }
         leaf quota-denied-redirect {
           description "Redirect non-free services if user quota is empty";
           type empty;
         }
         choice request-credit-on-activation-choice {
           leaf request-credit-on-activation {
             description "Send request to CCS on primary activation.";
             type empty;
           }
           leaf no-request-credit-on-activation {
             description "Don't send request to CCS on primary activation.";
             type empty;
           }
         }
       }
       list ro-profile {
         key name;
         description "Ro-based credit control profile";
         max-elements 32;
         leaf name {
           description "Profile identifier";
           type string {
             length "1 .. 64";
           }
         }
         uses apply-advanced;
         leaf diameter-application-system {
           description "Diameter application system";
           type string {
             length "1 .. 64";
           }
         }
         leaf-list additional-allowed-das {
           ordered-by user;
           description "Additional diameter application system allowed for the profile";
           type string {
             length "1 .. 64";
           }
           max-elements 16;
         }
         leaf service-context-id {
           description "Credit-control service-context supported";
           type string;
         }
         container ccr-avp {
           presence "enable ccr-avp";
           description "Inclusion of optional attributes in credit control requests";
           uses apply-advanced;
           leaf no-user-plmn-id {
             description "Do not include user-plmn-id AVP in credit control requests";
             type empty;
           }
           leaf no-ggsn-plmn-id {
             description "Do not include ggsn-plmn-id AVP in credit control requests";
             type empty;
           }
           leaf apn-type {
             description "APN type to include in Credit Control Requests";
             default "gi-apn";
             type enumeration {
               enum "gn-apn" {
                 description "Include Gn APN in CCR";
               }
               enum "gi-apn" {
                 description "Include Gi APN in CCR";
               }
             }
           }
         }
         leaf no-preemptive-reservation {
           description "Do not allow OCS to reserve quota preemptively";
           type empty;
         }
         container redirect {
           presence "enable redirect";
           description "Settings for redirect";
           uses apply-advanced;
           leaf append-uri {
             description "Append the request URL to the redirect URL";
             type empty;
           }
           leaf no-uri-formatting {
             description "Do not format URL according to included formatting codes";
             type empty;
           }
         }
         container failure {
           presence "enable failure";
           description "Failure handling settings for ro";
           uses apply-advanced;
           leaf failure-action {
             description "Failure action settings";
             default "retry-and-terminate";
             type enumeration {
               enum "continue" {
                 description "Retry once, and then continue context without credit control";
               }
               enum "terminate" {
                 description "Terminate context";
               }
               enum "retry-and-terminate" {
                 description "Retry once, and then terminate context";
               }
             }
           }
           container continue {
             presence "enable continue";
             description "Settings for handling continue";
             uses apply-advanced;
             leaf timeout {
               description "Validity time for continue action";
               default "30";
               units "minutes";
               type union {
                 type string {
                   pattern "<.*>|$.*";
                 }
                 type uint32 {
                   range "1 .. 4294967295";
                 }
               }
             }
             leaf no-reestablish {
               description "Don't reestablish credit session after communication failure";
               type empty;
             }
           }
         }
         leaf no-initiate-session-on-activation {
           description "Don't initiate a credit session on context activation";
           type empty;
         }
       }
       choice query-cc-as-choice {
         case case_1 {
           container query-cc-as {
             presence "enable query-cc-as";
             description "Credit Control Application System (CC-AS) user query";
             uses apply-advanced;
             container credit-control-user {
               description "Ask CC-AS whether to use credit control";
               presence "enable credit-control-user";
               uses fbc_credit_control_query_cc_as_type;
             }
             container no-credit-control-user {
               description "Settings to use if CC-AS forbids use credit control";
               presence "enable no-credit-control-user";
               uses fbc_credit_control_query_cc_as_type;
             }
           }
         }
         case case_2 {
           container query-ocs {
             presence "enable query-ocs";
             description "OCS user query";
             uses apply-advanced;
             container credit-control-user {
               presence "enable credit-control-user";
               description "Settings to use if OCS enables credit control for the user";
               uses apply-advanced;
               leaf cc {
                 description "Charging characteristics";
                 type union {
                   type string {
                     pattern "<.*>|$.*";
                   }
                   type uint32 {
                     range "0 .. 65535";
                   }
                 }
               }
             }
             container no-credit-control-user {
               presence "enable no-credit-control-user";
               description "Settings to use if OCS disables credit control for the user";
               uses apply-advanced;
               leaf cc {
                 description "Charging characteristics";
                 type union {
                   type string {
                     pattern "<.*>|$.*";
                   }
                   type uint32 {
                     range "0 .. 65535";
                   }
                 }
               }
             }
             container no-valid-answer {
               presence "enable no-valid-answer";
               description "Settings to use if no valid answer is received from the OCS";
               uses apply-advanced;
               leaf cc {
                 description "Charging characteristics";
                 type union {
                   type string {
                     pattern "<.*>|$.*";
                   }
                   type uint32 {
                     range "0 .. 65535";
                   }
                 }
               }
             }
           }
         }
       }
       leaf quota-threshold {
         description "Low credit threshold";
         default "0";
         units "percent";
         type union {
           type string {
             pattern "<.*>|$.*";
           }
           type uint32 {
             range "0 .. 10";
           }
         }
       }
       leaf allow-external-update {
         description "Allow externally initiated update of credit information";
         type empty;
       }
       leaf roaming-class {
         description "Include SCAP roaming class";
         type empty;
       }
     }
     container charging-unit {
       description "Charging unit";
       uses apply-advanced;
       list profile {
         key name;
         description "Charging unit profile";
         max-elements 16;
         leaf name {
           description "Profile identifier";
           type string {
             length "1 .. 64";
           }
         }
         uses apply-advanced;
         leaf currency {
           type string;
         }
       }
     }
     container service-class {
       description "Service class settings";
       status deprecated;
       uses apply-advanced;
       leaf authorization {
         description "Perform authorization";
         status deprecated;
         type empty;
       }
       container default {
         description "Default service class settings";
         uses apply-advanced;
         list activation-time {
           key name;
           description "Default service class activation times";
           max-elements 12;
           uses sbcc_service_class_rate_type;
         }
       }
     }
     container resource-identification {
       description "Resource identification service settings";
       uses apply-advanced;
       leaf service-set {
         description "Resource identification service set for APN";
         type string {
         }
       }
     }
     container authorization {
       presence "enable authorization";
       description "Perform authorization";
       uses apply-advanced;
       leaf redirect-unauthorized {
         description "Redirect unauthorized services";
         type empty;
       }
     }
     leaf postpaid-rating {
       description "Activate rating for postpaid subscribers";
       status deprecated;
       type empty;
     }
     leaf currency {
       description "Currency for proposed values";
       status deprecated;
       default "999";
       type string {
       }
     }
   }
   grouping fbc_credit_control_query_cc_as_type {
     uses apply-advanced;
     leaf cc {
       description "Charging characteristics";
       type union {
         type string {
           pattern "<.*>|$.*";
         }
         type uint32 {
           range "0 .. 65535";
         }
       }
     }
     leaf user-category {
       description "User category";
       type union {
         type string {
           pattern "<.*>|$.*";
         }
         type uint32 {
           range "1 .. 63";
         }
       }
     }
   }
   grouping fbc_static_rating_profile_type {
     leaf name {
       description "Profile identifier";
       type string {
         length "1 .. 64";
       }
     }
     uses apply-advanced;
     choice fbc_activation_time_choice {
       case case_1 {
         list activation-time {
           key name;
           description "Activation time for rates";
           max-elements 12;
           leaf name {
             description "Activation time (hh:mm)";
             type string {
             }
           }
           uses apply-advanced;
           list roaming-class {
             key name;
             description "Roaming class for rates";
             max-elements 24;
             leaf name {
               description "Roaming class identifier";
               type union {
                 type string {
                   pattern "<.*>|$.*";
                 }
                 type uint32 {
                   range "1 .. 24";
                 }
               }
             }
             uses apply-advanced;
             list quality-of-service {
               key name;
               description "Quality of service for rates";
               uses fbc_static_rating_qos_type;
             }
             container default-quality-of-service {
               description "Default quality of service for rates";
               uses fbc_static_rating_qos_default_type;
             }
           }
           container default-roaming-class {
             description "Default roaming class for rates";
             uses apply-advanced;
             list quality-of-service {
               key name;
               description "Quality of service for rates";
               uses fbc_static_rating_qos_type;
             }
             container default-quality-of-service {
               description "Default quality of service for rates";
               uses fbc_static_rating_qos_default_type;
             }
           }
         }
       }
       case case_2 {
         container all-time {
           description "Time-independent rates";
           uses apply-advanced;
           list roaming-class {
             key name;
             description "Roaming class for rates";
             max-elements 24;
             leaf name {
               description "Roaming class identifier";
               type union {
                 type string {
                   pattern "<.*>|$.*";
                 }
                 type uint32 {
                   range "1 .. 24";
                 }
               }
             }
             uses apply-advanced;
             list quality-of-service {
               key name;
               description "Quality of service for rates";
               uses fbc_static_rating_qos_type;
             }
             container default-quality-of-service {
               description "Default quality of service for rates";
               uses fbc_static_rating_qos_default_type;
             }
           }
           container default-roaming-class {
             description "Default roaming class for rates";
             uses apply-advanced;
             list quality-of-service {
               key name;
               description "Quality of service for rates";
               uses fbc_static_rating_qos_type;
             }
             container default-quality-of-service {
               description "Default quality of service for rates";
               uses fbc_static_rating_qos_default_type;
             }
           }
         }
       }
     }
   }
   grouping fbc_static_rating_qos_default_type {
     uses apply-advanced;
     list service-class {
       key name;
       description "Service class for rates";
       uses fbc_static_rating_service_class_type;
     }
     leaf block-rate {
       description "Rate per block for volume-based and duration-time-based block charging";
       default "0.0";
       type jt:unsigned-float;
     }
   }
   grouping fbc_static_rating_qos_type {
     leaf name {
       description "Quality of service";
       type enumeration {
         enum "conversational" {
           description "Conversational quality of service";
         }
         enum "streaming" {
           description "Streaming quality of service";
         }
         enum "interactive-1" {
           description "Interactive priority 1 quality of service";
         }
         enum "interactive-2" {
           description "Interactive priority 2 quality of service";
         }
         enum "interactive-3" {
           description "Interactive priority 3 quality of service";
         }
         enum "background" {
           description "Background quality of service";
         }
       }
     }
     uses apply-advanced;
     list service-class {
       key name;
       description "Service class";
       max-elements 64;
       uses fbc_static_rating_service_class_type;
     }
     leaf block-rate {
       description "Rate per block for volume-based and duration-time-based block charging";
       default "0.0";
       type jt:unsigned-float;
     }
   }
   grouping fbc_static_rating_service_class_type {
     leaf name {
       description "Service class identifier";
       type union {
         type string {
           pattern "<.*>|$.*";
         }
         type uint16 {
           range "1 .. 4096";
         }
       }
     }
     uses apply-advanced;
     leaf volume-rate {
       description "Rate per megabyte for volume-based charging";
       default "0.0";
       type jt:unsigned-float;
     }
     leaf block-rate {
       description "Rate per block for volume-based and active-time-based block charging";
       default "0.0";
       type jt:unsigned-float;
     }
     leaf authorization-code {
       description "Authorization code";
       default "authorized";
       type enumeration {
         enum "authorized" {
           description "Authorized";
         }
         enum "denied-roaming" {
           description "Deny access because of roaming class";
         }
         enum "denied-time-of-day" {
           description "Deny access because of time of day";
         }
         enum "denied-quality-of-service" {
           description "Deny access because of quality of service";
         }
         enum "denied-cost-warning" {
           description "Deny access because of cost warning";
         }
         enum "denied-volume-expired" {
           description "Deny access because volume expired";
         }
         enum "denied-user-defined-reason-1" {
           description "Deny access due to proprietery operator definition (1)";
         }
         enum "denied-user-defined-reason-2" {
           description "Deny access due to proprietery operator definition (2)";
         }
         enum "denied-redirect-first-access" {
           description "Deny access and redirect on first access of a service";
         }
         enum "denied-incompatible-user-application" {
           description "Deny access because user application is not compatible with service";
         }
         enum "denied-unknown" {
           description "Deny access for unknown reason";
         }
       }
     }
   }
   grouping sbcc_node_type {
     uses apply-advanced;
     leaf realm {
       description "Origin realm for Diameter messages";
       type string;
     }
     leaf host-name {
       description "Host name for Diameter messages";
       type string {
         length "1 .. 64";
       }
     }
     list diameter-host {
       key name;
       description "Diameter hosts";
       max-elements 63;
       uses diameter_host_type;
     }
     list diameter-peer {
       key name;
       description "Diameter peers";
       max-elements 16;
       uses diameter_peer_type;
     }
     list diameter-application-system {
       key name;
       description "Diameter application systems";
       max-elements 32;
       uses diameter_application_system_type;
     }
     container rating {
       description "Rating server settings";
       status deprecated;
       uses apply-advanced;
       leaf destination-realm {
         description "Destination realm for Diameter messages";
         type string;
       }
       list peer {
         key name;
         description "Diameter peer for messages";
         uses sbcc_diameter_peer_type;
       }
     }
     container prepaid {
       description "Prepaid system server settings";
       status deprecated;
       uses apply-advanced;
       leaf destination-realm {
         description "Destination realm for Diameter messages";
         type string;
       }
       list peer {
         key name;
         description "Diameter peer for messages";
         uses sbcc_diameter_peer_type;
       }
     }
     container subscription-update-nodes {
       description "External subscriber update server settings";
       uses apply-advanced;
       list peer {
         key "address port";
         ordered-by user;
         description "External update node configuration";
         max-elements 16;
         leaf address {
           description "IP address of external update node";
           type jt:ipv4addr;
         }
         leaf port {
           description "Port number of external update node";
           type union {
             type uint16;
             type string {
               pattern "<.*>|$.*";
             }
           }
         }
         uses apply-advanced;
       }
       list encryption {
         key name;
         ordered-by user;
         description "External update encryption configuration";
         max-elements 2;
         leaf name {
           description "Secret shared with the external update nodes";
           type jt:unreadable;
         }
         uses apply-advanced;
         leaf change-time {
           description "Activation time for secret";
           type string {
           }
         }
       }
     }
   }
   grouping diameter_application_system_type {
     leaf name {
       description "Diameter application system identifier";
       type string {
         length "1 .. 64";
       }
     }
     uses apply-advanced;
     leaf destination-realm {
       description "Destination realm";
       type string;
     }
     leaf application-id {
       description "Vendor-specific application identity";
       type string;
     }
     leaf diameter-peer {
       description "Diameter peer";
       status deprecated;
       type string {
         length "1 .. 64";
       }
     }
     list peer {
       key name;
       description "Diameter peers and priorities";
       max-elements 5;
       leaf name {
         description "Diameter peer id";
         type string {
           length "1 .. 64";
         }
       }
       uses apply-advanced;
       leaf priority {
         description "Priority of the peer";
         default "255";
         units "priority";
         type union {
           type string {
             pattern "<.*>|$.*";
           }
           type uint32 {
             range "0 .. 255";
           }
         }
       }
     }
     leaf allow-cc-session-failover {
       description "Allow failover for credit control session";
       type empty;
     }
     leaf timeout {
       description "Communication timeout";
       default "3";
       type union {
         type string {
           pattern "<.*>|$.*";
         }
         type uint32 {
           range "1 .. 60";
         }
       }
     }
     leaf request-window-size {
       description "Maximum number of outstanding requests";
       default "30";
       type union {
         type string {
           pattern "<.*>|$.*";
         }
         type uint32 {
           range "10 .. 32000";
         }
       }
     }
     leaf requests-per-second {
       description "Maximum requests per second";
       type union {
         type string {
           pattern "<.*>|$.*";
         }
         type uint32 {
           range "0 .. 5000";
         }
       }
     }
     leaf access-type {
       description "Connection type";
       default "agent";
       type enumeration {
         enum "direct" {
           description "Direct access to the diameter application server";
         }
         enum "agent" {
           description "The diameter application server is accessed via an agent";
         }
       }
     }
   }
   grouping diameter_host_type {
     leaf name {
       description "Host identifier";
       type string {
         length "1 .. 64";
       }
     }
     leaf host-name {
       description "Diameter host specified as fully qualified domain name";
       type string {
         length "1 .. 64";
       }
     }
   }
   grouping diameter_peer_type {
     description "Type of Diameter peer";
     leaf name {
       description "Peer identifier";
       type string {
         length "1 .. 64";
       }
     }
     leaf address {
       description "Peer address";
       type jt:ipv4addr;
     }
     leaf host {
       description "Diameter host identifier associated with the peer";
       type string {
         length "1 .. 64";
       }
     }
     leaf port {
       description "Peer port number";
       type union {
         type uint16;
         type string {
           pattern "<.*>|$.*";
         }
       }
     }
     container watchdog {
       uses apply-advanced;
       leaf timeout {
         description "Period between device watch dog requests";
         default "30";
         units "seconds";
         type union {
           type string {
             pattern "<.*>|$.*";
           }
           type uint32 {
             range "3 .. 300";
           }
         }
       }
     }
   }
   grouping sbcc_diameter_peer_type {
     leaf name {
       description "Diameter peer address";
       type jt:ipv4addr;
     }
     leaf timeout {
       description "Diameter protocol timeout";
       default "3";
       units "seconds";
       type union {
         type string {
           pattern "<.*>|$.*";
         }
         type uint32 {
           range "3 .. 10";
         }
       }
     }
   }
   grouping sbcc_service_class_rate_type {
     leaf name {
       description "Activation time for service class (hh:mm)";
       type string {
       }
     }
     uses apply-advanced;
     list service-class {
       key name;
       description "Service class identifier";
       max-elements 64;
       uses sbcc_service_class_rate_class_type;
     }
   }
   grouping sbcc_service_class_rate_class_type {
     leaf name {
       description "Service class identifier";
       type union {
         type string {
           pattern "<.*>|$.*";
         }
         type uint16 {
           range "1 .. 4096";
         }
       }
     }
     choice home_rate_or_free_choice {
       case case_1 {
         leaf home-rate {
           description "Nonroaming rate for default service class";
           default "0.0";
           type jt:unsigned-float;
         }
       }
       case case_2 {
         leaf home-free-use {
           description "Nonroaming users are not charged";
           type empty;
         }
       }
     }
     choice roaming_rate_or_free_choice {
       case case_1 {
         leaf roaming-rate {
           description "Roaming rate for default service class";
           default "0.0";
           type jt:unsigned-float;
         }
       }
       case case_2 {
         leaf roaming-free-use {
           description "Roaming users are not charged";
           type empty;
         }
       }
     }
   }
   grouping secintel-traceoptions {
     description "Security intelligence trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Trace flags";
       leaf name {
         type enumeration {
           enum "all" {
             description "Trace everything";
           }
           enum "feed" {
             description "Trace feed operation";
           }
           enum "ipc" {
             description "Trace ipc module";
           }
         }
       }
     }
   }
   grouping service_device_pool_object {
     leaf name {
       description "Service device pool name";
       type string {
         length "1 .. 63";
       }
     }
     uses apply-advanced;
     list interface {
       key name;
       ordered-by user;
       description "Service device name";
       leaf name {
         type string;
       }
       uses apply-advanced;
     }
   }
   grouping service_identification_type {
     description "Configure service identification services";
     uses apply-advanced;
     leaf unescape-conversion {
       description "Unescape characters in URI before processing";
       type empty;
     }
     container flow-limits {
       presence "enable flow-limits";
       description "Settings for limitation of inspection flows";
       uses apply-advanced;
       leaf max-user-child {
         description "Maximum allowed flows per protocol and user";
         default "150";
         type union {
           type string {
             pattern "<.*>|$.*";
           }
           type uint32 {
             range "0 .. 400";
           }
         }
       }
       leaf max-node-flow {
         description "Maximum accepted flows in the node";
         default "0";
         type union {
           type string {
             pattern "<.*>|$.*";
           }
           type uint32 {
             range "0 .. 1000000";
           }
         }
       }
       leaf max-analyzer-routing {
         description "Maximum accepted dynamic routing rule per analyzer";
         default "1000";
         type union {
           type string {
             pattern "<.*>|$.*";
           }
           type uint32 {
             range "0 .. 5000";
           }
         }
       }
     }
     list http-wsp-rule {
       key name;
       ordered-by user;
       description "HTTP WSP rule";
       max-elements 512;
       uses sid_http_wsp_rule_object;
     }
     list http-wsp-rule-set {
       key name;
       ordered-by user;
       description "Define a set of URI rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list smtp-rule {
       key name;
       ordered-by user;
       description "SMTP rule";
       max-elements 512;
       uses sid_smtp_rule_object;
     }
     list smtp-rule-set {
       key name;
       ordered-by user;
       description "Define a set of SMTP rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list pop3-rule {
       key name;
       ordered-by user;
       description "POP3 rule";
       max-elements 512;
       uses sid_pop3_rule_object;
     }
     list pop3-rule-set {
       key name;
       ordered-by user;
       description "Define a set of POP3 rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list ftp-rule {
       key name;
       ordered-by user;
       description "FTP rule";
       max-elements 512;
       uses sid_ftp_rule_object;
     }
     list ftp-rule-set {
       key name;
       ordered-by user;
       description "Define a set of FTP rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list tftp-rule {
       key name;
       ordered-by user;
       description "Define a TFTP rule";
       max-elements 512;
       uses sid_tftp_rule_object;
     }
     list tftp-rule-set {
       key name;
       ordered-by user;
       description "Define a set of TFTP rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list rtsp-rule {
       key name;
       ordered-by user;
       description "RTSP rule";
       max-elements 512;
       uses sid_rtsp_rule_object;
     }
     list rtsp-rule-set {
       key name;
       ordered-by user;
       description "Define a set of RTSP rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list sip-rule {
       key name;
       ordered-by user;
       description "SIP rule";
       max-elements 512;
       uses sid_sip_rule_object;
     }
     list sip-rule-set {
       key name;
       ordered-by user;
       description "Define a set of SIP rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list msn-rule {
       key name;
       ordered-by user;
       description "MSN rule";
       max-elements 512;
       uses sid_msn_rule_object;
     }
     list msn-rule-set {
       key name;
       ordered-by user;
       description "Define a set of MSN rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list dns-rule {
       key name;
       ordered-by user;
       description "DNS rule";
       max-elements 512;
       uses sid_dns_rule_object;
     }
     list dns-rule-set {
       key name;
       ordered-by user;
       description "Define a set of DNS rules";
       max-elements 256;
       leaf name {
         description "Name of the rule set";
         type string {
           length "1 .. 63";
         }
       }
       uses apply-advanced;
       list rule {
         key name;
         ordered-by user;
         description "Rule to be included in this rule set";
         max-elements 128;
         leaf name {
           description "Rule name";
           type string {
           }
         }
         uses apply-advanced;
       }
     }
     list header-rule {
       key name;
       ordered-by user;
       description "Header rule";
       max-elements 512;
       uses sid_header_rule_object;
     }
     list header-rule-set {
       key name;
       ordered-by user;
       description "Define a set of header rules";
       max-elements 256;
       leaf name {
         description "Name of the rule set";
         type string {
           length "1 .. 63";
         }
       }
       uses apply-advanced;
       list rule {
         key name;
         ordered-by user;
         description "Rule to be included in this rule set";
         max-elements 256;
         leaf name {
           description "Rule name";
           type string {
           }
         }
         uses apply-advanced;
       }
     }
     list heuristic-rule {
       key name;
       ordered-by user;
       description "Heuristic rule";
       max-elements 512;
       uses sid_heuristic_rule_object;
     }
     list heuristic-rule-set {
       key name;
       ordered-by user;
       description "Define a set of heuristic rules";
       max-elements 256;
       leaf name {
         description "Name of the rule set";
         type string {
           length "1 .. 63";
         }
       }
       uses apply-advanced;
       list rule {
         key name;
         ordered-by user;
         description "Rule to be included in this rule set";
         max-elements 256;
         leaf name {
           description "Rule name";
           type string {
           }
         }
         uses apply-advanced;
       }
     }
     list header-redirect-set {
       key name;
       ordered-by user;
       description "Define a set of header redirect rules";
       max-elements 128;
       leaf name {
         description "Name of header redirect set";
         type string {
           length "1 .. 63";
         }
       }
       uses apply-advanced;
       list cause {
         key name;
         ordered-by user;
         max-elements 16;
         uses header_redirect_cause_type;
       }
     }
     list uri-redirect-set {
       key name;
       ordered-by user;
       description "Define a set of URI redirect rules";
       max-elements 128;
       leaf name {
         description "Name of URI redirect set";
         type string {
           length "1 .. 63";
         }
       }
       uses apply-advanced;
       list cause {
         key name;
         ordered-by user;
         max-elements 16;
         uses uri_redirect_cause_type;
       }
     }
     container traceoptions {
       description "Trace options for GGSN services process";
       status deprecated;
       uses apply-advanced;
       list flag {
         key name;
         ordered-by user;
         description "Tracing parameters";
         leaf name {
           type enumeration {
             enum "routing-socket" {
               description "Trace routing-socket events";
             }
             enum "configuration" {
               description "Trace configuration events";
             }
             enum "service-identification" {
               description "Trace service-identification events";
             }
             enum "kernel-object" {
               description "Trace kernel object management";
             }
             enum "all" {
               description "Trace everything";
             }
           }
         }
       }
     }
   }
   grouping header_redirect_cause_type {
     leaf name {
       description "Cause of redirection";
       type enumeration {
         enum "roaming" {
           description "Traffic redirection because of roaming";
         }
         enum "calendar-time" {
           description "Traffic redirection because of time-of-day change";
         }
         enum "quality-of-service" {
           description "Traffic redirection because of QoS";
         }
         enum "volume-expired" {
           description "Traffic redirection because of expiration of volume limit";
         }
         enum "cost-warning" {
           description "Traffic redirection because of cost warning limit";
         }
         enum "user-defined-reason-1" {
           description "User-defined authorization code (1)";
         }
         enum "user-defined-reason-2" {
           description "User-defined authorization code (2)";
         }
         enum "user-defined-reason-3" {
           description "User-defined authorization code (3)";
         }
         enum "user-defined-reason-4" {
           description "User-defined authorization code (4)";
         }
         enum "user-defined-reason-5" {
           description "User-defined authorization code (5)";
         }
         enum "blacklisted" {
           description "Traffic redirection because if blacklisted rating group";
         }
         enum "not-allowed" {
           description "Traffic redirection because of disallowed service class";
         }
         enum "unsubscribed" {
           description "Traffic redirection because of unsubscribed service class";
         }
         enum "credit-expiry" {
           description "Traffic redirection because of expiration of credit";
         }
         enum "unknown" {
           description "Traffic redirection because of unknown reason";
         }
         enum "terminal" {
           description "Traffic redirection because of terminal denied access";
         }
         enum "default" {
           description "Default traffic redirection rule";
         }
       }
     }
     leaf destination-address {
       description "Redirect to this IP address";
       type jt:ipv4addr;
     }
     leaf destination-port {
       description "Redirect to this TCP/UDP port";
       type union {
         type string {
           pattern "<.*>|$.*";
         }
         type uint16 {
           range "1 .. 65535";
         }
       }
     }
   }
   grouping service_interface_pool_object {
     leaf name {
       description "Service interface pool name";
       type string {
         length "1 .. 63";
       }
     }
     uses apply-advanced;
     list interface {
       key name;
       ordered-by user;
       description "Service interface name";
       leaf name {
         type union {
           type jt:interface-unit;
           type string {
             pattern "<.*>|$.*";
           }
         }
       }
       uses apply-advanced;
     }
   }
   grouping service_point_type {
     leaf name {
       description "Service point name";
       type string;
     }
     uses apply-advanced;
     leaf service-point-type {
       description "Service point type";
       default "sip";
       type enumeration {
         enum "sip" {
         }
       }
     }
     container transport-details {
       presence "enable transport-details";
       description "IP address, port number and transport-protocols for the service-point";
       leaf port-number {
         description "Port number";
         type union {
           type string {
             pattern "<.*>|$.*";
           }
           type uint32 {
             range "0 .. 65535";
           }
         }
       }
       leaf ip-address {
         description "IP address";
         type jt:ipaddr;
       }
       leaf tcp {
         description "Transport protocol - TCP";
         type empty;
       }
       leaf udp {
         description "Transport protocol - UDP";
         type empty;
       }
       leaf fqdn {
         description "Fully Qualified Domain Name";
         type string {
           length "1 .. 128";
         }
       }
     }
     leaf service-interface {
       description "Associated service interface";
       type union {
         type jt:interface-unit;
         type string {
           pattern "<.*>|$.*";
         }
       }
     }
     container service-policies {
       presence "enable service-policies";
       uses service_policies_type;
     }
     leaf default-media-realm {
       description "Use this realm for allocating media resources for calls initiated to/from this service-point";
       type string {
         length "1 .. 4";
       }
     }
   }
   grouping service_policies_type {
     uses apply-advanced;
     leaf-list new-transaction-input-policies {
       ordered-by user;
       description "New transaction input policy name";
       type string;
       max-elements 10;
     }
     leaf-list new-transaction-output-policies {
       ordered-by user;
       description "New transaction output policy name";
       type string;
       max-elements 10;
     }
     leaf-list new-registration-input-policies {
       ordered-by user;
       description "New registration input policy name";
       type string;
       max-elements 10;
     }
     leaf-list new-call-usage-input-policies {
       ordered-by user;
       description "New call usage input policy name";
       type string;
       max-elements 10;
     }
     leaf-list new-call-usage-output-policies {
       ordered-by user;
       description "New call usage output policy name";
       type string;
       max-elements 10;
     }
   }
   grouping service_set_ipsec_vpn_options_object {
     uses apply-advanced;
     leaf-list trusted-ca {
       ordered-by user;
       description "List of trusted certificate authority profiles";
       type string;
     }
     container local-gateway {
       description "Address and routing instance for local gateway";
       leaf address {
         description "Local gateway address";
         type jt:ipaddr;
       }
       leaf routing-instance {
         description "Name of routing instance that hosts local gateway";
         default "default";
         type string;
       }
       leaf interface {
         description "Interface as local gateway";
         type union {
           type jt:interface-unit;
           type string {
             pattern "<.*>|$.*";
           }
         }
       }
       leaf gw-interface {
         description "Interface as local gateway";
         type union {
           type jt:interface-unit;
           type string {
             pattern "<.*>|$.*";
           }
         }
       }
     }
     leaf ike-access-profile {
       description "IKE access profile for dynamic peers";
       type string {
         length "1 .. 32";
       }
     }
     leaf passive-mode-tunneling {
       description "No active IP packet checks before IPSec encapsulation";
       type empty;
     }
     leaf clear-dont-fragment-bit {
       description "Clear the do not fragment bit";
       type empty;
     }
     leaf copy-dont-fragment-bit {
       description "Copy the do not fragment bit";
       type empty;
     }
     leaf set-dont-fragment-bit {
       description "Set the do not fragment bit";
       type empty;
     }
     leaf tunnel-mtu {
       description "Maximum transmit packet size";
       type union {
         type string {
           pattern "<.*>|$.*";
         }
         type uint32 {
           range "256 .. 9192";
         }
       }
     }
     leaf no-anti-replay {
       description "Disable the anti-replay check";
       type empty;
     }
     leaf anti-replay-window-size {
       description "Size of the anti-replay window";
       type union {
         type string {
           pattern "<.*>|$.*";
         }
         type uint32 {
           range "64 .. 4096";
         }
       }
     }
     container udp-encapsulate {
       presence "enable udp-encapsulate";
       description "UDP encapsulation of IPsec data traffic";
       leaf dest-port {
         description "UDP destination port";
         default "4565";
         type union {
           type string {
             pattern "<.*>|$.*";
           }
           type uint32 {
             range "1025 .. 65536";
           }
         }
       }
     }
     leaf no-nat-traversal {
       description "Disable NAT traversal for this service-set even if NAT is detected";
       type empty;
     }
     leaf nat-keepalive {
       description "NAT-T keepalive interval in secs";
       type union {
         type string {
           pattern "<.*>|$.*";
         }
         type uint32 {
           range "1 .. 300";
         }
       }
     }
     leaf no-certificate-chain-in-ike {
       description "Send only end-entity certificates";
       type empty;
     }
   }
   grouping service_set_type {
     leaf name {
       description "Service set name";
       type string {
         length "1 .. 63";
       }
     }
     uses apply-advanced;
     container service-identification {
       description "Service identification settings";
       uses apply-advanced;
       container service-id {
         description "Service ID settings";
         uses apply-advanced;
         container default {
           description "Default ID for packet content";
           uses apply-advanced;
           leaf payload {
             description "Identifier for all payload";
             type union {
               type string {
                 pattern "<.*>|$.*";
               }
               type uint32 {
                 range "0 .. 4294967295";
               }
             }
           }
           leaf retransmit {
             description "Identifier for restransmited bytes";
             status deprecated;
             type union {
               type string {
                 pattern "<.*>|$.*";
               }
               type uint32 {
                 range "0 .. 4294967295";
               }
             }
           }
           leaf retransmit-classification {
             status deprecated;
             type empty;
           }
         }
       }
       container service-class {
         description "Service class settings";
         uses apply-advanced;
         choice default_sc_or_sc_mirrors_si {
           case case_1 {
             leaf default {
               description "Default service class";
               type union {
                 type string {
                   pattern "<.*>|$.*";
                 }
                 type uint16 {
                   range "1 .. 4096";
                 }
               }
             }
           }
           case case_2 {
             leaf use-service-id {
               description "Use service ID for unmapped service classes";
               type empty;
             }
           }
         }
         list map {
           key name;
           description "Map of service IDs to service classes";
           max-elements 1000;
           uses sid_sc_to_scid_map_type;
         }
       }
       list header-rule-sets {
         key name;
         ordered-by user;
         description "List of service identification rule sets";
         max-elements 10;
         leaf name {
           type string {
             length "1 .. 63";
           }
         }
         uses apply-advanced;
       }
       list heuristic-rule-sets {
         key name;
         ordered-by user;
         description "List of heuristic rule sets";
         max-elements 10;
         leaf name {
           description "A heuristic rule set";
           type string {
             length "1 .. 63";
           }
         }
         uses apply-advanced;
       }
       list redirect-map {
         key name;
         ordered-by user;
         description "Mapping service identifiers to redirect sets";
         leaf name {
           description "A redirect set";
           type string {
             length "1 .. 63";
           }
         }
         leaf-list service-id {
           ordered-by user;
           description "Service identifier to redirect for the given redirect set";
           type string {
             length "1 .. 21";
           }
           max-elements 1000;
         }
       }
       leaf default-header-redirect-set {
         description "Default header redirect set for traffic redirection";
         type string {
           length "1 .. 63";
         }
       }
       leaf default-uri-redirect-set {
         description "Default URI redirect set for traffic redirection";
         type string {
           length "1 .. 63";
         }
       }
       leaf enable-http-pipeline {
         description "Enable HTTP pipeline support";
         type empty;
       }
       container enable-wtp-reassembly {
         presence "enable enable-wtp-reassembly";
         description "Enable WTP reassembly";
         uses apply-advanced;
         leaf max-reassembled-packets {
           description "Maximum number of reassembled packets";
           default "3";
           type union {
             type string {
               pattern "<.*>|$.*";
             }
             type uint32 {
               range "0 .. 255";
             }
           }
         }
         leaf max-reassembled-bytes {
           description "Maximum number of reassembled bytes";
           default "0";
           type union {
             type string {
               pattern "<.*>|$.*";
             }
             type uint32 {
               range "0 .. 362100";
             }
           }
         }
       }
       leaf enable-ftp-path-tracking {
         description "Enable FTP path tracking";
         type empty;
       }
       container signaling-classification {
         presence "enable signaling-classification";
         description "Settings for classification of session set-up and tear-down";
         uses apply-advanced;
         container setup {
           presence "enable setup";
           description "Settings for connection set-up";
           uses apply-advanced;
           leaf wsp-connection-oriented {
             description "Service identifier for WSP connection oriented traffic";
             type union {
               type string {
                 pattern "<.*>|$.*";
               }
               type uint32 {
                 range "0 .. 4294967295";
               }
             }
           }
           leaf tcp {
             description "Service identifier for TCP traffic";
             type union {
               type string {
                 pattern "<.*>|$.*";
               }
               type uint32 {
                 range "0 .. 4294967295";
               }
             }
           }
         }
         container teardown {
           presence "enable teardown";
           description "Settings for connection tear-down";
           uses apply-advanced;
           leaf wsp-connection-oriented {
             description "Service identifier for WSP connection oriented traffic";
             type union {
               type string {
                 pattern "<.*>|$.*";
               }
               type uint32 {
                 range "0 .. 4294967295";
               }
             }
           }
           leaf tcp {
             description "Service identifier for TCP traffic";
             type union {
               type string {
                 pattern "<.*>|$.*";
               }
               type uint32 {
                 range "0 .. 4294967295";
               }
             }
           }
         }
       }
       container unescape-conversion {
         description "Unescape characters in URI before processing";
         uses apply-advanced;
         leaf http {
           description "HTTP requests";
           type empty;
         }
         leaf wsp {
           description "WSP requests";
           type empty;
         }
         leaf rtsp {
           description "RTSP requests";
           type empty;
         }
         leaf sip {
           description "SIP requests";
           type empty;
         }
       }
     }
   }
   grouping services-ike {
     uses apply-advanced;
     list proposal {
       key name;
       ordered-by user;
       description "Define an IKE proposal";
       uses ike-proposal;
     }
     list policy {
       key name;
       ordered-by user;
       description "Define an IKE policy";
       uses svc-ike-policy;
     }
   }
   grouping ike-proposal {
     leaf name {
       description "Name of the IKE proposal";
       type string {
         length "1 .. 32";
       }
     }
     uses apply-advanced;
     leaf description {
       description "Text description of IKE proposal";
       type string {
         length "1 .. 80";
       }
     }
     leaf authentication-method {
       description "Define authentication method";
       type enumeration {
         enum "pre-shared-keys" {
           description "Preshared keys";
         }
         enum "rsa-signatures" {
           description "RSA signatures";
         }
         enum "dsa-signatures" {
           description "DSA signatures";
         }
         enum "ecdsa-signatures-256" {
           description "ECDSA signatures (254 bit modulus)";
         }
         enum "ecdsa-signatures-384" {
           description "ECDSA signatures (384 bit modulus)";
         }
       }
     }
     leaf dh-group {
       description "Define Diffie-Hellman group";
       type enumeration {
         enum "group1" {
           description "Diffie-Hellman Group1";
         }
         enum "group2" {
           description "Diffie-Hellman Group2";
         }
         enum "group5" {
           description "Diffie-Hellman Group5";
         }
         enum "group14" {
           description "Diffie-Hellman Group14";
         }
         enum "group15" {
           description "Diffie-Hellman Group15";
         }
         enum "group16" {
           description "Diffie-Hellman Group16";
         }
         enum "group19" {
           description "Diffie-Hellman Group19";
         }
         enum "group20" {
           description "Diffie-Hellman Group20";
         }
         enum "group24" {
           description "Diffie-Hellman Group24";
         }
       }
     }
     leaf authentication-algorithm {
       description "Define authentication algorithm";
       type enumeration {
         enum "md5" {
           description "MD5 authentication algorithm";
         }
         enum "sha1" {
           description "SHA1 authentication algorithm";
         }
         enum "sha-256" {
           description "SHA 256-bit authentication algorithm";
         }
         enum "sha-384" {
           description "SHA 384-bit authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
       }
     }
     leaf lifetime-seconds {
       description "Lifetime, in seconds";
       units "seconds";
       type union {
         type string {
           pattern "<.*>|$.*";
         }
         type uint32 {
           range "180 .. 86400";
         }
       }
     }
   }
   grouping services-ipsec {
     uses apply-advanced;
     list proposal {
       key name;
       ordered-by user;
       description "Define an IPSec proposal";
       uses ipsec-proposal;
     }
     list policy {
       key name;
       ordered-by user;
       description "Define an IPSec policy";
       uses ipsec-policy;
     }
   }
   grouping ipsec-policy {
     leaf name {
       description "Name of the IPSec policy";
       type string {
         length "1 .. 32";
       }
     }
     uses apply-advanced;
     leaf description {
       description "Text description of IPSec policy";
       type string {
         length "1 .. 80";
       }
     }
     container perfect-forward-secrecy {
       description "Define perfect forward secrecy";
       uses apply-advanced;
       leaf keys {
         description "Define Diffie-Hellman group";
         type enumeration {
           enum "group1" {
             description "Diffie-Hellman Group1";
           }
           enum "group2" {
             description "Diffie-Hellman Group2";
           }
           enum "group5" {
             description "Diffie-Hellman Group5";
           }
           enum "group14" {
             description "Diffie-Hellman Group14";
           }
           enum "group15" {
             description "Diffie-Hellman Group15";
           }
           enum "group16" {
             description "Diffie-Hellman Group16";
           }
           enum "group19" {
             description "Diffie-Hellman Group19";
           }
           enum "group20" {
             description "Diffie-Hellman Group20";
           }
           enum "group24" {
             description "Diffie-Hellman Group24";
           }
         }
       }
     }
     leaf-list proposals {
       ordered-by user;
       description "Name of the proposal";
       type string {
         length "1 .. 32";
       }
     }
     leaf proposal-set {
       description "Types of default IPSEC proposal-set";
       type enumeration {
         enum "basic" {
           description "IPSEC basic proposal-set";
         }
         enum "compatible" {
           description "IPSEC compatible proposal-set";
         }
         enum "standard" {
           description "IPSEC standard proposal-set";
         }
       }
     }
   }
   grouping ipsec-proposal {
     leaf name {
       description "Name of the IPSec proposal";
       type string {
         length "1 .. 32";
       }
     }
     uses apply-advanced;
     leaf description {
       description "Text description of IPSec proposal";
       type string {
         length "1 .. 80";
       }
     }
     leaf protocol {
       description "Define an IPSec protocol for the proposal";
       type enumeration {
         enum "ah" {
           description "Authentication header";
         }
         enum "esp" {
           description "Encapsulated Security Payload header";
         }
         enum "bundle" {
           description "Bundle (AH authentication plus ESP encryption)";
         }
       }
     }
     leaf authentication-algorithm {
       description "Define authentication algorithm";
       type enumeration {
         enum "hmac-md5-96" {
           description "HMAC-MD5-96 authentication algorithm";
         }
         enum "hmac-sha1-96" {
           description "HMAC-SHA1-96 authentication algorithm";
         }
         enum "hmac-sha-256-128" {
           description "HMAC-SHA-256-128 authentication algorithm";
         }
         enum "hmac-sha-256-96" {
           description "HMAC-SHA-256-96 authentication algorithm (non-RFC compliant)";
         }
         enum "hmac-sha2-256" {
           description "HMAC-SHA2-256 authentication algorithm";
         }
       }
     }
     leaf encryption-algorithm {
       description "Define encryption algorithm";
       type enumeration {
         enum "des-cbc" {
           description "DES-CBC encryption algorithm";
         }
         enum "3des-cbc" {
           description "3DES-CBC encryption algorithm";
         }
         enum "aes-128-cbc" {
           description "AES-CBC 128-bit encryption algorithm";
         }
         enum "aes-192-cbc" {
           description "AES-CBC 192-bit encryption algorithm";
         }
         enum "aes-256-cbc" {
           description "AES-CBC 256-bit encryption algorithm";
         }
         enum "aes-128-gcm" {
           description "AES-GCM 128-bit encryption algorithm with 16 octet ICV";
         }
         enum "aes-192-gcm" {
           description "AES-GCM 192-bit encryption algorithm with 16 octet ICV";
         }
         enum "aes-256-gcm" {
           description "AES-GCM 256-bit encryption algorithm with 16 octet ICV";
         }
       }
     }
     leaf lifetime-seconds {
       description "Lifetime, in seconds";
       units "seconds";
       type union {
         type string {
           pattern "<.*>|$.*";
         }
         type uint32 {
           range "180 .. 86400";
         }
       }
     }
   }
   grouping services-pcef {
     description "PCEF configuration";
     uses apply-advanced;
     container traceoptions {
       description "Trace options related to PCEF";
       uses pcef-traceoptions;
     }
     container event-trigger-profiles {
       description "Event trigger profiles";
       uses apply-advanced;
       list profile {
         key name;
         uses evt-trigger-profile;
       }
     }
     container flow-descriptions {
       description "PCC flow descriptions";
       uses apply-advanced;
       list definition {
         key name;
         uses pcc-flow;
       }
     }
     container pcc-action-profiles {
       description "PCC action profiles";
       uses apply-advanced;
       list definition {
         key name;
         uses pcc-action-profile;
       }
     }
     container pcc-rules {
       description "PCC rules";
       uses apply-advanced;
       list definition {
         key name;
         uses pcc-rule;
       }
     }
     container pcc-rulebases {
       description "PCC rulebases";
       uses apply-advanced;
       list definition {
         key name;
         ordered-by user;
         uses pcc-rulebase;
       }
     }
     container profile {
       description "PCEF profiles";
       uses apply-advanced;
       list definition {
         key name;
         ordered-by user;
         uses pcef-profiles;
       }
     }
   }
   grouping evt-trigger-profile {
     description "Event trigger profile";
     leaf name {
       description "Event trigger profile name";
       type string {
         length "1 .. 63";
       }
     }
     uses apply-advanced;
     leaf rat-change {
       description "RAT change trigger";
       type empty;
     }
     leaf sgsn-change {
       description "SGSN change trigger";
       type empty;
     }
     leaf plmn-change {
       description "PLMN change trigger";
       type empty;
     }
     leaf ip-can-change {
       description "IP-CAN change trigger";
       type empty;
     }
     leaf tft-change {
       description "TFT change trigger";
       type empty;
     }
     leaf rai-change {
       description "RAI change trigger";
       type empty;
     }
     leaf user-location-change {
       description "User location change";
       type empty;
     }
     leaf ue-timezone-change {
       description "UE timezone change";
       type empty;
     }
   }
   grouping pcc-action-profile {
     description "PCC action profiles";
     leaf name {
       description "PCC action profile identifier";
       type string {
         length "1 .. 63";
       }
     }
     uses apply-advanced;
     leaf logging-rule {
       description "Policy based logging rule name";
       type string {
         length "1 .. 63";
       }
     }
     container maximum-bit-rate {
       presence "enable maximum-bit-rate";
       description "Maximum bit rate";
       leaf uplink {
         description "Maximum bit rate uplink";
         default "0";
         units "kilobits";
         type union {
           type string {
             pattern "<.*>|$.*";
           }
           type uint32 {
             range "0 .. 6144000";
           }
         }
       }
       leaf downlink {
         description "Maximum bit rate downlink";
         default "0";
         units "kilobits";
         type union {
           type string {
             pattern "<.*>|$.*";
           }
           type uint32 {
             range "0 .. 6144000";
           }
         }
       }
     }
     container burst-size {
       presence "enable burst-size";
       description "Burst Size";
       uses apply-advanced;
       leaf uplink {
         description "Burst size uplink";
         units "bytes";
         type union {
           type string {
             pattern "<.*>|$.*";
           }
           type uint32 {
             range "1500 .. 1500000000";
           }
         }
       }
       leaf downlink {
         description "Burst size downlink";
         units "bytes";
         type union {
           type string {
             pattern "<.*>|$.*";
           }
           type uint32 {
             range "1500 .. 1500000000";
           }
         }
       }
     }
     leaf gate-status {
       description "Control gate status";
       type enumeration {
         enum "uplink" {
           description "Enable uplink traffic";
         }
         enum "downlink" {
           description "Enable downlink traffic";
         }
         enum "uplink-downlink" {
           description "Enable uplink and downlink traffic";
         }
         enum "disable-both" {
           description "Disable any traffic";
         }
       }
     }
     container charging {
       description "Charing related configuration";
       uses apply-advanced;
       leaf rating-group {
         description "Rating group";
         type union {
           type string {
             pattern "<.*>|$.*";
           }
           type uint32 {
             range "0 .. 4294967294";
           }
         }
       }
       leaf service-identifier {
         description "Service identifier";
         default "0";
         type union {
           type string {
             pattern "<.*>|$.*";
           }
           type uint32 {
             range "0 .. 4294967294";
           }
         }
       }
       leaf charging-method {
         description "Charging method";
         type enumeration {
           enum "online" {
             description "Use online charging method";
           }
           enum "offline" {
             description "Use offline charging method";
           }
           enum "both" {
             description "Use online and offline charging method";
           }
           enum "none" {
             description "Use no charging";
           }
         }
       }
       leaf measurement-method {
         description "Charging measure method";
         default "volume-time";
         type enumeration {
           enum "none" {
             description "No default measuring method for charging";
           }
           enum "volume" {
             description "Volume based charging";
           }
           enum "time" {
             description "Time based charging";
           }
           enum "volume-time" {
             description "Volume and time based charging";
           }
           enum "event" {
             description "Event based charging";
           }
         }
       }
       container application-function-record-info {
         presence "enable application-function-record-info";
         description "Application function record information";
         uses apply-advanced;
         leaf af-charging-identifier {
           description "Application function charging identifier";
           type string {
             length "1 .. 63";
           }
         }
       }
       leaf service-id-level-reporting {
         description "Toggle service-id level reporting";
         type empty;
       }
     }
     container redirect {
       description "Redirect to different destination";
       uses apply-advanced;
       leaf url {
         description "Redirect url name";
         type string {
           length "1 .. 512";
         }
       }
     }
     container forwarding-class {
       description "Classify packet to forwarding class";
       uses apply-advanced;
       leaf class-name {
         description "Forwarding class name";
         type string {
         }
       }
     }
     container steering {
       description "Steering information";
       uses apply-advanced;
       container routing-instance {
         description "Routing instance information";
         leaf uplink {
           description "Instance name uplink";
           type string;
         }
         leaf downlink {
           description "Instance name downlink";
           type string;
         }
       }
       container path {
         description "HTTP steering information";
         choice ip-address-type {
           case case_1 {
             leaf ipv4-address {
               description "IPv4 address of the steering destination";
               type jt:ipv4prefix;
             }
           }
           case case_2 {
             leaf ipv6-address {
               description "IPv6 address of the steering destination";
               type jt:ipv6prefix;
             }
           }
         }
       }
       leaf keep-existing-steering {
         description "Keep existing steering";
         type empty;
       }
     }
     container hcm-profile {
       description "HCM Profile";
       uses apply-advanced;
       leaf profile-name {
         description "HCM Profile Name";
         type string;
       }
     }
     leaf monitoring-key {
       description "Usage Monitoring key";
       type string {
         length "1 .. 63";
       }
     }
   }
   grouping pcc-flow {
     description "Configure PCC flow";
     leaf name {
       description "PCC flow identifier";
       type string {
         length "1 .. 63";
       }
     }
     uses apply-advanced;
     leaf direction {
       description "PCC flow direction";
       type enumeration {
         enum "downlink" {
           description "Downlink direction";
         }
         enum "uplink" {
           description "Uplink direction";
         }
         enum "both" {
           description "Both uplink and downlink directons";
         }
       }
     }
     leaf protocol {
       description "PCC flow IPv4 protocol";
       type union {
         type string {
           pattern "<.*>|$.*";
         }
         type uint8 {
           range "0 .. 255";
         }
       }
     }
     leaf-list local-ports {
       description "Local port or port list";
       type union {
         type string {
           pattern "<.*>|$.*";
         }
         type uint16 {
           range "1 .. 65535";
         }
       }
       max-elements 3;
     }
     list local-port-range {
       key "low high";
       ordered-by user;
       description "Local port range";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     leaf-list remote-ports {
       description "Remote port or port list";
       type union {
         type string {
           pattern "<.*>|$.*";
         }
         type uint16 {
           range "1 .. 65535";
         }
       }
       max-elements 3;
     }
     list remote-port-range {
       key "low high";
       ordered-by user;
       description "Remote port range";
       max-elements 3;
       leaf low {
         description "Lower limit of port range";
         type union {
           type string {
             pattern "<.*>|$.*";
           }
           type uint16 {
             range "1 .. 65535";
           }
         }
       }
       leaf high {
         description "Upper limit of port range";
         type union {
           type string {
             pattern "<.*>|$.*";
           }
           type uint16 {
             range "1 .. 65535";
           }
         }
       }
     }
     container remote-address {
       description "Remote address";
       choice ip-address-type {
         case case_1 {
           leaf ipv4-address {
             description "IPv4 address for the flow";
             type jt:ipv4prefix;
           }
         }
         case case_2 {
           leaf ipv6-address {
             description "IPv6 address for the flow";
             type jt:ipv6prefix;
           }
         }
       }
     }
   }
   grouping pcc-rule {
     description "PCC rules configuration";
     leaf name {
       description "PCC Rule identifier";
       type string {
       }
     }
     uses apply-advanced;
     container from {
       description "Aggregate of flows using same pcc-action-profile";
       uses apply-advanced;
       list flows {
         key name;
         ordered-by user;
         description "Associate PCC Flows";
         max-elements 64;
         leaf name {
           description "PCC Flow identifier";
           type string {
             length "1 .. 63";
           }
         }
         uses apply-advanced;
       }
       list applications {
         key name;
         ordered-by user;
         description "Associated application signature names";
         max-elements 10;
         leaf name {
           description "Signature names";
           type string {
             length "1 .. 63";
           }
         }
         uses apply-advanced;
       }
       list nested-applications {
         key name;
         ordered-by user;
         description "Associated nested application signature names";
         status deprecated;
         max-elements 10;
         leaf name {
           description "Nested application signature names";
           type string {
             length "1 .. 63";
           }
         }
         uses apply-advanced;
       }
       list application-groups {
         key name;
         ordered-by user;
         description "Application Group signature names";
         max-elements 10;
         leaf name {
           description "Application group names";
           type string {
             length "1 .. 63";
           }
         }
         uses apply-advanced;
       }
     }
     container then {
       description "Specified pcc-action-profile";
       uses apply-advanced;
       leaf pcc-action-profile {
         description "PCC Action profile name";
         type string {
           length "1 .. 63";
         }
       }
     }
   }
   grouping pcc-rulebase {
     description "PCC rulebases";
     leaf name {
       description "PCC Rulebase identifier";
       type string {
       }
     }
     uses apply-advanced;
     list pcc-rule {
       key name;
       ordered-by user;
       max-elements 32;
       leaf name {
         description "PCC rule name";
         type string {
           length "1 .. 63";
         }
       }
       leaf precedence {
         description "PCC rule precedence";
         type union {
           type string {
             pattern "<.*>|$.*";
           }
           type uint16 {
             range "1 .. 4000";
           }
         }
       }
     }
   }
   grouping pcef-profiles {
     description "PCEF profiles";
     leaf name {
       description "PCEF profile name";
       type string {
         length "1 .. 63";
       }
     }
     uses apply-advanced;
     leaf control-byte-rating-group {
       description "Rating group id";
       type union {
         type string {
           pattern "<.*>|$.*";
         }
         type uint32 {
           range "0 .. 4294967294";
         }
       }
     }
     leaf unresolved-flow-action {
       description "Flow action";
       type enumeration {
         enum "forward" {
           description "Forward";
         }
         enum "drop" {
           description "Drop";
         }
       }
     }
     container maximum-per-pdn-service-flows {
       description "Max service flows per PDN";
       leaf num {
         description "Value";
         type union {
           type uint32;
           type string {
             pattern "<.*>|$.*";
           }
         }
       }
     }
     container dynamic-policy-control {
       description "Dynamic policy control";
       uses apply-advanced;
       container pcc-rules {
         description "PCC rules association";
         uses apply-advanced;
         list rule-assoc {
           key name;
           ordered-by user;
           max-elements 64;
           uses profile-rule-assoc;
         }
       }
       list pcc-rulebases {
         key name;
         ordered-by user;
         description "PCC rulebase association";
         leaf name {
           description "PCC rulebase name";
           type string {
             length "1 .. 63";
           }
         }
         uses apply-advanced;
       }
       leaf diameter-profile {
         description "Diameter profile name";
         type string {
           length "1 .. 63";
         }
       }
       leaf event-trigger-profile {
         description "Event trigger profile name";
         type string {
           length "1 .. 63";
         }
       }
       leaf session-failover-not-supported {
         description "Session failover not supported";
         type empty;
       }
       leaf release {
         description "To override Gx release to R8|R9";
         type enumeration {
           enum "r8" {
             description "Gx release 8";
           }
           enum "r9" {
             description "Gx release 9";
           }
         }
       }
     }
     container static-policy-control {
       description "Static policy control";
       uses apply-advanced;
       container pcc-rules {
         description "PCC rules association";
         uses apply-advanced;
         list rule-assoc {
           key name;
           ordered-by user;
           max-elements 64;
           uses profile-static-rule-association;
         }
       }
       list pcc-rulebases {
         key name;
         ordered-by user;
         description "PCC rulebase association";
         leaf name {
           description "PCC rulebase name";
           type string {
             length "1 .. 63";
           }
         }
         uses apply-advanced;
         leaf time-of-day-profile {
           description "Time of day profile name";
           type string {
             length "1 .. 63";
           }
         }
       }
       leaf-list activate-dedicated-bearers {
         description "Enable dedicated bearer activation on initial attach with qci";
         type union {
           type string {
             pattern "<.*>|$.*";
           }
           type uint8 {
             range "1 .. 9";
           }
         }
         max-elements 9;
       }
     }
     container aaa-policy-control {
       description "AAA policy control";
       uses apply-advanced;
       leaf profile {
         description "AAA profile name";
         type string {
           length "1 .. 32";
         }
       }
       leaf user-password {
         description "User password";
         type string {
           length "1 .. 32";
         }
       }
       list pcc-rulebases {
         key name;
         ordered-by user;
         description "PCC rulebase association";
         leaf name {
           description "PCC rulebase name";
           type string {
             length "1 .. 63";
           }
         }
         uses apply-advanced;
       }
     }
   }
   grouping pcef-traceoptions {
     description "Trace options related to PCEF";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "init" {
             description "Trace initialization events";
           }
           enum "config" {
             description "Trace configuration events";
           }
           enum "general" {
             description "Trace general events";
           }
           enum "high-availability" {
             description "Trace high availability events";
           }
           enum "debug" {
             description "Trace debug internal events";
           }
           enum "fsm" {
             description "Trace fsm events";
           }
           enum "tftmgr" {
             description "Trace tftmgr events";
           }
           enum "all" {
             description "Trace everything";
           }
         }
       }
     }
   }
   grouping profile-rule-assoc {
     leaf name {
       description "PCC rule name";
       type string {
         length "1 .. 63";
       }
     }
     leaf precedence {
       description "PCC rule precedence";
       type union {
         type string {
           pattern "<.*>|$.*";
         }
         type uint16 {
           range "1 .. 4000";
         }
       }
     }
   }
   grouping profile-static-rule-association {
     leaf name {
       description "PCC rule name";
       type string {
         length "1 .. 63";
       }
     }
     leaf precedence {
       description "PCC rule precedence";
       type union {
         type string {
           pattern "<.*>|$.*";
         }
         type uint16 {
           range "1 .. 4000";
         }
       }
     }
     leaf time-of-day-profile {
       description "Time of day profile name";
       type string {
         length "1 .. 63";
       }
     }
     container pcc-action-profile {
       description "PCC action profile association";
       status deprecated;
       leaf rules-action-profile {
         description "PCC action profile name";
         type string {
           length "1 .. 63";
         }
       }
     }
   }
   grouping session_management_apn_type {
     uses apply-advanced;
     leaf exclude-dedicated-signaling {
       description "Exclude dedicated signaling from session management handling";
       type empty;
     }
     container idle-timeout {
       description "Idle timeout settings";
       uses apply-advanced;
       leaf no-supervision {
         description "Don't allow idle supervision";
         type empty;
       }
       container radius {
         description "Timeout settings based on RADIUS";
         uses apply-advanced;
         leaf use-timeout {
           description "Use idle timeout received from RADIUS";
           type empty;
         }
         leaf no-supervision {
           description "Don't allow RADIUS-based idle supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container sgsn-plmn-id {
         description "Timeout settings based on SGSN PLMN IDs";
         uses apply-advanced;
         list plmn {
           key name;
           description "Timeout settings based on SGSN PLMN";
           uses sgsn_plmn_id_idle_timeout_type;
         }
         leaf no-supervision {
           description "Don't allow idle supervision based on SGSN PLMN ID";
           type empty;
         }
       }
       container roaming {
         description "Timeout settings based on roaming";
         uses apply-advanced;
         leaf timeout {
           description "Maximum context idle time, a multiple of 15";
           units "minutes";
           type union {
             type string {
               pattern "<.*>|$.*";
             }
             type uint32 {
               range "1 .. 525600";
             }
           }
         }
         leaf no-supervision {
           description "Don't allow roaming-based idle supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container charging-profile {
         description "Timeout settings based on charging profile";
         uses apply-advanced;
         container profile0 {
           description "Profile 0";
           leaf timeout {
             description "Maximum consecutive idle minutes for a context";
             units "minutes";
             type union {
               type string {
                 pattern "<.*>|$.*";
               }
               type uint32 {
                 range "1 .. 525600";
               }
             }
           }
         }
         container profile1 {
           description "Profile 1";
           leaf timeout {
             description "Maximum consecutive idle minutes for a context";
             units "minutes";
             type union {
               type string {
                 pattern "<.*>|$.*";
               }
               type uint32 {
                 range "1 .. 525600";
               }
             }
           }
         }
         container profile2 {
           description "Profile 2";
           leaf timeout {
             description "Maximum consecutive idle minutes for a context";
             units "minutes";
             type union {
               type string {
                 pattern "<.*>|$.*";
               }
               type uint32 {
                 range "1 .. 525600";
               }
             }
           }
         }
         container profile3 {
           description "Profile 3";
           leaf timeout {
             description "Maximum consecutive idle minutes for a context";
             units "minutes";
             type union {
               type string {
                 pattern "<.*>|$.*";
               }
               type uint32 {
                 range "1 .. 525600";
               }
             }
           }
         }
         container profile4 {
           description "Profile 4";
           leaf timeout {
             description "Maximum consecutive idle minutes for a context";
             units "minutes";
             type union {
               type string {
                 pattern "<.*>|$.*";
               }
               type uint32 {
                 range "1 .. 525600";
               }
             }
           }
         }
         container profile5 {
           description "Profile 5";
           leaf timeout {
             description "Maximum consecutive idle minutes for a context";
             units "minutes";
             type union {
               type string {
                 pattern "<.*>|$.*";
               }
               type uint32 {
                 range "1 .. 525600";
               }
             }
           }
         }
         container profile6 {
           description "Profile 6";
           leaf timeout {
             description "Maximum consecutive idle minutes for a context";
             units "minutes";
             type union {
               type string {
                 pattern "<.*>|$.*";
               }
               type uint32 {
                 range "1 .. 525600";
               }
             }
           }
         }
         container profile7 {
           description "Profile 7";
           leaf timeout {
             description "Maximum consecutive idle minutes for a context";
             units "minutes";
             type union {
               type string {
                 pattern "<.*>|$.*";
               }
               type uint32 {
                 range "1 .. 525600";
               }
             }
           }
         }
         container profile8 {
           description "Profile 8";
           leaf timeout {
             description "Maximum consecutive idle minutes for a context";
             units "minutes";
             type union {
               type string {
                 pattern "<.*>|$.*";
               }
               type uint32 {
                 range "1 .. 525600";
               }
             }
           }
         }
         container profile9 {
           description "Profile 9";
           leaf timeout {
             description "Maximum consecutive idle minutes for a context";
             units "minutes";
             type union {
               type string {
                 pattern "<.*>|$.*";
               }
               type uint32 {
                 range "1 .. 525600";
               }
             }
           }
         }
         container profile10 {
           description "Profile 10";
           leaf timeout {
             description "Maximum consecutive idle minutes for a context";
             units "minutes";
             type union {
               type string {
                 pattern "<.*>|$.*";
               }
               type uint32 {
                 range "1 .. 525600";
               }
             }
           }
         }
         container profile11 {
           description "Profile 11";
           leaf timeout {
             description "Maximum consecutive idle minutes for a context";
             units "minutes";
             type union {
               type string {
                 pattern "<.*>|$.*";
               }
               type uint32 {
                 range "1 .. 525600";
               }
             }
           }
         }
         container profile12 {
           description "Profile 12";
           leaf timeout {
             description "Maximum consecutive idle minutes for a context";
             units "minutes";
             type union {
               type string {
                 pattern "<.*>|$.*";
               }
               type uint32 {
                 range "1 .. 525600";
               }
             }
           }
         }
         container profile13 {
           description "Profile 13";
           leaf timeout {
             description "Maximum consecutive idle minutes for a context";
             units "minutes";
             type union {
               type string {
                 pattern "<.*>|$.*";
               }
               type uint32 {
                 range "1 .. 525600";
               }
             }
           }
         }
         container profile14 {
           description "Profile 14";
           leaf timeout {
             description "Maximum consecutive idle minutes for a context";
             units "minutes";
             type union {
               type string {
                 pattern "<.*>|$.*";
               }
               type uint32 {
                 range "1 .. 525600";
               }
             }
           }
         }
         container profile15 {
           description "Profile 15";
           leaf timeout {
             description "Maximum consecutive idle minutes for a context";
             units "minutes";
             type union {
               type string {
                 pattern "<.*>|$.*";
               }
               type uint32 {
                 range "1 .. 525600";
               }
             }
           }
         }
         leaf no-supervision {
           description "Don't allow session supervision based on charging profile";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container default {
         description "Default timeout settings";
         uses apply-advanced;
         leaf timeout {
           description "Maximum continuous idle time for a context";
           units "minutes";
           type union {
             type string {
               pattern "<.*>|$.*";
             }
             type uint32 {
               range "1 .. 525600";
             }
           }
         }
         leaf no-supervision {
           description "Don't allow default idle supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
     }
     container session-timeout {
       description "Session timeout settings";
       uses apply-advanced;
       leaf no-supervision {
         description "Don't allow session supervision";
         type empty;
       }
       container radius {
         description "Timeout settings based on RADIUS";
         uses apply-advanced;
         leaf use-timeout {
           description "Use session timeout received from RADIUS";
           type empty;
         }
         leaf no-supervision {
           description "Don't allow RADIUS-based session supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container sgsn-plmn-id {
         description "Timeout settings based on SGSN PLMN IDs";
         uses apply-advanced;
         list plmn {
           key name;
           description "Timeout settings based on SGSN PLMN";
           uses sgsn_plmn_id_session_timeout_type;
         }
         leaf no-supervision {
           description "Don't allow session supervision based on SGSN PLMN ID";
           type empty;
         }
       }
       container roaming {
         description "Timeout settings based on roaming";
         uses apply-advanced;
         leaf timeout {
           description "Maximum duration for a context";
           units "minutes";
           type union {
             type string {
               pattern "<.*>|$.*";
             }
             type uint32 {
               range "15 .. 1440";
             }
           }
         }
         leaf no-supervision {
           description "Don't allow roaming-based session supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container charging-profile {
         description "Timeout settings based on charging profile";
         uses apply-advanced;
         container profile0 {
           description "Profile 0";
           leaf timeout {
             description "Maximum duration for a context";
             units "minutes";
             type union {
               type string {
                 pattern "<.*>|$.*";
               }
               type uint32 {
                 range "15 .. 1440";
               }
             }
           }
         }
         container profile1 {
           description "Profile 1";
           leaf timeout {
             description "Maximum duration for a context";
             units "minutes";
             type union {
               type string {
                 pattern "<.*>|$.*";
               }
               type uint32 {
                 range "15 .. 1440";
               }
             }
           }
         }
         container profile2 {
           description "Profile 2";
           leaf timeout {
             description "Maximum duration for a context";
             units "minutes";
             type union {
               type string {
                 pattern "<.*>|$.*";
               }
               type uint32 {
                 range "15 .. 1440";
               }
             }
           }
         }
         container profile3 {
           description "Profile 3";
           leaf timeout {
             description "Maximum duration for a context";
             units "minutes";
             type union {
               type string {
                 pattern "<.*>|$.*";
               }
               type uint32 {
                 range "15 .. 1440";
               }
             }
           }
         }
         container profile4 {
           description "Profile 4";
           leaf timeout {
             description "Maximum duration for a context";
             units "minutes";
             type union {
               type string {
                 pattern "<.*>|$.*";
               }
               type uint32 {
                 range "15 .. 1440";
               }
             }
           }
         }
         container profile5 {
           description "Profile 5";
           leaf timeout {
             description "Maximum duration for a context";
             units "minutes";
             type union {
               type string {
                 pattern "<.*>|$.*";
               }
               type uint32 {
                 range "15 .. 1440";
               }
             }
           }
         }
         container profile6 {
           description "Profile 6";
           leaf timeout {
             description "Maximum duration for a context";
             units "minutes";
             type union {
               type string {
                 pattern "<.*>|$.*";
               }
               type uint32 {
                 range "15 .. 1440";
               }
             }
           }
         }
         container profile7 {
           description "Profile 7";
           leaf timeout {
             description "Maximum duration for a context";
             units "minutes";
             type union {
               type string {
                 pattern "<.*>|$.*";
               }
               type uint32 {
                 range "15 .. 1440";
               }
             }
           }
         }
         container profile8 {
           description "Profile 8";
           leaf timeout {
             description "Maximum duration for a context";
             units "minutes";
             type union {
               type string {
                 pattern "<.*>|$.*";
               }
               type uint32 {
                 range "15 .. 1440";
               }
             }
           }
         }
         container profile9 {
           description "Profile 9";
           leaf timeout {
             description "Maximum duration for a context";
             units "minutes";
             type union {
               type string {
                 pattern "<.*>|$.*";
               }
               type uint32 {
                 range "15 .. 1440";
               }
             }
           }
         }
         container profile10 {
           description "Profile 10";
           leaf timeout {
             description "Maximum duration for a context";
             units "minutes";
             type union {
               type string {
                 pattern "<.*>|$.*";
               }
               type uint32 {
                 range "15 .. 1440";
               }
             }
           }
         }
         container profile11 {
           description "Profile 11";
           leaf timeout {
             description "Maximum duration for a context";
             units "minutes";
             type union {
               type string {
                 pattern "<.*>|$.*";
               }
               type uint32 {
                 range "15 .. 1440";
               }
             }
           }
         }
         container profile12 {
           description "Profile 12";
           leaf timeout {
             description "Maximum duration for a context";
             units "minutes";
             type union {
               type string {
                 pattern "<.*>|$.*";
               }
               type uint32 {
                 range "15 .. 1440";
               }
             }
           }
         }
         container profile13 {
           description "Profile 13";
           leaf timeout {
             description "Maximum duration for a context";
             units "minutes";
             type union {
               type string {
                 pattern "<.*>|$.*";
               }
               type uint32 {
                 range "15 .. 1440";
               }
             }
           }
         }
         container profile14 {
           description "Profile 14";
           leaf timeout {
             description "Maximum duration for a context";
             units "minutes";
             type union {
               type string {
                 pattern "<.*>|$.*";
               }
               type uint32 {
                 range "15 .. 1440";
               }
             }
           }
         }
         container profile15 {
           description "Profile 15";
           leaf timeout {
             description "Maximum duration for a context";
             units "minutes";
             type union {
               type string {
                 pattern "<.*>|$.*";
               }
               type uint32 {
                 range "15 .. 1440";
               }
             }
           }
         }
         leaf no-supervision {
           description "Don't allow session supervision based on charging profile";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container default {
         description "Default timeout settings";
         uses apply-advanced;
         leaf timeout {
           description "Maximum duration for a context";
           units "minutes";
           type union {
             type string {
               pattern "<.*>|$.*";
             }
             type uint32 {
               range "15 .. 1440";
             }
           }
         }
         leaf no-supervision {
           description "Don't allow default session supervision";
           type empty;
         }
         leaf measurement-type {
           description "Point of reference for time measurement";
           default "since-update";
           type enumeration {
             enum "since-creation" {
               description "Relative to the PDP context creation time";
             }
             enum "since-update" {
               description "Relative to the last PDP context update time";
             }
           }
         }
       }
     }
   }
   grouping session_management_type {
     uses apply-advanced;
     leaf dedicated-signaling-pdp {
       description "Enable session management for dedicated signaling PDP context";
       type empty;
     }
     container idle-timeout {
       description "Idle timeout settings";
       uses apply-advanced;
       container radius {
         description "Timeout settings based on RADIUS";
         uses apply-advanced;
         leaf use-timeout {
           description "Use idle timeout received from RADIUS";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container sgsn-plmn-id {
         description "Timeout settings based on SGSN PLMN IDs";
         uses apply-advanced;
         list plmn {
           key name;
           description "Timeout settings based on SGSN PLMN";
           uses sgsn_plmn_id_idle_timeout_type;
         }
       }
       container roaming {
         description "Timeout settings based on roaming";
         uses apply-advanced;
         leaf timeout {
           description "Maximum consecutive idle minutes for a context";
           units "minutes";
           type union {
             type string {
               pattern "<.*>|$.*";
             }
             type uint32 {
               range "1 .. 525600";
             }
           }
         }
         leaf measurement-type {
           description "Point of reference for time measurement";
           default "since-update";
           type enumeration {
             enum "since-creation" {
               description "Relative to the PDP context creation time";
             }
             enum "since-update" {
               description "Relative to the last PDP context update time";
             }
           }
         }
       }
       container charging-profile {
         description "Timeout settings based on charging profile";
         uses apply-advanced;
         container profile0 {
           description "Profile 0";
           leaf timeout {
             description "Maximum consecutive idle minutes for a context";
             units "minutes";
             type union {
               type string {
                 pattern "<.*>|$.*";
               }
               type uint32 {
                 range "1 .. 525600";
               }
             }
           }
         }
         container profile1 {
           description "Profile 1";
           leaf timeout {
             description "Maximum consecutive idle minutes for a context";
             units "minutes";
             type union {
               type string {
                 pattern "<.*>|$.*";
               }
               type uint32 {
                 range "1 .. 525600";
               }
             }
           }
         }
         container profile2 {
           description "Profile 2";
           leaf timeout {
             description "Maximum consecutive idle minutes for a context";
             units "minutes";
             type union {
               type string {
                 pattern "<.*>|$.*";
               }
               type uint32 {
                 range "1 .. 525600";
               }
             }
           }
         }
         container profile3 {
           description "Profile 3";
           leaf timeout {
             description "Maximum consecutive idle minutes for a context";
             units "minutes";
             type union {
               type string {
                 pattern "<.*>|$.*";
               }
               type uint32 {
                 range "1 .. 525600";
               }
             }
           }
         }
         container profile4 {
           description "Profile 4";
           leaf timeout {
             description "Maximum consecutive idle minutes for a context";
             units "minutes";
             type union {
               type string {
                 pattern "<.*>|$.*";
               }
               type uint32 {
                 range "1 .. 525600";
               }
             }
           }
         }
         container profile5 {
           description "Profile 5";
           leaf timeout {
             description "Maximum consecutive idle minutes for a context";
             units "minutes";
             type union {
               type string {
                 pattern "<.*>|$.*";
               }
               type uint32 {
                 range "1 .. 525600";
               }
             }
           }
         }
         container profile6 {
           description "Profile 6";
           leaf timeout {
             description "Maximum consecutive idle minutes for a context";
             units "minutes";
             type union {
               type string {
                 pattern "<.*>|$.*";
               }
               type uint32 {
                 range "1 .. 525600";
               }
             }
           }
         }
         container profile7 {
           description "Profile 7";
           leaf timeout {
             description "Maximum consecutive idle minutes for a context";
             units "minutes";
             type union {
               type string {
                 pattern "<.*>|$.*";
               }
               type uint32 {
                 range "1 .. 525600";
               }
             }
           }
         }
         container profile8 {
           description "Profile 8";
           leaf timeout {
             description "Maximum consecutive idle minutes for a context";
             units "minutes";
             type union {
               type string {
                 pattern "<.*>|$.*";
               }
               type uint32 {
                 range "1 .. 525600";
               }
             }
           }
         }
         container profile9 {
           description "Profile 9";
           leaf timeout {
             description "Maximum consecutive idle minutes for a context";
             units "minutes";
             type union {
               type string {
                 pattern "<.*>|$.*";
               }
               type uint32 {
                 range "1 .. 525600";
               }
             }
           }
         }
         container profile10 {
           description "Profile 10";
           leaf timeout {
             description "Maximum consecutive idle minutes for a context";
             units "minutes";
             type union {
               type string {
                 pattern "<.*>|$.*";
               }
               type uint32 {
                 range "1 .. 525600";
               }
             }
           }
         }
         container profile11 {
           description "Profile 11";
           leaf timeout {
             description "Maximum consecutive idle minutes for a context";
             units "minutes";
             type union {
               type string {
                 pattern "<.*>|$.*";
               }
               type uint32 {
                 range "1 .. 525600";
               }
             }
           }
         }
         container profile12 {
           description "Profile 12";
           leaf timeout {
             description "Maximum consecutive idle minutes for a context";
             units "minutes";
             type union {
               type string {
                 pattern "<.*>|$.*";
               }
               type uint32 {
                 range "1 .. 525600";
               }
             }
           }
         }
         container profile13 {
           description "Profile 13";
           leaf timeout {
             description "Maximum consecutive idle minutes for a context";
             units "minutes";
             type union {
               type string {
                 pattern "<.*>|$.*";
               }
               type uint32 {
                 range "1 .. 525600";
               }
             }
           }
         }
         container profile14 {
           description "Profile 14";
           leaf timeout {
             description "Maximum consecutive idle minutes for a context";
             units "minutes";
             type union {
               type string {
                 pattern "<.*>|$.*";
               }
               type uint32 {
                 range "1 .. 525600";
               }
             }
           }
         }
         container profile15 {
           description "Profile 15";
           leaf timeout {
             description "Maximum consecutive idle minutes for a context";
             units "minutes";
             type union {
               type string {
                 pattern "<.*>|$.*";
               }
               type uint32 {
                 range "1 .. 525600";
               }
             }
           }
         }
         leaf measurement-type {
           description "Point of reference for time measurement";
           default "since-update";
           type enumeration {
             enum "since-creation" {
               description "Relative to the PDP context creation time";
             }
             enum "since-update" {
               description "Relative to the last PDP context update time";
             }
           }
         }
       }
       container default {
         description "Default timeout settings";
         uses apply-advanced;
         leaf timeout {
           description "Maximum consecutive idle minutes for a context";
           units "minutes";
           type union {
             type string {
               pattern "<.*>|$.*";
             }
             type uint32 {
               range "1 .. 525600";
             }
           }
         }
         leaf measurement-type {
           description "Point of reference for time measurement";
           default "since-update";
           type enumeration {
             enum "since-creation" {
               description "Relative to the PDP context creation time";
             }
             enum "since-update" {
               description "Relative to the last PDP context update time";
             }
           }
         }
       }
     }
     container session-timeout {
       description "Session timeout settings";
       uses apply-advanced;
       container radius {
         description "Timeout settings based on RADIUS";
         uses apply-advanced;
         leaf use-timeout {
           description "Use session timeout received from RADIUS";
           type empty;
         }
         leaf measurement-type {
           description "Point of reference for time measurement";
           default "since-update";
           type enumeration {
             enum "since-creation" {
               description "Relative to the PDP context creation time";
             }
             enum "since-update" {
               description "Relative to the last PDP context update time";
             }
           }
         }
       }
       container sgsn-plmn-id {
         description "Timeout settings based on SGSN PLMN IDs";
         uses apply-advanced;
         list plmn {
           key name;
           description "Timeout settings based on SGSN PLMN";
           uses sgsn_plmn_id_session_timeout_type;
         }
       }
       container roaming {
         description "Timeout settings based on SGSN PLMN IDs";
         uses apply-advanced;
         leaf timeout {
           description "Maximum duration for a context";
           units "minutes";
           type union {
             type string {
               pattern "<.*>|$.*";
             }
             type uint32 {
               range "15 .. 1440";
             }
           }
         }
         leaf measurement-type {
           description "Point of reference for time measurement";
           default "since-update";
           type enumeration {
             enum "since-creation" {
               description "Relative to the PDP context creation time";
             }
             enum "since-update" {
               description "Relative to the last PDP context update time";
             }
           }
         }
       }
       container charging-profile {
         description "Timeout settings based on charging profile";
         uses apply-advanced;
         container profile0 {
           description "Profile 0";
           leaf timeout {
             description "Maximum duration for a context";
             units "minutes";
             type union {
               type string {
                 pattern "<.*>|$.*";
               }
               type uint32 {
                 range "15 .. 1440";
               }
             }
           }
         }
         container profile1 {
           description "Profile 1";
           leaf timeout {
             description "Maximum duration for a context";
             units "minutes";
             type union {
               type string {
                 pattern "<.*>|$.*";
               }
               type uint32 {
                 range "15 .. 1440";
               }
             }
           }
         }
         container profile2 {
           description "Profile 2";
           leaf timeout {
             description "Maximum duration for a context";
             units "minutes";
             type union {
               type string {
                 pattern "<.*>|$.*";
               }
               type uint32 {
                 range "15 .. 1440";
               }
             }
           }
         }
         container profile3 {
           description "Profile 3";
           leaf timeout {
             description "Maximum duration for a context";
             units "minutes";
             type union {
               type string {
                 pattern "<.*>|$.*";
               }
               type uint32 {
                 range "15 .. 1440";
               }
             }
           }
         }
         container profile4 {
           description "Profile 4";
           leaf timeout {
             description "Maximum duration for a context";
             units "minutes";
             type union {
               type string {
                 pattern "<.*>|$.*";
               }
               type uint32 {
                 range "15 .. 1440";
               }
             }
           }
         }
         container profile5 {
           description "Profile 5";
           leaf timeout {
             description "Maximum duration for a context";
             units "minutes";
             type union {
               type string {
                 pattern "<.*>|$.*";
               }
               type uint32 {
                 range "15 .. 1440";
               }
             }
           }
         }
         container profile6 {
           description "Profile 6";
           leaf timeout {
             description "Maximum duration for a context";
             units "minutes";
             type union {
               type string {
                 pattern "<.*>|$.*";
               }
               type uint32 {
                 range "15 .. 1440";
               }
             }
           }
         }
         container profile7 {
           description "Profile 7";
           leaf timeout {
             description "Maximum duration for a context";
             units "minutes";
             type union {
               type string {
                 pattern "<.*>|$.*";
               }
               type uint32 {
                 range "15 .. 1440";
               }
             }
           }
         }
         container profile8 {
           description "Profile 8";
           leaf timeout {
             description "Maximum duration for a context";
             units "minutes";
             type union {
               type string {
                 pattern "<.*>|$.*";
               }
               type uint32 {
                 range "15 .. 1440";
               }
             }
           }
         }
         container profile9 {
           description "Profile 9";
           leaf timeout {
             description "Maximum duration for a context";
             units "minutes";
             type union {
               type string {
                 pattern "<.*>|$.*";
               }
               type uint32 {
                 range "15 .. 1440";
               }
             }
           }
         }
         container profile10 {
           description "Profile 10";
           leaf timeout {
             description "Maximum duration for a context";
             units "minutes";
             type union {
               type string {
                 pattern "<.*>|$.*";
               }
               type uint32 {
                 range "15 .. 1440";
               }
             }
           }
         }
         container profile11 {
           description "Profile 11";
           leaf timeout {
             description "Maximum duration for a context";
             units "minutes";
             type union {
               type string {
                 pattern "<.*>|$.*";
               }
               type uint32 {
                 range "15 .. 1440";
               }
             }
           }
         }
         container profile12 {
           description "Profile 12";
           leaf timeout {
             description "Maximum duration for a context";
             units "minutes";
             type union {
               type string {
                 pattern "<.*>|$.*";
               }
               type uint32 {
                 range "15 .. 1440";
               }
             }
           }
         }
         container profile13 {
           description "Profile 13";
           leaf timeout {
             description "Maximum duration for a context";
             units "minutes";
             type union {
               type string {
                 pattern "<.*>|$.*";
               }
               type uint32 {
                 range "15 .. 1440";
               }
             }
           }
         }
         container profile14 {
           description "Profile 14";
           leaf timeout {
             description "Maximum duration for a context";
             units "minutes";
             type union {
               type string {
                 pattern "<.*>|$.*";
               }
               type uint32 {
                 range "15 .. 1440";
               }
             }
           }
         }
         container profile15 {
           description "Profile 15";
           leaf timeout {
             description "Maximum duration for a context";
             units "minutes";
             type union {
               type string {
                 pattern "<.*>|$.*";
               }
               type uint32 {
                 range "15 .. 1440";
               }
             }
           }
         }
         leaf measurement-type {
           description "Point of reference for time measurement";
           default "since-update";
           type enumeration {
             enum "since-creation" {
               description "Relative to the PDP context creation time";
             }
             enum "since-update" {
               description "Relative to the last PDP context update time";
             }
           }
         }
       }
       container default {
         description "Default timeout settings";
         uses apply-advanced;
         leaf timeout {
           description "Maximum duration for a context";
           units "minutes";
           type union {
             type string {
               pattern "<.*>|$.*";
             }
             type uint32 {
               range "15 .. 1440";
             }
           }
         }
         leaf measurement-type {
           description "Point of reference for time measurement";
           default "since-update";
           type enumeration {
             enum "since-creation" {
               description "Relative to the PDP context creation time";
             }
             enum "since-update" {
               description "Relative to the last PDP context update time";
             }
           }
         }
       }
     }
   }
   grouping sfw_addr_object {
     leaf name {
       description "Match IP address";
       type string;
     }
     leaf except {
       description "Match address not in this prefix";
       type empty;
     }
   }
   grouping sfw_match_object {
     uses apply-advanced;
     list source-address {
       key name;
       ordered-by user;
       description "Match IP source address";
       uses sfw_addr_object;
     }
     list destination-address {
       key name;
       ordered-by user;
       description "Match IP destination address";
       uses sfw_addr_object;
     }
     container destination-port {
       presence "enable destination-port";
       uses apply-advanced;
       choice port_choice {
         case case_1 {
           container range {
             description "Range of ports";
             leaf low {
               description "Lower limit of port range";
               type union {
                 type string {
                   pattern "<.*>|$.*";
                 }
                 type uint16 {
                   range "1 .. 65535";
                 }
               }
             }
             leaf high {
               description "Upper limit of port range";
               type union {
                 type string {
                   pattern "<.*>|$.*";
                 }
                 type uint16 {
                   range "1 .. 65535";
                 }
               }
             }
           }
         }
       }
     }
     list source-address-range {
       key "low high";
       ordered-by user;
       description "Match IP source address range";
       leaf low {
         description "Lower limit of address range";
         type jt:ipaddr;
       }
       leaf high {
         description "Upper limit of address range";
         type jt:ipaddr;
       }
       leaf except {
         description "Match address not in this prefix";
         type empty;
       }
     }
     list source-prefix-list {
       key name;
       ordered-by user;
       description "One or more named lists of source prefixes to match";
       leaf name {
         description "Name of prefix list to match against";
         type string;
       }
       leaf except {
         description "Name of prefix list not to match against";
         type empty;
       }
     }
     list destination-address-range {
       key "low high";
       ordered-by user;
       description "Match IP destination address range";
       leaf low {
         description "Lower limit of address range";
         type jt:ipaddr;
       }
       leaf high {
         description "Upper limit of address range";
         type jt:ipaddr;
       }
       leaf except {
         description "Match address not in this prefix";
         type empty;
       }
     }
     list destination-prefix-list {
       key name;
       ordered-by user;
       description "One or more named lists of destination prefixes to match";
       leaf name {
         description "Name of prefix list to match against";
         type string;
       }
       leaf except {
         description "Name of prefix list not to match against";
         type empty;
       }
     }
     leaf-list applications {
       ordered-by user;
       description "Match one or more applications";
       type string;
     }
     list application-sets {
       key name;
       ordered-by user;
       description "Match one or more application sets";
       leaf name {
         type string {
           length "1 .. 63";
         }
       }
       uses apply-advanced;
     }
     leaf-list application {
       ordered-by user;
       type string;
     }
   }
   grouping sfw_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
         enum "input-output" {
           description "Match on input to or output from interface";
         }
       }
     }
     list term {
       key name;
       ordered-by user;
       description "Define a stateful firewall term";
       leaf name {
         description "Term name";
         type string {
           length "1 .. 63";
         }
       }
       uses apply-advanced;
       container from {
         description "Define match criteria";
         uses sfw_match_object;
       }
       container then {
         description "Action to take if the 'from' condition is matched";
         uses apply-advanced;
         choice designation {
           case case_1 {
             leaf accept {
               description "Accept the packet";
               type empty;
             }
           }
           case case_2 {
             container discard {
               presence "enable discard";
               description "Discard the packet";
               uses apply-advanced;
             }
           }
           case case_3 {
             leaf reject {
               description "Reject the packet";
               type empty;
             }
           }
         }
         leaf-list allow-ip-options {
           ordered-by user;
           type string;
         }
         leaf syslog {
           description "System log information about the packet";
           type empty;
         }
         leaf skip-ids {
           description "No IDS processing will be done on a matching packet";
           type empty;
         }
       }
     }
   }
   grouping sgsn_address_type {
     leaf name {
       description "SGSN address or address prefix";
       type jt:ipv4prefix;
     }
     leaf rat-type {
       description "SGSN radio access type (RAT)";
       type enumeration {
         enum "utran" {
           description "WCDMA/UMTS Terrestrial radio access network";
         }
         enum "geran" {
           description "GSM/EDGE radio access network";
         }
         enum "wlan" {
           description "Wireless local area network";
         }
       }
     }
   }
   grouping sgsn_plmn_id_idle_timeout_type {
     leaf name {
       description "Public Land Mobile Network name";
       type string {
         length "1 .. 20";
       }
     }
     uses apply-advanced;
     list plmn-id {
       key name;
       description "PLMN ID of the SGSN";
       leaf name {
         description "SGSN Public Land Mobile Network identifier";
         type string;
       }
       uses apply-advanced;
       leaf timeout {
         description "Maximum continuous idle time for a context";
         units "minutes";
         type union {
           type string {
             pattern "<.*>|$.*";
           }
           type uint32 {
             range "1 .. 525600";
           }
         }
       }
       leaf measurement-type {
         description "Point of reference for time measurement";
         default "since-update";
         type enumeration {
           enum "since-creation" {
             description "Relative to the PDP context creation time";
           }
           enum "since-update" {
             description "Relative to the last PDP context update time";
           }
         }
       }
     }
   }
   grouping sgsn_plmn_id_session_timeout_type {
     leaf name {
       description "Public Land Mobile Network name";
       type string {
         length "1 .. 20";
       }
     }
     uses apply-advanced;
     list plmn-id {
       key name;
       description "PLMN ID of the SGSN";
       leaf name {
         description "SGSN Public Land Mobile Network identifier";
         type string;
       }
       uses apply-advanced;
       leaf timeout {
         description "Maximum duration for a context";
         units "minutes";
         type union {
           type string {
             pattern "<.*>|$.*";
           }
           type uint32 {
             range "15 .. 1440";
           }
         }
       }
       leaf measurement-type {
         description "Point of reference for time measurement";
         default "since-update";
         type enumeration {
           enum "since-creation" {
             description "Relative to the PDP context creation time";
           }
           enum "since-update" {
             description "Relative to the last PDP context update time";
           }
         }
       }
     }
   }
   grouping sgsn_type {
     leaf name {
       description "SGSN address or address prefix";
       type jt:ipv4prefix;
     }
     uses apply-advanced;
     leaf home-plmn {
       description "SGSN is within the home PLMN";
       type empty;
     }
     container gtp {
       description "GTP configuration";
       uses apply-advanced;
       leaf no-path-management {
         description "SGSN does not support GTP path management";
         type empty;
       }
     }
   }
   grouping si-ip-address-list-object {
     leaf name {
       description "Name of ip-address list";
       type string {
         length "1 .. 64";
       }
     }
     uses apply-advanced;
     leaf-list ipv4 {
       ordered-by user;
       description "List of ipv4 addresses";
       type jt:ipv4addr;
     }
     leaf-list ipv6 {
       ordered-by user;
       description "List of ipv6 addresses";
       type jt:ipv6addr;
     }
   }
   grouping sid_dns_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_dns_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
       }
     }
   }
   grouping sid_dns_match_object {
     uses apply-advanced;
     container dns {
       presence "enable dns";
       description "Match DNS sessions";
       uses apply-advanced;
       container query-name {
         description "Match query name";
         uses apply-advanced;
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
       container answer-name {
         presence "enable answer-name";
         description "Match answer name";
         uses apply-advanced;
         leaf case {
           description "Consider case while processing";
           type empty;
         }
         leaf-list contains {
           ordered-by user;
           description "Matches a substring";
           type string {
             length "1 .. 256";
           }
         }
         leaf-list not-contains {
           ordered-by user;
           description "Doesn't match a substring";
           type string {
             length "1 .. 256";
           }
         }
       }
     }
   }
   grouping sid_ftp_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_ftp_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_ftp_match_object {
     uses apply-advanced;
     container ftp {
       presence "enable ftp";
       description "Match FTP sessions";
       uses apply-advanced;
       container filename {
         presence "enable filename";
         description "Match filename";
         uses apply-advanced;
         leaf case {
           description "Consider case while processing";
           type empty;
         }
         leaf-list contains {
           ordered-by user;
           description "Matches a substring";
           type string {
             length "1 .. 256";
           }
         }
         leaf-list not-contains {
           ordered-by user;
           description "Doesn't match a substring";
           type string {
             length "1 .. 256";
           }
         }
       }
       container operation {
         description "Limit match to operation being performed";
         uses apply-advanced;
         leaf retrieve {
           description "Apply rule for RETR operation";
           type empty;
         }
         leaf store {
           description "Apply rule for STORE operation";
           type empty;
         }
       }
     }
   }
   grouping sid_header_rule_object {
     leaf name {
       description "Rule name";
       type string {
         length "1 .. 63";
       }
     }
     uses apply-advanced;
     leaf flow-direction {
       description "Restrict matching of flows by initiation";
       status deprecated;
       type enumeration {
         enum "uplink-initiated" {
           description "Match flows initiated in the uplink direction";
           status deprecated;
         }
         enum "downlink-initiated" {
           description "Match flows initiated in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         uses sid_header_match_object;
       }
       container then {
         description "Action to take if the 'from' condition is matched";
         uses apply-advanced;
         container service-id {
           description "Override service ID";
           uses apply-advanced;
           leaf payload {
             description "Identifier for payload bytes";
             type union {
               type string {
                 pattern "<.*>|$.*";
               }
               type uint32 {
                 range "0 .. 4294967295";
               }
             }
           }
           leaf retransmit {
             description "Identifier for restransmited bytes";
             status deprecated;
             type union {
               type string {
                 pattern "<.*>|$.*";
               }
               type uint32 {
                 range "0 .. 4294967295";
               }
             }
           }
           leaf retransmit-classification {
             status deprecated;
             type empty;
           }
         }
         container protocol-inspection {
           description "Protocol inspection settings for flow";
           uses apply-advanced;
           choice rule_set {
             case case_1 {
               leaf http-wsp-rule-set {
                 description "Apply a HTTS/WSP rule set for transactions";
                 type string {
                 }
               }
             }
             case case_2 {
               leaf smtp-rule-set {
                 description "Apply an SMTP rule set for transactions";
                 type string {
                 }
               }
             }
             case case_3 {
               leaf pop3-rule-set {
                 description "Apply a POP3 rule set for transactions";
                 type string {
                 }
               }
             }
             case case_4 {
               leaf ftp-rule-set {
                 description "Apply an FTP rule set for transactions";
                 type string {
                 }
               }
             }
             case case_5 {
               leaf tftp-rule-set {
                 description "Apply an TFTP rule set for transactions";
                 type string {
                 }
               }
             }
             case case_6 {
               leaf rtsp-rule-set {
                 description "Apply an FTP rule set for transactions";
                 type string {
                 }
               }
             }
             case case_7 {
               leaf sip-rule-set {
                 description "Apply an FTP rule set for transactions";
                 type string {
                 }
               }
             }
             case case_8 {
               leaf msn-rule-set {
                 description "Apply an MSN rule set for transactions";
                 type string {
                 }
               }
             }
             case case_9 {
               leaf dns-rule-set {
                 description "Apply a DNS rule set for transactions";
                 type string {
                 }
               }
             }
           }
         }
         leaf redirect-unauthorized {
           description "Redirect the flow if not authorized";
           type empty;
         }
       }
     }
   }
   grouping sid_header_match_object {
     uses apply-advanced;
     leaf-list ms-prefix {
       ordered-by user;
       description "Match MS prefix";
       type jt:ipv4prefix;
       max-elements 10;
     }
     leaf-list ms-address {
       ordered-by user;
       description "Match MS address";
       type jt:ipv4addr;
       max-elements 10;
     }
     leaf-list network-prefix {
       ordered-by user;
       description "Match network prefix";
       type jt:ipv4prefix;
       max-elements 10;
     }
     leaf-list network-address {
       ordered-by user;
       description "Match network address";
       type jt:ipv4addr;
       max-elements 10;
     }
     leaf-list network-port {
       ordered-by user;
       description "Match network port";
       type string;
       max-elements 10;
     }
     leaf-list ms-port {
       ordered-by user;
       description "Match MS port";
       type string;
       max-elements 10;
     }
     leaf-list protocol {
       ordered-by user;
       description "Match protocol type";
       type string;
       max-elements 8;
     }
   }
   grouping sid_heuristic_rule_object {
     leaf name {
       description "Rule name";
       type string {
         length "1 .. 63";
       }
     }
     uses apply-advanced;
     list term {
       key name;
       ordered-by user;
       description "Define a service identification term";
       max-elements 128;
       leaf name {
         description "Term name";
         type string {
           length "1 .. 63";
         }
       }
       uses apply-advanced;
       container from {
         description "Define match criteria";
         presence "enable from";
         uses sid_heuristic_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
       }
     }
   }
   grouping sid_heuristic_match_object {
     uses apply-advanced;
     list protocol {
       key name;
       ordered-by user;
       description "Match protocol sessions";
       max-elements 1;
       leaf name {
         type string;
       }
       uses apply-advanced;
     }
   }
   grouping sid_http_wsp_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_http_wsp_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf redirect-unauthorized {
           description "Redirect the flow if not authorized";
           type empty;
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_http_wsp_match_object {
     uses apply-advanced;
     container uri {
       description "Match URI settings";
       uses apply-advanced;
       container include-uri-handling {
         presence "enable include-uri-handling";
         uses apply-advanced;
         leaf case {
           description "Consider case while processing";
           type empty;
         }
       }
       leaf is {
         description "Exact match";
         type string {
           length "1 .. 256";
         }
       }
       leaf-list not-is {
         ordered-by user;
         description "Exclude exact match";
         type string {
           length "1 .. 256";
         }
       }
       leaf starts-with {
         description "Beginning matches";
         type string {
           length "1 .. 256";
         }
       }
       leaf-list not-starts-with {
         ordered-by user;
         description "Beginning doesn't match";
         type string {
           length "1 .. 256";
         }
       }
       leaf ends-with {
         description "End matches";
         type string {
           length "1 .. 256";
         }
       }
       leaf-list not-ends-with {
         ordered-by user;
         description "End doesn't match";
         type string {
           length "1 .. 256";
         }
       }
       leaf-list contains {
         ordered-by user;
         description "Matches a substring";
         type string {
           length "1 .. 256";
         }
       }
       leaf-list not-contains {
         ordered-by user;
         description "Doesn't match a substring";
         type string {
           length "1 .. 256";
         }
       }
       leaf-list matches {
         ordered-by user;
         description "Regular expression for match";
         status deprecated;
         type string {
           length "1 .. 256";
         }
       }
     }
     container http {
       presence "enable http";
       description "Match HTTP sessions";
       uses apply-advanced;
       container operation {
         description "Limit match to operation being performed";
         uses apply-advanced;
         leaf delete {
           description "Apply rule for delete";
           type empty;
         }
         leaf get {
           description "Apply rule for get";
           type empty;
         }
         leaf head {
           description "Apply rule for head";
           type empty;
         }
         leaf options {
           description "Apply rule for options";
           type empty;
         }
         leaf post {
           description "Apply rule for post";
           type empty;
         }
         leaf put {
           description "Apply rule for put";
           type empty;
         }
         leaf trace {
           description "Apply rule for trace";
           type empty;
         }
         leaf connect {
           description "Apply rule for connect";
           type empty;
         }
       }
       container header {
         description "HTTP header options";
         uses apply-advanced;
         container host {
           description "HTTP 'host' header settings";
           uses apply-advanced;
           leaf is {
             description "Exact match";
             type string {
               length "1 .. 256";
             }
           }
           leaf-list not-is {
             ordered-by user;
             description "Exclude exact match";
             type string {
               length "1 .. 256";
             }
           }
           leaf starts-with {
             description "Beginning matches";
             type string {
               length "1 .. 256";
             }
           }
           leaf-list not-starts-with {
             ordered-by user;
             description "Beginning doesn't match";
             type string {
               length "1 .. 256";
             }
           }
           leaf ends-with {
             description "End matches";
             type string {
               length "1 .. 256";
             }
           }
           leaf-list not-ends-with {
             ordered-by user;
             description "End doesn't match";
             type string {
               length "1 .. 256";
             }
           }
           leaf-list contains {
             ordered-by user;
             description "Matches a substring";
             type string {
               length "1 .. 256";
             }
           }
           leaf-list not-contains {
             ordered-by user;
             description "Doesn't match a substring";
             type string {
               length "1 .. 256";
             }
           }
           leaf-list matches {
             ordered-by user;
             description "Regular expression for match";
             status deprecated;
             type string {
               length "1 .. 256";
             }
           }
           leaf case {
             description "Consider case while processing";
             type empty;
           }
         }
       }
       container content-type {
         description "Content type contained in http body";
         uses apply-advanced;
         leaf case {
           description "Consider case while processing";
           type empty;
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
     }
     container wsp {
       presence "enable wsp";
       description "Match WSP sessions";
       uses apply-advanced;
       container operation {
         description "Limit match to operation being performed";
         uses apply-advanced;
         leaf delete {
           description "Apply rule for delete";
           type empty;
         }
         leaf get {
           description "Apply rule for get";
           type empty;
         }
         leaf head {
           description "Apply rule for head";
           type empty;
         }
         leaf options {
           description "Apply rule for options";
           type empty;
         }
         leaf post {
           description "Apply rule for post";
           type empty;
         }
         leaf put {
           description "Apply rule for put";
           type empty;
         }
         leaf trace {
           description "Apply rule for trace";
           type empty;
         }
         leaf connect {
           description "Apply rule for connect";
           type empty;
         }
       }
       container content-type {
         description "Content type contained in wsp body";
         uses apply-advanced;
         leaf case {
           description "Consider case while processing";
           type empty;
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
     }
     container mms {
       presence "enable mms";
       description "Match MMS sessions";
       uses apply-advanced;
       container mms-send {
         presence "enable mms-send";
         description "Settings for send operation";
         uses apply-advanced;
         container any-mms-destination {
           presence "enable any-mms-destination";
           description "Criteria for destinations";
           uses apply-advanced;
           leaf case {
             description "Consider case while processing";
             type empty;
           }
           leaf-list contains {
             ordered-by user;
             description "Matches a substring";
             type string {
               length "1 .. 256";
             }
           }
           leaf-list not-contains {
             ordered-by user;
             description "Doesn't match a substring";
             type string {
               length "1 .. 256";
             }
           }
         }
       }
       container mms-retrieve {
         presence "enable mms-retrieve";
         description "Settings for retrieve operation";
         uses apply-advanced;
         container mm-origin {
           presence "enable mm-origin";
           description "Originator of MMS";
           uses apply-advanced;
           leaf case {
             description "Consider case while processing";
             type empty;
           }
           leaf is {
             description "Exact match";
             type string {
               length "1 .. 256";
             }
           }
           leaf-list not-is {
             ordered-by user;
             description "Exclude exact match";
             type string {
               length "1 .. 256";
             }
           }
           leaf starts-with {
             description "Beginning matches";
             type string {
               length "1 .. 256";
             }
           }
           leaf-list not-starts-with {
             ordered-by user;
             description "Beginning doesn't match";
             type string {
               length "1 .. 256";
             }
           }
           leaf ends-with {
             description "End matches";
             type string {
               length "1 .. 256";
             }
           }
           leaf-list not-ends-with {
             ordered-by user;
             description "End doesn't match";
             type string {
               length "1 .. 256";
             }
           }
           leaf-list contains {
             ordered-by user;
             description "Matches a substring";
             type string {
               length "1 .. 256";
             }
           }
           leaf-list not-contains {
             ordered-by user;
             description "Doesn't match a substring";
             type string {
               length "1 .. 256";
             }
           }
           leaf-list matches {
             ordered-by user;
             description "Regular expression for match";
             status deprecated;
             type string {
               length "1 .. 256";
             }
           }
         }
       }
       leaf mms-notification {
         description "Match notification operation";
         type empty;
       }
       leaf mms-forward {
         description "Match forward operation";
         type empty;
       }
       leaf mms-acknowledge {
         description "Match acknowledge operation";
         type empty;
       }
       leaf mms-read-report {
         description "Match read-report operation";
         type empty;
       }
     }
   }
   grouping sid_msn_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_msn_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_msn_match_object {
     uses apply-advanced;
     container msn {
       presence "enable msn";
       description "Match MSN sessions";
       uses apply-advanced;
     }
   }
   grouping sid_pop3_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_pop3_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_pop3_match_object {
     uses apply-advanced;
     container pop3 {
       presence "enable pop3";
       description "Match POP3 sessions";
       uses apply-advanced;
       container user {
         presence "enable user";
         description "Match user";
         uses apply-advanced;
         leaf case {
           description "Consider case while processing";
           type empty;
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
       container operation {
         description "Limit match to operation being performed";
         uses apply-advanced;
         leaf retr {
           description "Apply rule for retr single email operation";
           type empty;
         }
         leaf top {
           description "Apply rule for get email header operation";
           type empty;
         }
         leaf list {
           description "Apply rule for list server content operation";
           type empty;
         }
       }
     }
   }
   grouping sid_rtsp_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_rtsp_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_rtsp_match_object {
     uses apply-advanced;
     container rtsp {
       presence "enable rtsp";
       description "Match RTSP sessions";
       uses apply-advanced;
       container uri {
         description "URI settings";
         uses apply-advanced;
         container include-uri-handling {
           presence "enable include-uri-handling";
           uses apply-advanced;
           leaf case {
             description "Consider case while processing";
             type empty;
           }
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
     }
   }
   grouping sid_sc_to_scid_map_type {
     leaf name {
       description "Service class identifier";
       type union {
         type string {
           pattern "<.*>|$.*";
         }
         type uint16 {
           range "1 .. 4096";
         }
       }
     }
     leaf-list service-id {
       ordered-by user;
       description "Service identifier for service class";
       type string {
         length "1 .. 9";
       }
       max-elements 1000;
     }
   }
   grouping sid_sip_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_sip_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_sip_match_object {
     uses apply-advanced;
     container sip {
       presence "enable sip";
       description "Match SIP sessions";
       uses apply-advanced;
       container request-uri {
         description "URI settings";
         uses apply-advanced;
         container include-uri-handling {
           presence "enable include-uri-handling";
           uses apply-advanced;
           leaf case {
             description "Consider case while processing";
             type empty;
           }
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
       container response-code {
         description "Response code settings";
         uses apply-advanced;
         leaf-list is {
           ordered-by user;
           description "Exact match";
           type string {
             length "1 .. 7";
           }
         }
       }
       container via {
         description "Via settings";
         uses apply-advanced;
         container include-uri-handling {
           presence "enable include-uri-handling";
           uses apply-advanced;
           leaf case {
             description "Consider case while processing";
             type empty;
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
       }
     }
   }
   grouping sid_smtp_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_smtp_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
         container activate-event-tracking {
           presence "enable activate-event-tracking";
           description "Settings for event tracking";
           uses apply-advanced;
         }
       }
     }
   }
   grouping sid_smtp_match_object {
     uses apply-advanced;
     container smtp {
       presence "enable smtp";
       description "Match SMTP sessions";
       uses apply-advanced;
       container sender {
         presence "enable sender";
         description "Match smtp sender";
         uses apply-advanced;
         leaf case {
           description "Consider case while processing";
           type empty;
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
     }
   }
   grouping sid_tftp_rule_object {
     leaf name {
       description "Rule name";
       type string {
         length "1 .. 63";
       }
     }
     uses apply-advanced;
     leaf transaction-direction {
       description "Restrict matching of URI by direction";
       status deprecated;
       type enumeration {
         enum "uplink-initiated" {
           description "Match transactions in the uplink direction";
           status deprecated;
         }
         enum "downlink-initiated" {
           description "Match transactions in the downlink direction";
           status deprecated;
         }
         enum "both" {
           description "Match all flows";
           status deprecated;
         }
       }
     }
     list term {
       key name;
       ordered-by user;
       description "Define a service identification term";
       max-elements 128;
       leaf name {
         description "Term name";
         type string {
           length "1 .. 63";
         }
       }
       uses apply-advanced;
       container from {
         description "Define match criteria";
         presence "enable from";
         uses sid_tftp_match_object;
       }
       container then {
         description "Action to take if the 'from' condition is matched";
         uses apply-advanced;
         leaf payload {
           description "Identifier for all payload";
           type union {
             type string {
               pattern "<.*>|$.*";
             }
             type uint32 {
               range "0 .. 4294967295";
             }
           }
         }
         leaf aggregated-volume {
           description "Volume type reported for aggregated charging";
           default "bearer";
           type enumeration {
             enum "bearer" {
               description "Count volume for bearer level";
             }
             enum "application" {
               description "Count volume for application level";
             }
           }
         }
       }
     }
   }
   grouping sid_tftp_match_object {
     uses apply-advanced;
     container tftp {
       presence "enable tftp";
       description "Match TFTP sessions";
       uses apply-advanced;
       container filename {
         presence "enable filename";
         description "Match filename";
         uses apply-advanced;
         leaf case {
           description "Consider case while processing";
           type empty;
         }
         leaf is {
           description "Exact match";
           type string {
             length "1 .. 256";
           }
         }
         leaf-list not-is {
           ordered-by user;
           description "Exclude exact match";
           type string {
             length "1 .. 256";
           }
         }
         leaf starts-with {
           description "Beginning matches";
           type string {
             length "1 .. 256";
           }
         }
         leaf-list not-starts-with {
           ordered-by user;
           description "Beginning doesn't match";
           type string {
             length "1 .. 256";
           }
         }
         leaf ends-with {
           description "End matches";
           type string {
             length "1 .. 256";
           }
         }
         leaf-list not-ends-with {
           ordered-by user;
           description "End doesn't match";
           type string {
             length "1 .. 256";
           }
         }
         leaf-list contains {
           ordered-by user;
           description "Matches a substring";
           type string {
             length "1 .. 256";
           }
         }
         leaf-list not-contains {
           ordered-by user;
           description "Doesn't match a substring";
           type string {
             length "1 .. 256";
           }
         }
         leaf-list matches {
           ordered-by user;
           description "Regular expression for match";
           status deprecated;
           type string {
             length "1 .. 256";
           }
         }
       }
       container operation {
         description "Limit match to operation being performed";
         uses apply-advanced;
         leaf read-request {
           description "Apply rule for read-request operation";
           type empty;
         }
         leaf write-request {
           description "Apply rule for write-request operation";
           type empty;
         }
       }
     }
   }
   grouping sid_to_rg_map_type {
     leaf name {
       description "Rating group identifier";
       type union {
         type string {
           pattern "<.*>|$.*";
         }
         type uint32 {
           range "1 .. 4294967295";
         }
       }
     }
     leaf-list service-id {
       ordered-by user;
       description "Service identifier for rating group";
       type string {
         length "1 .. 21";
       }
       max-elements 512;
     }
   }
   grouping signaling-realm {
     description "Signaling realm";
     leaf name {
       description "Realm name";
       type string;
     }
     uses apply-advanced;
   }
   grouping sip_timers_type {
     uses apply-advanced;
     leaf inactive-call {
       description "Maximum time for signaling inactivity";
       default "86400";
       units "seconds";
       type union {
         type string {
           pattern "<.*>|$.*";
         }
         type uint32 {
           range "300 .. 86400";
         }
       }
     }
     leaf timer-c {
       description "Maximum time to wait for final response on invite";
       default "180";
       units "seconds";
       type union {
         type string {
           pattern "<.*>|$.*";
         }
         type uint32 {
           range "180 .. 300";
         }
       }
     }
   }
   grouping sm-traceoptions-type {
     description "Trace options for SAEGW SM";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing parameters";
       leaf name {
         type enumeration {
           enum "general" {
             description "Trace general events";
           }
           enum "state-machine" {
             description "Trace state-machine events";
           }
           enum "mirroring" {
             description "Trace mirroring events";
           }
           enum "all" {
             description "Trace everything";
           }
         }
       }
     }
   }
   grouping soft_gre_tunnel_group_object {
     leaf name {
       description "Tunnel group name";
       type string {
       }
     }
     uses apply-advanced;
     leaf source-address {
       description "Local address of tunnel";
       type jt:ipaddr;
     }
     list destination-networks {
       key name;
       ordered-by user;
       description "Create tunnels for routes in these destination networks";
       uses soft_gre_destination_network_object;
     }
     leaf service-interface {
       description "Pseudowire interface to use";
       type union {
         type jt:interface-unit;
         type string {
           pattern "<.*>|$.*";
         }
       }
     }
     leaf tunnel-idle-timeout {
       description "Time to tear down tunnel when idle";
       default "120";
       units "seconds";
       type union {
         type uint16;
         type string {
           pattern "<.*>|$.*";
         }
       }
     }
     leaf dynamic-profile {
       description "Dynamic profile for tunnel interface";
       type string {
         length "1 .. 80";
       }
     }
   }
   grouping soft_gre_destination_network_object {
     leaf name {
       description "Network prefix";
       type jt:ipprefix;
     }
     uses apply-advanced;
   }
   grouping srd-rs-id-object {
     description "Definition of redundancy-set";
     leaf name {
       description "Redundancy set identifier";
       type union {
         type string {
           pattern "<.*>|$.*";
         }
         type uint32 {
           range "1 .. 100";
         }
       }
     }
     uses apply-advanced;
     leaf redundancy-group {
       description "Name of redundancy-group";
       type union {
         type string {
           pattern "<.*>|$.*";
         }
         type uint32 {
           range "1 .. 16";
         }
       }
     }
     leaf-list redundancy-policy {
       description "Redundancy-policy list";
       type string;
     }
     leaf keepalive {
       description "Frequency of SRD hello messages";
       default "10";
       units "seconds";
       type union {
         type string {
           pattern "<.*>|$.*";
         }
         type uint32 {
           range "1 .. 60";
         }
       }
     }
     leaf hold-time {
       description "Time before SRD peer is declared down";
       default "30";
       units "seconds";
       type union {
         type string {
           pattern "<.*>|$.*";
         }
         type uint32 {
           range "0 .. 3600";
         }
       }
     }
     leaf healthcheck-timer-interval {
       description "Healthcheck timer interval";
       default "5";
       units "seconds";
       type union {
         type string {
           pattern "<.*>|$.*";
         }
         type uint32 {
           range "1 .. 3600";
         }
       }
     }
   }
   grouping srd-traceoptions-object {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "config" {
             description "Trace parse events";
           }
           enum "connect" {
             description "Trace ipc events";
           }
           enum "route" {
             description "Trace route events";
           }
           enum "ssd" {
             description "Trace SDK Service events";
           }
           enum "snmp" {
             description "Trace snmp events";
           }
           enum "system" {
             description "Trace services redundancy system events";
           }
           enum "opcmd" {
             description "Trace operational command events";
           }
           enum "state-machine" {
             description "Trace finite-state-machine events";
           }
           enum "kcom" {
             description "Trace KCOM events";
           }
           enum "database" {
             description "Trace database events";
           }
           enum "swithover" {
             description "Trace switchover events";
           }
           enum "stateful-sync" {
             description "Trace stateful-sync related events";
           }
           enum "redundancy-group" {
             description "Trace redundancy-group related events";
           }
           enum "all" {
             description "Trace everything";
           }
         }
       }
     }
   }
   grouping ssl-initiation-config {
     uses apply-advanced;
     list profile {
       key name;
       ordered-by user;
       description "SSL client profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf-list trusted-ca {
         ordered-by user;
         description "List of trusted certificate authority profiles";
         type string;
         max-elements 1024;
       }
       container crypto-hardware-offload {
         presence "enable crypto-hardware-offload";
         description "Config related to crypto hardware offload";
         uses apply-advanced;
         leaf tpm {
           description "Enable TPM hardware offload";
           type empty;
         }
       }
       leaf client-certificate {
         description "Local certificate identifier";
         type string {
         }
       }
       container actions {
         description "Traffic related actions";
         uses apply-advanced;
         leaf ignore-server-auth-failure {
           description "Ignore server authentication failure";
           type empty;
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
       }
     }
   }
   grouping ssl-proxy-config {
     uses apply-advanced;
     container global-config {
       description "Global proxy configuration";
       uses apply-advanced;
       leaf session-cache-timeout {
         description "Session cache timeout";
         units "seconds";
         type union {
           type string {
             pattern "<.*>|$.*";
           }
           type uint32 {
             range "300 .. 86400";
           }
         }
       }
       leaf disable-cert-cache {
         description "Disable proxy mode certificate cache";
         type empty;
       }
       leaf certificate-cache-timeout {
         description "Certificate cache timeout";
         units "seconds";
         type union {
           type string {
             pattern "<.*>|$.*";
           }
           type uint32 {
             range "300 .. 3600";
           }
         }
       }
       leaf invalidate-cache-on-crl-update {
         description "Invalidate certificate cache on crl update";
         type empty;
       }
       leaf cache-usage-enforcement-threshold {
         description "Percentage of total cache size after which per lsys limits will be enforced";
         type union {
           type string {
             pattern "<.*>|$.*";
           }
           type uint32 {
             range "1 .. 100";
           }
         }
       }
       leaf disable-deferred-profile-selection {
         description "Disable the deferred profile selection mechanism";
         type empty;
       }
       container non-ssl-detection-threshold {
         presence "enable non-ssl-detection-threshold";
         description "Thresholds that allow user to decide how long to wait for STARTTLS/AUTHTLS (EMAIL,FTP)";
         uses apply-advanced;
         leaf packet-threshold {
           description "Number of plain packets in C2S direction after which session will be ignored";
           default "5";
           type union {
             type string {
               pattern "<.*>|$.*";
             }
             type uint32 {
               range "1 .. 15";
             }
           }
         }
         leaf byte-threshold {
           description "Minimum bytes required to ignore the session";
           default "200";
           type union {
             type string {
               pattern "<.*>|$.*";
             }
             type uint32 {
               range "1 .. 600";
             }
           }
         }
       }
       container actions {
         description "Define global ssl proxy actions";
         uses apply-advanced;
       }
     }
     list profile {
       key name;
       ordered-by user;
       description "SSL Proxy profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf-list trusted-ca {
         ordered-by user;
         description "List of trusted certificate authority profiles";
         type string;
         max-elements 1024;
       }
       choice certificate {
         case case_1 {
           leaf-list root-ca {
             ordered-by user;
             description "Root certificate for interdicting server certificates in proxy mode";
             type string;
             max-elements 2;
           }
         }
         case case_2 {
         }
       }
       container mirror-decrypt-traffic {
         description "Configure mirror interface and Destination MAC address";
         uses apply-advanced;
         leaf interface {
           description "Interface on which SSL decrypted traffic is mirrored";
           type union {
             type jt:interface-name;
             type string {
               pattern "<.*>|$.*";
             }
           }
         }
         leaf destination-mac-address {
           description "Mac address of host/server to which decrypted traffic is mirrored";
           type jt:mac-addr;
         }
         leaf only-after-security-policies-enforcement {
           description "Enables decrypted Traffic mirroring after policy enforcement";
           type empty;
         }
       }
       leaf-list whitelist {
         ordered-by user;
         description "Addresses exempted from SSL Proxy ";
         type string;
       }
       leaf-list whitelist-url-categories {
         ordered-by user;
         type string;
       }
       container actions {
         description "Logging and traffic related actions";
         uses apply-advanced;
         leaf ignore-server-auth-failure {
           description "Ignore server authentication failure";
           type empty;
         }
         container log {
           presence "enable log";
           description "Logging actions";
           leaf all {
             description "Log all events";
             type empty;
           }
           leaf sessions-dropped {
             description "Log only ssl session drop events";
             type empty;
           }
           leaf sessions-allowed {
             description "Log ssl session allow events after an error";
             type empty;
           }
           leaf sessions-ignored {
             description "Log  session ignore events ";
             type empty;
           }
           leaf sessions-whitelisted {
             description "Log ssl session whitelist events ";
             type empty;
           }
           leaf errors {
             description "Log all error events ";
             type empty;
           }
           leaf warning {
             description "Log all warning events ";
             type empty;
           }
           leaf info {
             description "Log all information events ";
             type empty;
           }
         }
         container crl {
           description "Certificate Revocation actions.";
           leaf disable {
             description "Disable CRL validation.";
             type empty;
           }
           leaf if-not-present {
             description "Action if CRL information is not present.";
             default "allow";
             type enumeration {
               enum "allow" {
                 description "Allow session if CRL information is not present.";
               }
               enum "drop" {
                 description "Drop session if CRL information is not present.";
               }
             }
           }
           leaf ignore-hold-instruction-code {
             description "Ignore 'Hold Instruction Code' present in the CRL entry.";
             type empty;
           }
         }
         leaf renegotiation {
           description "Renegotiation options";
           default "allow-secure";
           type enumeration {
             enum "allow" {
               description "Allow secure as well as non secure renegotiation";
             }
             enum "allow-secure" {
               description "Allow secure negotiation only (RFC 5746)";
             }
             enum "drop" {
               description "Drop session on renegotiation request";
             }
           }
         }
         leaf disable-session-resumption {
           description "Disable session resumption";
           type empty;
         }
         leaf unsupported-cipher-on-hw {
           description "Unsupported cipher processing on hardware mode";
           default "drop";
           type enumeration {
             enum "drop" {
               description "Drop session if cipher isn't supported on hardware mode";
             }
             enum "software-inspection" {
               description "Allow session in software mode";
             }
           }
         }
         leaf allow-strong-certificate {
           description "Certificate till 4K key-size processing on standalone SRX300/SRX320 platform";
           type empty;
         }
       }
       leaf disable-deferred-profile-selection {
         description "Disable the deferred profile selection mechanism at profile level";
         type empty;
       }
     }
   }
   grouping ssl-termination-config {
     uses apply-advanced;
     list profile {
       key name;
       ordered-by user;
       description "SSL server profile";
       leaf name {
         description "Profile identifier";
         type string {
           length "1 .. 63";
         }
       }
       uses apply-advanced;
       leaf enable-flow-tracing {
         description "Enable flow tracing for the profile";
         type empty;
       }
       leaf supported-ec-groups {
         description "Supported electic curve groups";
         type enumeration {
           enum "P-256" {
             description "P-256 group";
           }
           enum "P-384" {
             description "P-384 group";
           }
           enum "P-521" {
             description "P-521 group";
           }
         }
       }
       leaf protocol-version {
         description "Protocol SSL version accepted";
         default "all";
         type enumeration {
           enum "all" {
             description "TLS version 1.0 or TLS version 1.1 or TLS version 1.2 or TLS version 1.3";
           }
           enum "ssl3" {
             description "SSL version 3";
           }
           enum "tls1" {
             description "TLS version 1";
           }
           enum "tls11" {
             description "TLS version 1.1";
           }
           enum "tls12" {
             description "TLS version 1.2";
           }
           enum "tls13" {
             description "TLS version 1.3";
           }
           enum "tls12-and-lower" {
             description "Dont support TLS 1.3 (downgrade all the connections to TLS 1.2 or below)";
           }
         }
       }
       leaf preferred-ciphers {
         description "Select preferred ciphers";
         default "medium";
         type enumeration {
           enum "strong" {
             description "Use ciphers with key strength of 168-bits or greater";
           }
           enum "medium" {
             description "Use ciphers with key strength of 128-bits or greater";
           }
           enum "weak" {
             description "Use ciphers with key strength of 40-bits or greater";
           }
           enum "custom" {
             description "Configure custom cipher suite and order of preference";
           }
         }
       }
       leaf-list custom-ciphers {
         ordered-by user;
         description "Custom cipher list";
         type enumeration {
           enum "tls12-rsa-aes-128-cbc-sha" {
             description "RSA, 128 bit aes/cbc, sha hash";
           }
           enum "tls12-rsa-aes-256-cbc-sha" {
             description "RSA, 256 bit aes/cbc, sha hash";
           }
           enum "tls12-rsa-aes-256-gcm-sha384" {
             description "RSA, 256 bit aes/gcm, sha384 hash ";
           }
           enum "tls12-rsa-aes-256-cbc-sha256" {
             description "RSA, 256 bit aes/cbc, sha256 hash";
           }
           enum "tls12-rsa-aes-128-gcm-sha256" {
             description "RSA, 128 bit aes/gcm, sha256 hash";
           }
           enum "tls12-rsa-aes-128-cbc-sha256" {
             description "RSA, 128 bit aes/cbc, sha256 hash";
           }
           enum "tls12-ecdhe-rsa-aes-256-gcm-sha384" {
             description "ECDHE/rsa, 256 bit aes/gcm, sha384 hash";
           }
           enum "tls12-ecdhe-rsa-aes-256-cbc-sha" {
             description "ECDHE/rsa, 256 bit aes/cbc, sha hash";
           }
           enum "tls12-ecdhe-rsa-aes-256-cbc-sha384" {
             description "ECDHE/rsa, 256 bit aes/cbc, sha384 hash";
           }
           enum "tls12-ecdhe-rsa-3des-ede-cbc-sha" {
             description "ECDHE/rsa, 3des ede/cbc, sha hash";
           }
           enum "tls12-ecdhe-rsa-aes-128-gcm-sha256" {
             description "ECDHE/rsa, 128 bit aes/gcm, sha256 hash";
           }
           enum "tls12-ecdhe-rsa-aes-128-cbc-sha" {
             description "ECDHE/rsa, 128 bit aes/cbc, sha hash";
           }
           enum "tls12-ecdhe-rsa-aes-128-cbc-sha256" {
             description "ECDHE/rsa, 128 bit aes/cbc, sha256 hash";
           }
           enum "tls12-rsa-aes-128-ccm-sha256" {
             description "RSA, 128 bit aes/ccm, sha256 hash";
           }
           enum "tls12-rsa-aes-128-ccm8-sha256" {
             description "RSA, 128 bit aes/ccm8, sha256 hash";
           }
           enum "tls12-rsa-aes-256-ccm-sha256" {
             description "RSA, 256 bit aes/ccm, sha256 hash";
           }
           enum "tls12-rsa-aes-256-ccm8-sha256" {
             description "RSA, 128 bit aes/ccm8, sha256 hash";
           }
           enum "tls12-ecdhe-ecdsa-aes-128-ccm-sha256" {
             description "ECDHE,ECDSA, 128 bit aes/ccm, sha256 hash";
           }
           enum "tls12-ecdhe-ecdsa-aes-256-ccm-sha256" {
             description "ECDHE,ECDSA, 256 bit aes/ccm, sha256 hash";
           }
           enum "tls12-ecdhe-ecdsa-aes-128-ccm8-sha256" {
             description "ECDHE,ECDSA, 128 bit aes/ccm8, sha256 hash";
           }
           enum "tls12-ecdhe-ecdsa-aes-256-ccm8-sha256" {
             description "ECDHE,ECDSA, 256 bit aes/ccm8, sha256 hash";
           }
           enum "tls12-ecdhe-rsa-chacha20-poly1305-sha256" {
             description "ECDHE/rsa, chacha_poly , sha256 hash";
           }
           enum "tls12-ecdhe-ecdsa-aes-256-gcm-sha384" {
             description "ECDHE,ECDSA, 256 bit aes/gcm, sha384 hash";
           }
           enum "tls12-ecdhe-ecdsa-aes-256-cbc-sha" {
             description "ECDHE,ECDSA, 256 bit aes/cbc, sha hash";
           }
           enum "tls12-ecdhe-ecdsa-aes-256-cbc-sha384" {
             description "ECDHE,ECDSA, 256 bit aes/cbc, sha384 hash";
           }
           enum "tls12-ecdhe-ecdsa-aes-128-gcm-sha256" {
             description "ECDHE,ECDSA, 128 bit aes/gcm, sha256 hash";
           }
           enum "tls12-ecdhe-ecdsa-aes-128-cbc-sha" {
             description "ECDHE,ECDSA, 128 bit aes/cbc, sha hash";
           }
           enum "tls12-ecdhe-ecdsa-aes-128-cbc-sha256" {
             description "ECDHE,ECDSA, 128 bit aes/cbc, sha256 hash";
           }
           enum "tls12-ecdhe-ecdsa-3des-ede-cbc-sha" {
             description "ECDHE,ECDSA, 3des ede/cbc, sha hash";
           }
           enum "dhe-rsa-with-aes-128-ccm8-sha256" {
             description "DHE/rsa, 128 bit aes/ccm8, sha256 hash";
           }
           enum "dhe-rsa-with-aes-256-ccm8-sha256" {
             description "DHE/rsa, 256 bit aes/ccm8, sha256 hash";
           }
           enum "dhe-rsa-with-aes-256-ccm-sha256" {
             description "DHE/rsa, 256 bit aes/ccm, sha256 hash";
           }
           enum "dhe-rsa-with-aes-128-ccm-sha256" {
             description "DHE/rsa, 128 bit aes/ccm, sha256 hash";
           }
           enum "tls12-ecdhe-ecdsa-chacha20-poly1305-sha256" {
             description "ECDHE,ECDSA, chacha_poly, sha256 hash";
           }
           enum "tls13-with-aes-256-gcm-sha384" {
             description "Any key-exchange, Any authentication,256bit aes, sha384 hash";
           }
           enum "tls13-with-aes-128-gcm-sha256" {
             description "Any key-exchange, Any authentication,128bit aes, sha256 hash";
           }
           enum "tls13-with-chacha20-poly1305-sha256" {
             description "Any key-exchange, Any authentication,chacha, sha256 hash";
           }
           enum "tls13-with-aes-128-ccm-sha256" {
             description "Any key-exchange, Any authentication,128bit aes, sha256 hash";
           }
           enum "tls13-with-aes-128-ccm8-sha256" {
             description "Any key-exchange, Any authentication,128bit aes, sha256 hash";
           }
           enum "rsa-with-rc4-128-md5" {
             description "RSA, 128bit rc4, md5 hash";
           }
           enum "rsa-with-rc4-128-sha" {
             description "RSA, 128bit rc4, sha hash";
           }
           enum "rsa-with-des-cbc-sha" {
             description "RSA, des cbc, sha hash";
           }
           enum "rsa-with-3des-ede-cbc-sha" {
             description "RSA, 3des ede/cbc, sha hash";
           }
           enum "rsa-with-aes-128-cbc-sha" {
             description "RSA, 128 bit aes/cbc, sha hash";
           }
           enum "rsa-with-aes-256-cbc-sha" {
             description "RSA, 256 bit aes/cbc, sha hash";
           }
           enum "rsa-export-with-rc4-40-md5" {
             description "RSA-export, 40 bit rc4, md5 hash";
           }
           enum "rsa-export-with-des40-cbc-sha" {
             description "RSA-export, 40 bit des/cbc, sha hash";
           }
           enum "rsa-export1024-with-des-cbc-sha" {
             description "RSA 1024 bit export, des/cbc, sha hash";
           }
           enum "rsa-export1024-with-rc4-56-md5" {
             description "RSA 1024 bit export, 56 bit rc4, md5 hash";
           }
           enum "rsa-export1024-with-rc4-56-sha" {
             description "RSA 1024 bit export, 56 bit rc4, sha hash";
           }
           enum "rsa-with-aes-256-gcm-sha384" {
             description "RSA, 256 bit aes/gcm, sha384 hash ";
           }
           enum "rsa-with-aes-256-cbc-sha256" {
             description "RSA, 256 bit aes/cbc, sha256 hash";
           }
           enum "rsa-with-aes-128-gcm-sha256" {
             description "RSA, 128 bit aes/gcm, sha256 hash";
           }
           enum "rsa-with-aes-128-cbc-sha256" {
             description "RSA, 128 bit aes/cbc, sha256 hash";
           }
           enum "ecdhe-rsa-with-aes-256-gcm-sha384" {
             description "ECDHE/rsa, 256 bit aes/gcm, sha384 hash";
           }
           enum "ecdhe-rsa-with-aes-256-cbc-sha" {
             description "ECDHE/rsa, 256 bit aes/cbc, sha hash";
           }
           enum "ecdhe-rsa-with-aes-256-cbc-sha384" {
             description "ECDHE/rsa, 256 bit aes/cbc, sha384 hash";
           }
           enum "ecdhe-rsa-with-3des-ede-cbc-sha" {
             description "ECDHE/rsa, 3des ede/cbc, sha hash";
           }
           enum "ecdhe-rsa-with-aes-128-gcm-sha256" {
             description "ECDHE/rsa, 128 bit aes/gcm, sha256 hash";
           }
           enum "ecdhe-rsa-with-aes-128-cbc-sha" {
             description "ECDHE/rsa, 128 bit aes/cbc, sha hash";
           }
           enum "ecdhe-rsa-with-aes-128-cbc-sha256" {
             description "ECDHE/rsa, 128 bit aes/cbc, sha256 hash";
           }
           enum "ecdhe-ecdsa-with-aes-256-gcm-sha384" {
             description "ECDHE,ECDSA, 256 bit aes/gcm, sha384 hash";
           }
           enum "ecdhe-ecdsa-with-aes-256-cbc-sha" {
             description "ECDHE,ECDSA, 256 bit aes/cbc, sha hash";
           }
           enum "ecdhe-ecdsa-with-aes-256-cbc-sha384" {
             description "ECDHE,ECDSA, 256 bit aes/cbc, sha384 hash";
           }
           enum "ecdhe-ecdsa-with-aes-128-gcm-sha256" {
             description "ECDHE,ECDSA, 128 bit aes/gcm, sha256 hash";
           }
           enum "ecdhe-ecdsa-with-aes-128-cbc-sha" {
             description "ECDHE,ECDSA, 128 bit aes/cbc, sha hash";
           }
           enum "ecdhe-ecdsa-with-aes-128-cbc-sha256" {
             description "ECDHE,ECDSA, 128 bit aes/cbc, sha256 hash";
           }
           enum "ecdhe-ecdsa-with-3des-ede-cbc-sha" {
             description "ECDHE,ECDSA, 3des ede/cbc, sha hash";
           }
           enum "dhe-rsa-with-aes-256-gcm-sha384" {
             description "DHE/rsa, 256 bit aes/gcm, sha384 hash";
           }
           enum "dhe-rsa-with-aes-256-cbc-sha" {
             description "DHE/rsa, 256 bit aes/cbc, sha hash";
           }
           enum "dhe-rsa-with-aes-256-cbc-sha256" {
             description "DHE/rsa, 256 bit aes/cbc, sha256 hash";
           }
           enum "dhe-rsa-with-3des-ede-cbc-sha" {
             description "DHE/rsa, 3des ede/cbc, sha hash";
           }
           enum "dhe-rsa-with-aes-128-gcm-sha256" {
             description "DHE/rsa, 128 bit aes/gcm, sha256 hash";
           }
           enum "dhe-rsa-with-aes-128-cbc-sha" {
             description "DHE/rsa, 128 bit aes/cbc, sha hash";
           }
           enum "dhe-rsa-with-aes-128-cbc-sha256" {
             description "DHE/rsa, 128 bit aes/cbc, sha256 hash";
           }
         }
         max-elements 64;
       }
       leaf enable-session-cache {
         description "Enable SSL session cache";
         type empty;
       }
       leaf-list trusted-ca {
         ordered-by user;
         description "List of trusted certificate authority profiles";
         type string;
         max-elements 1024;
       }
       leaf server-certificate {
         description "Local certificate identifier";
         type string {
         }
       }
     }
   }
   grouping ssl-traceoptions {
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "brief";
       type enumeration {
         enum "brief" {
           description "Brief debugging output";
         }
         enum "detail" {
           description "Detailed debugging output";
         }
         enum "extensive" {
           description "Extensive debugging output";
         }
         enum "verbose" {
           description "Verbose debugging output";
         }
       }
     }
     list flag {
       key name;
       ordered-by user;
       description "Tracing parameters";
       leaf name {
         type enumeration {
           enum "cli-configuration" {
             description "Trace CLI configuration events";
           }
           enum "termination" {
             description "Trace termination service events";
           }
           enum "initiation" {
             description "Trace initiation service events";
           }
           enum "proxy" {
             description "Trace proxy service events";
           }
           enum "selected-profile" {
             description "Trace events for profiles with enable-flow-tracing set";
           }
           enum "all" {
             description "Trace everything";
           }
         }
       }
     }
     container packet-filter {
       description "SSL Packet filter";
       uses apply-advanced;
       leaf source-ip {
         description "Source IP address";
         type jt:ipaddr;
       }
       leaf destination-ip {
         description "Destination IP address";
         type jt:ipaddr;
       }
       leaf source-port {
         description "Source port";
         type union {
           type string {
             pattern "<.*>|$.*";
           }
           type uint16 {
             range "1 .. 65535";
           }
         }
       }
       leaf destination-port {
         description "Destination port";
         type union {
           type string {
             pattern "<.*>|$.*";
           }
           type uint16 {
             range "1 .. 65535";
           }
         }
       }
     }
   }
   grouping svc-ike-policy {
     leaf name {
       description "Name of the IKE policy";
       type string {
         length "1 .. 32";
       }
     }
     uses apply-advanced;
     leaf description {
       description "Text description of IKE policy";
       type string {
         length "1 .. 80";
       }
     }
     leaf mode {
       description "Define the IKE first phase mode";
       type enumeration {
         enum "main" {
           description "Main mode";
         }
         enum "aggressive" {
           description "Aggressive mode";
         }
       }
     }
     leaf version {
       description "Define the IKE version to use for the negotiation";
       type enumeration {
         enum "1" {
           description "Initiate IKEv1 negotiation";
         }
         enum "2" {
           description "Initiate IKEv2 negotiation";
         }
       }
     }
     leaf-list proposals {
       ordered-by user;
       description "Name of the proposal";
       type string {
         length "1 .. 32";
       }
     }
     container local-id {
       description "Define local identification";
       choice id-type {
         case case_1 {
           leaf ipv4_addr {
             description "One or more IPv4 address identification values";
             type jt:ipv4addr;
           }
         }
         case case_2 {
           leaf distinguished-name {
             description "Use a distinguished name specified in local certificate";
             type empty;
           }
         }
         case case_3 {
           leaf fqdn {
             description "One or more fully qualified domain name values";
             type string {
               length "1 .. 255";
             }
           }
         }
         case case_4 {
           leaf key-id {
             description "One or more key ID identification values";
             type string {
               length "1 .. 255";
             }
           }
         }
         case case_5 {
           leaf ipv6-addr {
             description "One or more IPv6 address identification values";
             type jt:ipv6addr;
           }
         }
       }
     }
     leaf-list certificate-policy-oids {
       ordered-by user;
       description "Allowed certificate policy object identifiers (maximum 5)";
       type string {
         length "1 .. 63";
       }
       max-elements 5;
     }
     leaf local-certificate {
       description "Local certificate identifier";
       type string {
       }
     }
     leaf peer-certificate-type {
       description "Preferred type of certificate from peer";
       default "x509-signature";
       type enumeration {
         enum "pkcs7" {
           description "PKCS7 encoding";
         }
         enum "x509-signature" {
           description "X509 signature encoding";
         }
       }
     }
     container remote-id {
       description "Define remote identification";
       uses apply-advanced;
       leaf any-remote-id {
         description "Allow any remote ID";
         type empty;
       }
       leaf-list ipv4_addr {
         ordered-by user;
         description "One or more IPv4 address identification values";
         type jt:ipv4addr;
       }
       container distinguished-name {
         description "One or more distinguished name values";
         uses apply-advanced;
         leaf-list container {
           ordered-by user;
           description "One or more distinguished name container string";
           type string {
             length "1 .. 255";
           }
         }
         leaf-list wildcard {
           ordered-by user;
           description "One or more distinguished name wildcard string";
           type string {
             length "1 .. 255";
           }
         }
         leaf-list exact-match {
           ordered-by user;
           description "One or more distinguished name to do full length exact match";
           type string {
             length "1 .. 255";
           }
         }
       }
       leaf-list fqdn {
         ordered-by user;
         description "One or more fully qualified domain name values";
         type string {
           length "1 .. 255";
         }
       }
       leaf-list key-id {
         ordered-by user;
         description "One or more key ID identification values";
         type string {
           length "1 .. 255";
         }
       }
       leaf-list ipv6-addr {
         ordered-by user;
         description "One or more IPv6 address identification values";
         type jt:ipv6addr;
       }
     }
     container pre-shared-key {
       description "Define a preshared key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     container respond-bad-spi {
       presence "enable respond-bad-spi";
       description "Respond to IPSec packets with bad SPI values";
       leaf max-responses {
         description "Maximum number of times to respond";
         default "5";
         type union {
           type string {
             pattern "<.*>|$.*";
           }
           type uint32 {
             range "1 .. 30";
           }
         }
       }
     }
   }
   grouping sw_rule_object {
     leaf name {
       description "Rule name";
       type string {
         length "1 .. 63";
       }
     }
     uses apply-advanced;
     leaf match-direction {
       description "Direction for which the rule match is applied";
       type enumeration {
         enum "input" {
           description "Match on input to interface";
         }
         enum "output" {
           description "Match on output from interface";
         }
       }
     }
     list term {
       key name;
       ordered-by user;
       description "Define a softwire term";
       leaf name {
         description "Term name";
         type string {
           length "1 .. 63";
         }
       }
       uses apply-advanced;
       container then {
         description "Action to take if the 'from' condition is matched";
         uses apply-advanced;
         choice designation {
           case case_1 {
             leaf ds-lite {
               description "Apply DS-Lite softwire";
               type string {
                 length "1 .. 63";
               }
             }
           }
           case case_2 {
             leaf v6rd {
               description "Apply 6rd softwire";
               type string {
                 length "1 .. 63";
               }
             }
           }
           case case_3 {
             leaf map-e {
               description "Apply map-e softwire";
               type string {
                 length "1 .. 63";
               }
             }
           }
           case case_4 {
             leaf map-t {
               description "Apply map-t softwire";
               type string {
                 length "1 .. 63";
               }
             }
           }
         }
       }
     }
   }
   grouping tdir_netmon_object {
     description "Network monitoring probe configuration";
     uses apply-advanced;
     container traceoptions {
       description "Net Monitoring trace options";
       uses tdir_netmon_traceoptions_object;
     }
     list profile {
       key name;
       description "Network monitoring probe profile configuration";
       max-elements 32;
       uses tdir_netmon_profile_object;
     }
     list source-interface {
       key name;
       description "Network monitoring probe sending interface";
       max-elements 32;
       uses tdir_netmon_src_iface;
     }
   }
   grouping tdir_netmon_profile_object {
     leaf name {
       description "Network monitoring probe profile name";
       type string {
         length "1 .. 20";
       }
     }
     uses apply-advanced;
     choice probe-type {
       case case_1 {
         container http {
           description "HTTP probe options";
           presence "enable http";
           uses tdir_http_probe_object;
         }
       }
       case case_2 {
         leaf icmp {
           description "ICMP probe options";
           type empty;
         }
       }
       case case_3 {
         container tcp {
           description "TCP probe options";
           presence "enable tcp";
           uses tdir_tcp_probe_object;
         }
       }
       case case_4 {
         container ssl-hello {
           description "SSL hello probe options";
           presence "enable ssl-hello";
           uses tdir_ssl_hello_probe_object;
         }
       }
       case case_5 {
         container tls-hello {
           description "TLS hello probe options";
           presence "enable tls-hello";
           uses tdir_tls_hello_probe_object;
         }
       }
       case case_6 {
         container custom {
           description "Custom probe options";
           presence "enable custom";
           uses tdir_netmon_custom_probe_object;
         }
       }
     }
     leaf probe-interval {
       description "Probe interval";
       default "5";
       units "seconds";
       type union {
         type string {
           pattern "<.*>|$.*";
         }
         type uint32;
       }
     }
     leaf failure-retries {
       description "Probe failure retries";
       default "5";
       type union {
         type string {
           pattern "<.*>|$.*";
         }
         type uint32 {
           range "1 .. 255";
         }
       }
     }
     leaf recovery-retries {
       description "Probe recovery retries";
       default "5";
       type union {
         type string {
           pattern "<.*>|$.*";
         }
         type uint32 {
           range "1 .. 255";
         }
       }
     }
   }
   grouping tdir_http_probe_object {
     description "HTTP probe information";
     uses apply-advanced;
     leaf port {
       description "Port number";
       default "80";
       type union {
         type string {
           pattern "<.*>|$.*";
         }
         type uint16 {
           range "1 .. 65535";
         }
       }
     }
     leaf url {
       description "URL name";
       type string {
         length "1 .. 127";
       }
     }
     leaf method {
       description "HTTP method";
       default "get";
       type enumeration {
         enum "get" {
           description "HTTP method GET";
         }
         enum "options" {
           description "HTTP method OPTIONS";
         }
       }
     }
     leaf hostname {
       description "Hostname";
       type string {
         length "1 .. 63";
       }
     }
   }
   grouping tdir_netmon_custom_probe_object {
     description "Custom probe information";
     uses apply-advanced;
     leaf protocol {
       description "Custom protocol";
       type enumeration {
         enum "tcp" {
           description "TCP protocol";
         }
         enum "udp" {
           description "UDP protocol";
         }
       }
     }
     list cmd {
       key name;
       description "Custom probe command configuration";
       max-elements 1;
       uses tdir_netmon_custom_probe_command_object;
     }
   }
   grouping tdir_netmon_custom_probe_command_object {
     description "Command information in custom probe";
     leaf name {
       description "Custom probe command priority";
       type union {
         type string {
           pattern "<.*>|$.*";
         }
         type uint16 {
           range "1 .. 2";
         }
       }
     }
     uses apply-advanced;
     leaf port {
       description "Port number";
       type union {
         type string {
           pattern "<.*>|$.*";
         }
         type uint16 {
           range "1 .. 65535";
         }
       }
     }
     leaf default-real-service-status {
       description "Default status of real service";
       default "down";
       type enumeration {
         enum "down" {
           description "RS marked down by default";
         }
         enum "up" {
           description "RS marked up by default";
         }
       }
     }
     container send {
       description "Send ASCII string or binary buffer";
       presence "enable send";
       uses tdir_netmon_custom_probe_send_object;
     }
     container expect {
       description "Expect ASCII string or binary buffer";
       presence "enable expect";
       uses tdir_netmon_custom_probe_expect_object;
     }
   }
   grouping tdir_netmon_custom_probe_expect_object {
     uses apply-advanced;
     choice expect_choice {
       case case_1 {
         container ascii {
           description "Expect ASCII string";
           presence "enable ascii";
           uses tdir_netmon_cust_probe_ascii_expect_obj;
         }
       }
       case case_2 {
         container binary {
           description "Expect binary buffer";
           presence "enable binary";
           uses tdir_netmon_cust_probe_binary_expect_obj;
         }
       }
     }
   }
   grouping tdir_netmon_cust_probe_ascii_expect_obj {
     leaf ascii-buf {
       type string {
         length "1 .. 512";
       }
     }
     container offset {
       description "Expect buffer offset";
       presence "enable offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_binary_expect_obj {
     leaf binary-buf {
       type string {
         length "1 .. 512";
       }
     }
     container offset {
       description "Expect buffer offset";
       presence "enable offset";
       uses tdir_netmon_cust_probe_expect_offset_obj;
     }
     leaf real-service-action {
       description "Action on expect match";
       default "up";
       type enumeration {
         enum "up" {
           description "Mark RS up";
         }
         enum "down" {
           description "Mark RS down";
         }
       }
     }
   }
   grouping tdir_netmon_cust_probe_expect_offset_obj {
     leaf offset {
       type union {
         type uint16;
         type string {
           pattern "<.*>|$.*";
         }
       }
     }
     leaf length {
       description "Expect buffer offset length";
       type union {
         type string {
           pattern "<.*>|$.*";
         }
         type uint16 {
           range "1 .. 65535";
         }
       }
     }
   }
   grouping tdir_netmon_custom_probe_send_object {
     choice send_choice {
       case case_1 {
         leaf ascii {
           description "Send ASCII string";
           type string {
             length "1 .. 512";
           }
         }
       }
       case case_2 {
         leaf binary {
           description "Send binary buffer";
           type string {
             length "1 .. 512";
           }
         }
       }
     }
   }
   grouping tdir_netmon_src_iface {
     leaf name {
       description "Network monitoring probe source interface name";
       type string {
         length "1 .. 20";
       }
     }
     uses apply-advanced;
     container family {
       description "Address family";
       uses apply-advanced;
       container inet {
         description "Address family IPv4";
         uses apply-advanced;
         leaf address {
           description "Address family IPv4 address";
           type jt:ipv4addr;
         }
       }
       container inet6 {
         description "Address family IPv6";
         uses apply-advanced;
         leaf address {
           description "Address family IPv6 address";
           type jt:ipv6addr;
         }
       }
     }
   }
   grouping tdir_netmon_traceoptions_object {
     description "Network Monitoring trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "all-real-services" {
             description "Trace all real services";
           }
           enum "messages" {
             description "Trace normal events";
           }
           enum "probe" {
             description "Trace probe events";
           }
           enum "inter-thread" {
             description "Trace inter thread communication events";
           }
           enum "database" {
             description "Trace database events";
           }
           enum "file-descriptor-queue" {
             description "Trace file descriptor queue events";
           }
           enum "probe-infra" {
             description "Trace probe infra events";
           }
           enum "all" {
             description "Trace everything";
           }
         }
       }
     }
     list monitor {
       key name;
       leaf name {
         description "Monitor name";
         type string {
           length "1 .. 20";
         }
       }
       uses apply-advanced;
       leaf group-name {
         description "Group name";
         type string {
           length "1 .. 20";
         }
       }
       leaf real-services-name {
         description "Real service";
         type string {
           length "1 .. 20";
         }
       }
     }
   }
   grouping tdir_service_load_balance_object {
     uses apply-advanced;
     container traceoptions {
       description "Traffic load balance trace options";
       uses tdir_traceoptions_object;
     }
     leaf route-hold-timer {
       description "Route hold timer, when PIC is down";
       default "180";
       type union {
         type string {
           pattern "<.*>|$.*";
         }
         type uint32 {
           range "1 .. 600";
         }
       }
     }
     list instance {
       key name;
       description "Traffic load balance instance configuration";
       max-elements 2048;
       uses tdir_slb_instance_object;
     }
     list flb-policy {
       key name;
       description "Firewall load balancer instance configuration";
       max-elements 2048;
       uses tdir_flb_policy_object;
     }
     list interfaces {
       key name;
       description "Client/server facing interfaces";
       max-elements 8160;
       uses tdir_interfaces_object;
     }
   }
   grouping tdir_flb_policy_object {
     leaf name {
       description "Policy name";
       type string {
         length "1 .. 20";
       }
     }
     uses apply-advanced;
     leaf client-interface {
       description "Client facing interface name";
       type string {
         length "1 .. 20";
       }
     }
     leaf server-interface {
       description "Server facing interface name";
       type string {
         length "1 .. 20";
       }
     }
     list destination {
       key name;
       description "Destination configuration";
       max-elements 8160;
       uses tdir_destination_object;
     }
     leaf-list network-monitoring-profile {
       description "Network monitoring profile name";
       type string {
         length "1 .. 20";
       }
       max-elements 2;
     }
     container load-balance-method {
       presence "enable load-balance-method";
       description "Load balance method";
       uses apply-advanced;
       choice method-type {
         case case_1 {
           container hash {
             presence "enable hash";
             description "Load balance hash method";
             uses apply-advanced;
             container hash-key {
               description "Hash-key type";
               presence "enable hash-key";
               uses tdir_flb_lb_hash_method_obj;
             }
           }
         }
         case case_2 {
           leaf random {
             description "Load balance random method";
             type empty;
           }
         }
         case case_3 {
           leaf least-connections {
             description "Load balance least-connections method";
             type empty;
           }
         }
         case case_4 {
           leaf round-robin {
             description "Load balance round-robin method";
             type empty;
           }
         }
       }
     }
   }
   grouping tdir_destination_object {
     leaf name {
       description "Destiation name";
       type string {
         length "1 .. 20";
       }
     }
     uses apply-advanced;
     leaf destination-ip {
       description "IP address";
       type jt:ipaddr;
     }
     leaf source-ip {
       description "IP address";
       type jt:ipaddr;
     }
     leaf interface {
       description "Interface name";
       type union {
         type jt:interface-name;
         type string {
           pattern "<.*>|$.*";
         }
       }
     }
     leaf routing-instance {
       description "Routing instance name";
       type string {
         length "1 .. 30";
       }
     }
     leaf admin-down {
       description "Set the destination to DOWN state";
       type empty;
     }
   }
   grouping tdir_flb_lb_hash_method_obj {
     uses apply-advanced;
     leaf source-ip {
       description "Source-address based hashing";
       type empty;
     }
     leaf destination-ip {
       description "Destination-address based hashing";
       type empty;
     }
     leaf protocol {
       description "Protocol based hashing";
       type empty;
     }
   }
   grouping tdir_interfaces_object {
     leaf name {
       description "Client/server interfaces name";
       type string {
         length "1 .. 20";
       }
     }
     uses apply-advanced;
     list interfaces {
       key name;
       ordered-by user;
       description "Interfaces part of this zone";
       uses tdir-interface-unit;
     }
   }
   grouping tdir-interface-unit {
     description "Logical interfaces in this zone";
     leaf name {
       description "Logical interface";
       type union {
         type jt:interface-name;
         type string {
           pattern "<.*>|$.*";
         }
       }
     }
     uses apply-advanced;
   }
   grouping tdir_slb_instance_object {
     leaf name {
       description "Instance name";
       type string {
         length "1 .. 20";
       }
     }
     uses apply-advanced;
     leaf interface {
       description "Interface name";
       type union {
         type jt:interface-name;
         type string {
           pattern "<.*>|$.*";
         }
       }
     }
     leaf server-inet-bypass-filter {
       description "Server Implicit inet bypass filter reference";
       type string;
     }
     leaf server-inet6-bypass-filter {
       description "Server Implicit inet6 bypass filter reference";
       type string;
     }
     leaf-list client-interface {
       ordered-by user;
       description "Client facing interface name";
       type union {
         type jt:interface-unit;
         type string {
           pattern "<.*>|$.*";
         }
       }
     }
     leaf-list server-interface {
       ordered-by user;
       description "Server facing interface name";
       type union {
         type jt:interface-unit;
         type string {
           pattern "<.*>|$.*";
         }
       }
     }
     leaf client-vrf {
       description "Client-side VRF";
       type string {
         length "1 .. 30";
       }
     }
     leaf server-vrf {
       description "Server-side VRF";
       type string {
         length "1 .. 30";
       }
     }
     list group {
       key name;
       description "Group configuration";
       max-elements 32;
       uses tdir_slb_group_object;
     }
     list real-service {
       key name;
       description "Real service configuration";
       max-elements 8160;
       uses tdir_real_service_object;
     }
     list virtual-service {
       key name;
       description "Virtual service configuration";
       max-elements 32;
       uses tdir_virtual_service_object;
     }
   }
   grouping tdir_real_service_object {
     leaf name {
       description "Real service name";
       type string {
         length "1 .. 20";
       }
     }
     uses apply-advanced;
     leaf address {
       description "IP address";
       type jt:ipaddr;
     }
     leaf admin-down {
       description "Set the real service to DOWN state";
       type empty;
     }
   }
   grouping tdir_slb_group_object {
     leaf name {
       description "Group name";
       type string {
         length "1 .. 20";
       }
     }
     uses apply-advanced;
     leaf-list real-services {
       ordered-by user;
       description "Real services group association";
       type string {
         length "1 .. 20";
       }
       max-elements 255;
     }
     leaf routing-instance {
       description "Routing instance name";
       type string {
         length "1 .. 30";
       }
     }
     leaf health-check-interface-subunit {
       description "Subunit on which the health-check is to be initiated";
       default "0";
       type union {
         type uint16;
         type string {
           pattern "<.*>|$.*";
         }
       }
     }
     leaf-list network-monitoring-profile {
       description "Network monitoring profile name";
       type string {
         length "1 .. 20";
       }
       max-elements 2;
     }
     container real-service-rejoin-options {
       description "Real service rejoin options";
       uses tdir_auto_rejoin_object;
     }
   }
   grouping tdir_auto_rejoin_object {
     uses apply-advanced;
     leaf no-auto-rejoin {
       description "Disable real service auto-rejoin, when it comes up";
       type empty;
     }
   }
   grouping tdir_ssl_hello_probe_object {
     description "SSL hello probe information";
     uses apply-advanced;
     leaf port {
       description "Port number";
       default "443";
       type union {
         type string {
           pattern "<.*>|$.*";
         }
         type uint16 {
           range "1 .. 65535";
         }
       }
     }
     leaf version {
       description "SSL version";
       type enumeration {
         enum "2" {
           description "SSL version 2";
         }
         enum "3" {
           description "SSL version 3";
         }
       }
     }
   }
   grouping tdir_tcp_probe_object {
     description "TCP probe information";
     uses apply-advanced;
     leaf port {
       description "Port number";
       type union {
         type string {
           pattern "<.*>|$.*";
         }
         type uint16 {
           range "1 .. 65535";
         }
       }
     }
   }
   grouping tdir_tls_hello_probe_object {
     description "TLS hello probe information";
     uses apply-advanced;
     leaf port {
       description "Port number";
       default "443";
       type union {
         type string {
           pattern "<.*>|$.*";
         }
         type uint16 {
           range "1 .. 65535";
         }
       }
     }
   }
   grouping tdir_traceoptions_object {
     description "Traffic load balance trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace traffic load balance config events";
           }
           enum "connect" {
             description "Trace traffic load balance ipc events";
           }
           enum "health" {
             description "Trace traffic load balance health events";
           }
           enum "parse" {
             description "Trace traffic load balance parse events";
           }
           enum "probe" {
             description "Trace traffic load balance probe events";
           }
           enum "route" {
             description "Trace traffic load balance route events";
           }
           enum "snmp" {
             description "Trace traffic load balance snmp events";
           }
           enum "statistics" {
             description "Trace traffic load balance statistics events";
           }
           enum "system" {
             description "Trace traffic load balance system events";
           }
           enum "operational-commands" {
             description "Trace traffic load balance show events";
           }
           enum "filter" {
             description "Trace traffic load balance filter programming events";
           }
           enum "batch" {
             description "Trace traffic load balance Batching related events";
           }
           enum "all" {
             description "Trace everything";
           }
         }
       }
     }
     list monitor {
       key name;
       leaf name {
         description "Monitor name";
         type string {
           length "1 .. 20";
         }
       }
       uses apply-advanced;
       leaf virtual-svc-name {
         description "Virtual service name";
         type string {
           length "1 .. 20";
         }
       }
       leaf instance-name {
         description "Instance name";
         type string {
           length "1 .. 20";
         }
       }
     }
     container in-memory-tracing {
       presence "enable in-memory-tracing";
       leaf max-lines {
         description "Number of max lines in memory tracing";
         type union {
           type string {
             pattern "<.*>|$.*";
           }
           type uint32 {
             range "5120 .. 20480";
           }
         }
       }
     }
   }
   grouping tdir_virtual_service_object {
     leaf name {
       description "Virtual service name";
       type string {
         length "1 .. 20";
       }
     }
     uses apply-advanced;
     leaf mode {
       description "Virtual service mode";
       type enumeration {
         enum "layer2-direct-server-return" {
           description "Layer2 Direct Server Return mode";
         }
         enum "direct-server-return" {
           description "Direct Server Return mode";
         }
         enum "translated" {
           description "Translated mode";
         }
       }
     }
     leaf address {
       description "IP address";
       type jt:ipaddr;
     }
     leaf route-metric {
       description "Route metric";
       default "1";
       type union {
         type string {
           pattern "<.*>|$.*";
         }
         type uint16 {
           range "1 .. 255";
         }
       }
     }
     leaf rebalance-threshold {
       description "Rebalance threshold";
       default "25";
       type union {
         type string {
           pattern "<.*>|$.*";
         }
         type uint16 {
           range "1 .. 100";
         }
       }
     }
     leaf routing-instance {
       description "Routing instance name";
       type string {
         length "1 .. 30";
       }
     }
     list service {
       key name;
       description "Listening service configuration";
       max-elements 1;
       uses tdir_virtual_service_svc_object;
     }
     leaf-list server-interface {
       ordered-by user;
       description "Server facing interface name";
       type union {
         type jt:interface-unit;
         type string {
           pattern "<.*>|$.*";
         }
       }
     }
     leaf group {
       description "Group name";
       type string {
         length "1 .. 20";
       }
     }
     container load-balance-method {
       presence "enable load-balance-method";
       description "Load balance method";
       uses apply-advanced;
       choice method-type {
         case case_1 {
           container hash {
             presence "enable hash";
             description "Load balance hash method";
             uses apply-advanced;
             container hash-key {
               description "Hash-key type";
               presence "enable hash-key";
               uses tdir_virtual_service_lb_hash_method_obj;
             }
           }
         }
         case case_2 {
           leaf random {
             description "Load balance random method";
             type empty;
           }
         }
       }
     }
   }
   grouping tdir_virtual_service_lb_hash_method_obj {
     uses apply-advanced;
     leaf source-ip {
       description "Source-address based hashing";
       type empty;
     }
     leaf destination-ip {
       description "Destination-address based hashing";
       type empty;
     }
     leaf protocol {
       description "Protocol based hashing";
       type empty;
     }
   }
   grouping tdir_virtual_service_svc_object {
     description "Service information in virtual service";
     leaf name {
       description "Service name";
       type string {
         length "1 .. 20";
       }
     }
     uses apply-advanced;
     leaf virtual-port {
       description "Virtual port number";
       type union {
         type string {
           pattern "<.*>|$.*";
         }
         type uint16 {
           range "1 .. 65535";
         }
       }
     }
     leaf server-listening-port {
       description "Server listening port";
       type union {
         type string {
           pattern "<.*>|$.*";
         }
         type uint16 {
           range "1 .. 65535";
         }
       }
     }
     leaf protocol {
       description "Service transport portocol";
       type string;
     }
     leaf include-real-server-ips-in-server-filter {
       description "Includes list of all real server ip address in server filter";
       type empty;
     }
   }
   grouping transaction-method-type {
     leaf name {
       type enumeration {
         enum "method-invite" {
         }
         enum "method-options" {
         }
         enum "method-refer" {
         }
         enum "method-subscribe" {
         }
         enum "method-publish" {
         }
         enum "method-message" {
         }
         enum "method-register" {
         }
       }
     }
     uses apply-advanced;
   }
   grouping transaction_policy_type {
     leaf name {
       description "Policy name";
       type string;
     }
     uses apply-advanced;
     list term {
       key name;
       ordered-by user;
       description "Term definition";
       max-elements 20;
       leaf name {
         description "Term name";
         type string;
       }
       uses apply-advanced;
       container from {
         description "From action";
         presence "enable from";
         uses new_transaction_from_type;
       }
       container then {
         description "Action";
         presence "enable then";
         uses new_transaction_then_type;
       }
     }
   }
   grouping new_transaction_then_type {
     uses apply-advanced;
     leaf accept {
       description "Accept the request";
       type empty;
     }
     leaf reject {
       description "Reject the request";
       type empty;
     }
     container route {
       description "How to route the request";
       uses route_action;
     }
     leaf trace {
       description "Trace messages accepted on this policy";
       type empty;
     }
     leaf admission-control {
       description "Admission controller for the request";
       type string;
     }
     container message-manipulation {
       presence "enable message-manipulation";
       description "Definitions of forward and reverse manipulations ";
       uses apply-advanced;
       list forward-manipulation {
         key name;
         ordered-by user;
         max-elements 5;
         leaf name {
           description "Forward manipulation rules";
           type string;
         }
         uses apply-advanced;
       }
       list reverse-manipulation {
         key name;
         ordered-by user;
         max-elements 5;
         leaf name {
           description "Reverse manipulation rules";
           type string;
         }
         uses apply-advanced;
       }
     }
     leaf signaling-realm {
       description "Signaling realm";
       type string;
     }
     container on-3xx-response {
       presence "enable on-3xx-response";
       description "Behavior on receiving a 3XX Response";
       uses apply-advanced;
       choice _3xx_recursion {
         case case_1 {
           leaf recursion-limit {
             description "The number of recursion to manage";
             default "16";
             type union {
               type string {
                 pattern "<.*>|$.*";
               }
               type uint32 {
                 range "1 .. 16";
               }
             }
           }
         }
       }
     }
   }
   grouping route_action {
     uses apply-advanced;
     container next-hop {
       presence "enable next-hop";
       uses apply-advanced;
       choice next-hop {
         case case_1 {
           container address {
             description "Static route by IP address";
             presence "enable address";
             uses routing-destination-address;
           }
         }
         case case_2 {
           leaf request-uri {
             description "Route by request-uri";
             type empty;
           }
         }
         case case_3 {
           leaf sip-based {
             description "Routing based on the SIP procedures";
             status deprecated;
             type empty;
           }
         }
       }
     }
     leaf egress-service-point {
       description "Exit point";
       type string;
     }
     leaf server-cluster {
       description "Cluster name";
       type string;
     }
   }
   grouping transport_protocol {
     uses apply-advanced;
     choice transport-protocol {
       case case_1 {
         leaf udp {
           type empty;
         }
       }
       case case_2 {
         leaf tcp {
           type empty;
         }
       }
     }
   }
   grouping tunnel_interface_type {
     description "One or more tunnel interfaces on which to configure flow-tap service";
     leaf name {
       description "Tunnel Interface name";
       type union {
         type jt:interface-unit;
         type string {
           pattern "<.*>|$.*";
         }
       }
     }
     uses apply-advanced;
   }
   grouping uri_redirect_cause_type {
     leaf name {
       description "Cause of redirection";
       type enumeration {
         enum "roaming" {
           description "Traffic redirection because of roaming";
         }
         enum "calendar-time" {
           description "Traffic redirection because of time-of-day change";
         }
         enum "quality-of-service" {
           description "Traffic redirection because of QoS";
         }
         enum "volume-expired" {
           description "Traffic redirection because of expiration of volume limit";
         }
         enum "cost-warning" {
           description "Traffic redirection because of cost warning limit";
         }
         enum "user-defined-reason-1" {
           description "User-defined authorization code (1)";
         }
         enum "user-defined-reason-2" {
           description "User-defined authorization code (2)";
         }
         enum "user-defined-reason-3" {
           description "User-defined authorization code (3)";
         }
         enum "user-defined-reason-4" {
           description "User-defined authorization code (4)";
         }
         enum "user-defined-reason-5" {
           description "User-defined authorization code (5)";
         }
         enum "blacklisted" {
           description "Traffic redirection because if blacklisted rating group";
         }
         enum "not-allowed" {
           description "Traffic redirection because of disallowed service class";
         }
         enum "unsubscribed" {
           description "Traffic redirection because of unsubscribed service class";
         }
         enum "credit-expiry" {
           description "Traffic redirection because of expiration of credit";
         }
         enum "unknown" {
           description "Traffic redirection because of unknown reason";
         }
         enum "terminal" {
           description "Traffic redirection because of terminal denied access";
         }
         enum "default" {
           description "Default traffic redirection rule";
         }
       }
     }
     leaf uri {
       description "Redirect to this URI";
       type string {
         length "1 .. 256";
       }
     }
   }
   grouping urlf-profile-object {
     leaf name {
       description "Name of profile";
       type string {
         length "1 .. 64";
       }
     }
     uses apply-advanced;
     leaf feed-name {
       description "Name of feed";
       type string {
         length "1 .. 64";
       }
     }
     leaf url-filter-database {
       description "Full path of the file";
       type string {
         length "1 .. 1024";
       }
     }
     leaf global-dns-filter-stats-log-timer {
       description "Global DNS filtering statistics log timer in minutes";
       default "5";
       units "minutes";
       type union {
         type string {
           pattern "<.*>|$.*";
         }
         type uint32 {
           range "0 .. 60";
         }
       }
     }
     container security-intelligence-policy {
       presence "enable security-intelligence-policy";
       description "Use the database supplied by security intelligence for blacklisted traffic.";
       uses apply-advanced;
       leaf file-type {
         type enumeration {
           enum "txt" {
             description "Policy DB is a text file";
           }
           enum "json" {
             description "Policy DB is in json format";
           }
         }
       }
       container whitelist {
         presence "enable whitelist";
         description "Specify ip-addresses to be whitelisted";
         uses apply-advanced;
         choice address-list {
           case case_1 {
             leaf ip-address-list {
               description "Ip address list";
               type string {
                 length "1 .. 63";
               }
             }
           }
           case case_2 {
             leaf filename {
               description "Full path of file containing whitelist ip-addresses";
               type string {
                 length "1 .. 1024";
               }
             }
           }
         }
       }
       container blacklist {
         presence "enable blacklist";
         description "Specify ip-addresses to be blacklisted";
         uses apply-advanced;
         choice address-list {
           case case_1 {
             leaf ip-address-list {
               description "Ip address list";
               type string {
                 length "1 .. 63";
               }
             }
           }
           case case_2 {
             leaf filename {
               description "Full path of file containing blacklist ip-addresses";
               type string {
                 length "1 .. 1024";
               }
             }
           }
         }
       }
       list threat-level {
         key name;
         ordered-by user;
         description "Define a URL filtering threat level";
         max-elements 10;
         uses threat-level-object;
       }
       container geo-ip {
         presence "enable geo-ip";
         description "GeoIP configuration";
         uses apply-advanced;
         container rule {
           description "GeoIP profile rule";
           uses apply-advanced;
           container match {
             uses apply-advanced;
             leaf-list country {
               ordered-by user;
               description "GeoIP Country List";
               type string;
             }
           }
           container then {
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     container dns-filter {
       description "DNS filter information";
       presence "enable dns-filter";
       uses dns-filter-object;
     }
     list url-filter-template {
       key name;
       ordered-by user;
       description "URL filter template";
       max-elements 8000;
       uses urlf-template-object;
     }
     list dns-filter-template {
       key name;
       ordered-by user;
       description "DNS filter template";
       max-elements 8000;
       uses dnsf-template-object;
     }
   }
   grouping dns-filter-object {
     uses apply-advanced;
     leaf database-file {
       description "Full path of the DNS filter database file";
       type string {
         length "1 .. 1024";
       }
     }
     leaf-list dns-server {
       ordered-by user;
       description "One or more DNS servers addresses";
       type jt:ipaddr;
       max-elements 20;
     }
     container hash-key {
       description "Define hash key for domains key";
       choice key-choice {
         case case_1 {
           leaf ascii-text {
             description "Format as text";
             type string {
               length "1 .. 255";
             }
           }
         }
         case case_2 {
           leaf hexadecimal {
             description "Format as hexadecimal";
             type string {
               length "1 .. 255";
             }
           }
         }
       }
     }
     leaf hash-method {
       description "Define authentication algorithm";
       type enumeration {
         enum "hmac-sha2-256" {
           description "HMAC-SHA2-256 authentication algorithm";
         }
       }
     }
     leaf statistics-log-timer {
       description "DNS log timer in minutes";
       default "5";
       units "minutes";
       type union {
         type string {
           pattern "<.*>|$.*";
         }
         type uint32 {
           range "0 .. 60";
         }
       }
     }
     leaf dns-resp-ttl {
       description "TTL to be used in DNS response";
       default "1800";
       units "seconds";
       type union {
         type string {
           pattern "<.*>|$.*";
         }
         type uint32 {
           range "0 .. 3600";
         }
       }
     }
     leaf wildcarding-level {
       description "Wildcarding level for exact match";
       default "2";
       type union {
         type string {
           pattern "<.*>|$.*";
         }
         type uint32 {
           range "0 .. 10";
         }
       }
     }
     leaf txt-resp-err-code {
       description "Text response error code";
       default "Refused";
       type enumeration {
         enum "Noerror" {
           description "No error response";
         }
         enum "Refused" {
           description "Refuse the DNS Query";
         }
       }
     }
     leaf srv-resp-err-code {
       description "Server response error code";
       default "Refused";
       type enumeration {
         enum "Noerror" {
           description "No error response";
         }
         enum "Refused" {
           description "Refuse the DNS Query";
         }
       }
     }
   }
   grouping dnsf-template-object {
     leaf name {
       description "Name of template";
       type string {
         length "1 .. 64";
       }
     }
     uses apply-advanced;
     leaf feed-name {
       description "Name of feed";
       type string {
         length "1 .. 64";
       }
     }
     container dns-filter {
       description "DNS filter information";
       presence "enable dns-filter";
       uses dns-filter-object;
     }
     leaf-list client-interfaces {
       ordered-by user;
       description "Client facing interfaces on which the dns filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf client-routing-instance {
       description "Routing instance name";
       type string;
     }
     leaf server-routing-instance {
       description "Routing instance name";
       type string;
     }
     list term {
       key name;
       ordered-by user;
       description "Define a DNS filtering term";
       max-elements 64;
       leaf name {
         description "Term name";
         type string {
           length "1 .. 64";
         }
       }
       uses apply-advanced;
       leaf feed-name {
         description "Name of feed";
         type string {
           length "1 .. 64";
         }
       }
       container from {
         description "Define match criteria";
         uses dnsf-match-object;
       }
       container then {
         presence "enable then";
         description "Action to take if the 'from' condition is matched";
         uses apply-advanced;
         choice dns-filter-action {
           case case_1 {
             leaf dns-sinkhole {
               description "DNS sinkhole";
               type empty;
             }
           }
         }
       }
     }
   }
   grouping dnsf-match-object {
     uses apply-advanced;
     leaf-list src-ip-prefix {
       ordered-by user;
       description "Source IP Prefix list specification";
       type jt:ipprefix;
       max-elements 64;
     }
   }
   grouping threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf accept {
             description "Accept";
             type empty;
           }
         }
         case case_2 {
           leaf log {
             description "Log";
             type empty;
           }
         }
         case case_3 {
           leaf drop {
             description "Drop";
             type empty;
           }
         }
         case case_4 {
           leaf drop-and-log {
             description "Drop and log";
             type empty;
           }
         }
         case case_5 {
           leaf drop-and-sample {
             description "Drop and sample";
             type empty;
           }
         }
         case case_6 {
           leaf drop-log-and-sample {
             description "Drop log and sample";
             type empty;
           }
         }
         case case_7 {
           leaf log-and-sample {
             description "Log and sample";
             type empty;
           }
         }
         case case_8 {
           leaf sample {
             description "Push packets to sampling collector";
             type empty;
           }
         }
       }
     }
   }
   grouping urlf-template-object {
     leaf name {
       description "Name of template";
       type string {
         length "1 .. 64";
       }
     }
     uses apply-advanced;
     leaf-list client-interfaces {
       ordered-by user;
       description "Client facing interfaces on which the url filtering is applied";
       type union {
         type jt:interface-unit;
         type string {
           pattern "<.*>|$.*";
         }
       }
       max-elements 64;
     }
     leaf-list server-interfaces {
       ordered-by user;
       description "Server facing interfaces to which traffic destined to";
       type union {
         type jt:interface-unit;
         type string {
           pattern "<.*>|$.*";
         }
       }
       max-elements 64;
     }
     leaf dns-source-interface {
       description "Interface on which the DNS queries are originated";
       type union {
         type jt:interface-unit;
         type string {
           pattern "<.*>|$.*";
         }
       }
     }
     leaf dns-routing-instance {
       description "Routing instance for DNS queries";
       type string;
     }
     leaf client-routing-instance {
       description "Routing instance name";
       type string;
     }
     leaf-list dns-server {
       ordered-by user;
       description "One or more DNS servers addresses";
       type jt:ipaddr;
       max-elements 2;
     }
     leaf dns-resolution-interval {
       description "DNS resolution timer in minutes";
       default "1440";
       units "minutes";
       type union {
         type string {
           pattern "<.*>|$.*";
         }
         type uint32 {
           range "60 .. 1440";
         }
       }
     }
     leaf dns-retries {
       description "DNS resolution attempts";
       default "3";
       type union {
         type string {
           pattern "<.*>|$.*";
         }
         type uint32 {
           range "1 .. 5";
         }
       }
     }
     leaf dns-resolution-rate {
       description "DNS resolution rate per chunk interval";
       default "50";
       type union {
         type string {
           pattern "<.*>|$.*";
         }
         type uint32 {
           range "50 .. 100";
         }
       }
     }
     leaf url-filter-database {
       description "Full path of the file";
       type string {
         length "1 .. 1024";
       }
     }
     leaf disable-url-ip-filtering {
       description "Disable filtering of IPs belonging to blocklisted domains";
       type empty;
     }
     container security-intelligence-policy {
       presence "enable security-intelligence-policy";
       description "Use the database supplied by security intelligence";
       uses apply-advanced;
       list threat-level {
         key name;
         ordered-by user;
         description "Define a URL filtering threat level";
         max-elements 10;
         uses template-threat-level-object;
       }
       container geo-ip {
         presence "enable geo-ip";
         description "GeoIP Template Rule configuration";
         uses apply-advanced;
         container rule {
           description "GeoIP Template";
           uses apply-advanced;
           container match {
             uses apply-advanced;
             leaf-list group {
               ordered-by user;
               description "GeoIP Country List";
               type string;
             }
           }
           container then {
             presence "enable then";
             uses apply-advanced;
             container action {
               description "Action to take if the 'match' condition is met";
               uses apply-advanced;
               choice action {
                 case case_1 {
                   leaf drop {
                     description "Drop";
                     type empty;
                   }
                 }
                 case case_2 {
                   leaf drop-and-sample {
                     description "Drop and sample";
                     type empty;
                   }
                 }
               }
             }
           }
         }
       }
     }
     list term {
       key name;
       ordered-by user;
       description "Define a url filtering term";
       max-elements 8;
       leaf name {
         description "Term name";
         type string {
           length "1 .. 64";
         }
       }
       uses apply-advanced;
       container from {
         description "Define match criteria";
         uses urlf-match-object;
       }
       container then {
         presence "enable then";
         description "Action to take if the 'from' condition is matched";
         uses apply-advanced;
         choice url-filter-action {
           case case_1 {
             leaf redirect-url {
               description "Redirect URL";
               type string {
                 length "1 .. 1024";
               }
             }
           }
           case case_2 {
             leaf custom-page {
               description "Custome page string";
               type string {
                 length "1 .. 1025";
               }
             }
           }
           case case_3 {
             leaf http-status-code {
               description "HTTP status code value";
               type union {
                 type string {
                   pattern "<.*>|$.*";
                 }
                 type uint16 {
                   range "400 .. 599";
                 }
               }
             }
           }
           case case_4 {
             leaf tcp-reset {
               description "TCP Reset";
               type empty;
             }
           }
           case case_5 {
             leaf accept {
               description "Accept";
               type empty;
             }
           }
         }
       }
     }
   }
   grouping template-threat-level-object {
     leaf name {
       description "Threat level value";
       type union {
         type string {
           pattern "<.*>|$.*";
         }
         type uint32 {
           range "1 .. 10";
         }
       }
     }
     uses apply-advanced;
     container threat-action {
       presence "enable threat-action";
       description "Action to be taken for the given threat level ";
       uses apply-advanced;
       choice secintl-action {
         case case_1 {
           leaf drop-and-sample {
             description "Drop and sample";
             type empty;
           }
         }
         case case_2 {
           leaf sample {
             description "Push packets to sampling collector";
             type empty;
           }
         }
       }
     }
   }
   grouping urlf-match-object {
     uses apply-advanced;
     leaf-list src-ip-prefix {
       ordered-by user;
       description "Source IP Prefix list specification";
       type jt:ipprefix;
       max-elements 10;
     }
     leaf-list dest-ports {
       ordered-by user;
       description " Destination port list specification";
       type union {
         type string {
           pattern "<.*>|$.*";
         }
         type uint16 {
           range "1 .. 65535";
         }
       }
       max-elements 10;
     }
   }
   grouping urlf-traceoptions-object {
     description "URL filtering trace options";
     uses apply-advanced;
     leaf no-remote-trace {
       description "Disable remote tracing";
       type empty;
     }
     container file {
       description "Trace file information";
       leaf filename {
         description "Name of file in which to write trace information";
         type string {
           length "1 .. 1024";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     leaf level {
       description "Level of debugging output";
       default "error";
       type enumeration {
         enum "error" {
           description "Match error conditions";
         }
         enum "warning" {
           description "Match warning messages";
         }
         enum "notice" {
           description "Match conditions that should be handled specially";
         }
         enum "info" {
           description "Match informational messages";
         }
         enum "verbose" {
           description "Match verbose messages";
         }
         enum "all" {
           description "Match all levels";
         }
       }
     }
     list flag {
       key name;
       ordered-by user;
       description "Tracing flag parameters";
       leaf name {
         type enumeration {
           enum "normal" {
             description "Trace normal events";
           }
           enum "config" {
             description "Trace url filtering config events";
           }
           enum "dns" {
             description "Trace url filtering DNS crawler events";
           }
           enum "timer" {
             description "Trace url filtering timer events";
           }
           enum "connect" {
             description "Trace url filtering ipc events";
           }
           enum "parse" {
             description "Trace url filtering parse events";
           }
           enum "statistics" {
             description "Trace url filtering statistics events";
           }
           enum "system" {
             description "Trace url filtering system events";
           }
           enum "operational-commands" {
             description "Trace url filtering show events";
           }
           enum "filter" {
             description "Trace url filtering filter programming events";
           }
           enum "gencfg" {
             description "Trace url filtering gencfg events";
           }
           enum "routing" {
             description "Trace url filtering route programming events";
           }
           enum "snmp" {
             description "Trace url filtering snmp events";
           }
           enum "all" {
             description "Trace everything";
           }
         }
       }
     }
   }
   grouping user-plane-object {
     leaf name {
       description "User plane name";
       type string {
         length "1 .. 80";
       }
     }
     uses apply-advanced;
     leaf ip-address {
       description "User plane ip address";
       type jt:ipv4addr;
     }
     leaf routing-instance {
       description "User plane routing instance";
       type string {
       }
     }
     leaf data-network-name {
       description "Data network name";
       type string {
         length "3 .. 102";
       }
     }
     container colocated-user-plane {
       presence "enable colocated-user-plane";
       description "User plane is colocated";
       uses apply-advanced;
       leaf ip-endpoint-address {
         description "Endpoint ip address of user plane";
         type jt:ipv4addr;
       }
     }
   }
   grouping user_category_type {
     uses apply-advanced;
     leaf cc-mask {
       description "Charging characteristics mask";
       type string {
         length 4;
       }
     }
     container default {
       presence "enable default";
       description "Default user category";
       uses apply-advanced;
       container rule-space {
         presence "enable rule-space";
         description "Default rule space settings";
         uses apply-advanced;
         leaf default {
           description "Default rule space to apply initially to all contexts";
           type string {
             length "1 .. 64";
           }
         }
         leaf default-secondary {
           description "Default rule space to apply to secondary contexts";
           type string {
             length "1 .. 64";
           }
         }
       }
       container pdp-context {
         description "PDP context settings";
         uses apply-advanced;
         leaf creation {
           description "PDP context creation state";
           type enumeration {
             enum "unblocked" {
               description "No restrictions on PDP context creation";
             }
             enum "blocked" {
               description "New PDP context creation fully blocked";
             }
           }
         }
       }
       leaf policy-control-static-profile {
         description "Default static policy control profile";
         type string {
           length "1 .. 64";
         }
       }
       choice dynamic-profile-choice {
         case case_1 {
           leaf policy-control-dynamic-profile {
             description "Default dynamic policy control profile";
             type string {
               length "1 .. 64";
             }
           }
         }
         case case_2 {
           leaf policy-control-dynamic-gx-profile {
             description "Default policy control gx profile";
             type string {
               length "1 .. 64";
             }
           }
         }
         case case_3 {
           leaf policy-control-dynamic-vf-gx-profile {
             description "Default policy control vf gx profile";
             status deprecated;
             type string {
               length "1 .. 64";
             }
           }
         }
       }
       leaf rating-control-profile {
         description "Default rating control profile";
         type string {
           length "1 .. 64";
         }
       }
       choice credit-control-choice {
         case case_1 {
           leaf credit-control-profile {
             description "Default credit control profile";
             type string {
               length "1 .. 64";
             }
           }
         }
         case case_2 {
           leaf credit-control-ro-profile {
             description "Default ro profile";
             type string {
               length "1 .. 64";
             }
           }
         }
       }
       leaf charging-unit-profile {
         description "Default charging unit profile";
         type string {
           length "1 .. 64";
         }
       }
       leaf block-based-charging-profile {
         description "Default block-based charging profile";
         type string {
           length "1 .. 64";
         }
       }
       leaf qos-control-profile {
         description "Default QoS control profile";
         type string {
           length "1 .. 64";
         }
       }
     }
     list category {
       key name;
       max-elements 63;
       leaf name {
         description "User category identifier";
         type union {
           type string {
             pattern "<.*>|$.*";
           }
           type uint32 {
             range "1 .. 63";
           }
         }
       }
       uses apply-advanced;
       leaf-list cc-values {
         ordered-by user;
         description "CC values that select this category.";
         type union {
           type string {
             pattern "<.*>|$.*";
           }
           type uint32 {
             range "0 .. 65535";
           }
         }
         max-elements 64;
       }
       choice imsi-msisdn-choice {
         case case_1 {
           leaf imsi {
             description "IMSI regular expression that selects this category";
             type jt:regular-expression;
           }
         }
         case case_2 {
           leaf msisdn {
             description "MSISDN regular expression that selects this category";
             type jt:regular-expression;
           }
         }
       }
       container rule-space {
         presence "enable rule-space";
         description "Default rule space settings";
         uses apply-advanced;
         leaf default {
           description "Default rule space to apply initially to all contexts";
           type string {
             length "1 .. 64";
           }
         }
         leaf default-secondary {
           description "Default rule space to apply to secondary contexts";
           type string {
             length "1 .. 64";
           }
         }
       }
       container pdp-context {
         description "PDP context settings";
         uses apply-advanced;
         leaf creation {
           description "PDP context creation state";
           type enumeration {
             enum "unblocked" {
               description "No restrictions on PDP context creation";
             }
             enum "blocked" {
               description "New PDP context creation fully blocked";
             }
           }
         }
       }
       leaf policy-control-static-profile {
         description "Static policy-control profile";
         type string {
           length "1 .. 64";
         }
       }
       choice dynamic-profile-choice {
         case case_1 {
           leaf policy-control-dynamic-profile {
             description "Dynamic policy control profile";
             type string {
               length "1 .. 64";
             }
           }
         }
         case case_2 {
           leaf policy-control-dynamic-gx-profile {
             description "Gx policy control profile";
             type string {
               length "1 .. 64";
             }
           }
         }
         case case_3 {
           leaf policy-control-dynamic-vf-gx-profile {
             description "Vf Gx policy control profile";
             status deprecated;
             type string {
               length "1 .. 64";
             }
           }
         }
       }
       leaf rating-control-profile {
         description "Rating control profile";
         type string {
           length "1 .. 64";
         }
       }
       choice credit-control-choice {
         case case_1 {
           leaf credit-control-profile {
             description "Credit control profile";
             type string {
               length "1 .. 64";
             }
           }
         }
         case case_2 {
           leaf credit-control-ro-profile {
             description "Ro profile";
             type string {
               length "1 .. 64";
             }
           }
         }
       }
       leaf charging-unit-profile {
         description "Charging unit profile";
         type string {
           length "1 .. 64";
         }
       }
       leaf block-based-charging-profile {
         description "Block-based charging profile";
         type string {
           length "1 .. 64";
         }
       }
       leaf qos-control-profile {
         description "QoS control profile";
         type string {
           length "1 .. 64";
         }
       }
     }
   }
   grouping v6rd_object {
     leaf name {
       description "6rd concentrator name";
       type string {
         length "1 .. 63";
       }
     }
     uses apply-advanced;
     leaf softwire-address {
       description "Softwire concentrator IPV4 prefix";
       type jt:ipv4addr;
     }
     leaf ipv4-prefix {
       description "6rd customer edge IPV4 prefix";
       type jt:ipv4prefix;
     }
     leaf v6rd-prefix {
       description "6rd domain's IPV6 prefix";
       type jt:ipv6prefix;
     }
     leaf mtu-v4 {
       description "MTU for the softwire tunnel";
       type union {
         type string {
           pattern "<.*>|$.*";
         }
         type int32 {
           range "576 .. 9192";
         }
       }
     }
   }
   grouping version-ipfix-template {
     description "One or more version-ipfix  templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf observation-domain-id {
       description "Observation Domain Id";
       default "0";
       type union {
         type string {
           pattern "<.*>|$.*";
         }
         type uint32 {
           range "0 .. 255";
         }
       }
     }
     leaf multi-bgp-path {
       description "Enable multi bgp path support";
       type empty;
     }
     container nexthop-learning {
       presence "enable nexthop-learning";
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container data-record-fields {
       description "Extended AS info required";
       uses apply-advanced;
       leaf include-policy-map-name {
         description "Include first 4 letters of policymap name applied on packet";
         type empty;
       }
       container destination-prefix-as-path {
         presence "enable destination-prefix-as-path";
         description "Destination prefix AS path";
         uses apply-advanced;
         leaf count {
           description "Count of destination prefix AS path";
           type union {
             type string {
               pattern "<.*>|$.*";
             }
             type uint32 {
               range "1 .. 50";
             }
           }
         }
       }
       container source-prefix-as-path {
         presence "enable source-prefix-as-path";
         description "Source prefix AS path";
         uses apply-advanced;
         leaf count {
           description "Count of pource prefix AS path";
           type union {
             type string {
               pattern "<.*>|$.*";
             }
             type uint32 {
               range "1 .. 50";
             }
           }
         }
       }
       container bgp-destination-standard-community {
         presence "enable bgp-destination-standard-community";
         description "BGP destination standard community";
         uses apply-advanced;
         leaf count {
           description "Count of BGP destination standard community";
           type union {
             type string {
               pattern "<.*>|$.*";
             }
             type uint32 {
               range "1 .. 50";
             }
           }
         }
       }
       container bgp-source-standard-community {
         presence "enable bgp-source-standard-community";
         description "BGP source standard community";
         uses apply-advanced;
         leaf count {
           description "Count of BGP source standard community";
           type union {
             type string {
               pattern "<.*>|$.*";
             }
             type uint32 {
               range "1 .. 50";
             }
           }
         }
       }
       container bgp-destination-extended-community {
         presence "enable bgp-destination-extended-community";
         description "BGP destination extended community";
         uses apply-advanced;
         leaf count {
           description "Count of BGP destination extended community";
           type union {
             type string {
               pattern "<.*>|$.*";
             }
             type uint32 {
               range "1 .. 50";
             }
           }
         }
       }
       container bgp-source-extended-community {
         presence "enable bgp-source-extended-community";
         description "BGP source extended community";
         uses apply-advanced;
         leaf count {
           description "Count of BGP source extended community";
           type union {
             type string {
               pattern "<.*>|$.*";
             }
             type uint32 {
               range "1 .. 50";
             }
           }
         }
       }
       container bgp-destination-large-community {
         presence "enable bgp-destination-large-community";
         description "BGP destination large community";
         uses apply-advanced;
         leaf count {
           description "Count of BGP destination large community";
           type union {
             type string {
               pattern "<.*>|$.*";
             }
             type uint32 {
               range "1 .. 50";
             }
           }
         }
       }
       container bgp-source-large-community {
         presence "enable bgp-source-large-community";
         description "BGP source large community";
         uses apply-advanced;
         leaf count {
           description "Count of BGP source large community";
           type union {
             type string {
               pattern "<.*>|$.*";
             }
             type uint32 {
               range "1 .. 50";
             }
           }
         }
       }
     }
     choice template-types {
       case case_1 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Flow-direction field type";
                 }
                 enum "app-id" {
                   description "Applicationid field type";
                 }
               }
             }
             uses apply-advanced;
           }
         }
       }
       case case_2 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Flow-direction field type";
                 }
                 enum "app-id" {
                   description "Applicationid field type";
                 }
               }
             }
             uses apply-advanced;
           }
         }
       }
       case case_3 {
         container vpls-template {
           presence "enable vpls-template";
           description "VPLS template configuration";
           status deprecated;
         }
       }
       case case_4 {
         container bridge-template {
           presence "enable bridge-template";
           description "BRIDGE template configuration";
         }
       }
       case case_5 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_6 {
         container mpls-ipv4-template {
           presence "enable mpls-ipv4-template";
           description "MPLS-IPv4 template must be configured only for MS-MIC and MS-MPC based line cards";
           uses apply-advanced;
           leaf-list label-position {
             ordered-by user;
             description "One or more MPLS label positions";
             type union {
               type string {
                 pattern "<.*>|$.*";
               }
               type uint8 {
                 range "1 .. 8";
               }
             }
             max-elements 3;
           }
         }
       }
     }
     container tunnel-observation {
       description "Tunnel observation";
       uses apply-advanced;
       leaf mpls-over-udp {
         description "Mpls-over-udp";
         type empty;
       }
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping version9-template {
     description "One or more version 9 templates for flow monitoring";
     leaf name {
       description "Name of template";
       type string;
     }
     uses apply-advanced;
     leaf flow-active-timeout {
       description "Interval after which active flow is exported";
       default "60";
       type union {
         type string {
           pattern "<.*>|$.*";
         }
         type uint32 {
           range "10 .. 600";
         }
       }
     }
     leaf flow-inactive-timeout {
       description "Period of inactivity that marks a flow inactive";
       default "60";
       type union {
         type string {
           pattern "<.*>|$.*";
         }
         type uint32 {
           range "10 .. 600";
         }
       }
     }
     leaf template-id {
       description "Template id";
       type union {
         type string {
           pattern "<.*>|$.*";
         }
         type uint32;
       }
     }
     leaf option-template-id {
       description "Options template id";
       type union {
         type string {
           pattern "<.*>|$.*";
         }
         type uint32;
       }
     }
     leaf source-id {
       description "Source Id";
       default "0";
       type union {
         type string {
           pattern "<.*>|$.*";
         }
         type uint32 {
           range "0 .. 255";
         }
       }
     }
     leaf multi-bgp-path {
       description "Enable multi bgp path support";
       type empty;
     }
     container nexthop-learning {
       description "Nexthop learning parameter. Valid ONLY for INLINE-JFLOW";
       uses apply-advanced;
       choice enable-disable {
         case case_1 {
           leaf enable {
             description "Enable nexthop learning";
             type empty;
           }
         }
         case case_2 {
           leaf disable {
             description "Disable nexthop learning";
             type empty;
           }
         }
       }
     }
     container template-refresh-rate {
       presence "enable template-refresh-rate";
       description "Template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container option-refresh-rate {
       presence "enable option-refresh-rate";
       description "Option template refresh rate";
       uses apply-advanced;
       leaf packets {
         description "In number of packets";
         default "4800";
         type union {
           type string {
             pattern "<.*>|$.*";
           }
           type uint32 {
             range "1 .. 480000";
           }
         }
       }
       leaf seconds {
         description "In number of seconds";
         type union {
           type string {
             pattern "<.*>|$.*";
           }
           type uint32 {
             range "10 .. 600";
           }
         }
       }
     }
     container data-record-fields {
       description "Extended Data record fields";
       uses apply-advanced;
       leaf include-policy-map-name {
         description "Include first 4 letters of policymap name applied on packet";
         type empty;
       }
     }
     choice template-types {
       case case_1 {
         container mpls-ipv4-template {
           presence "enable mpls-ipv4-template";
           description "MPLS-IPv4 template must be configured only for MS-MIC and MS-MPC based line cards";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_2 {
         container mpls-template {
           presence "enable mpls-template";
           description "MPLS template configuration";
           uses apply-advanced;
           leaf-list label-position {
             ordered-by user;
             description "One or more MPLS label positions";
             type union {
               type string {
                 pattern "<.*>|$.*";
               }
               type uint8 {
                 range "1 .. 8";
               }
             }
             max-elements 3;
           }
         }
       }
       case case_3 {
         container ipv6-template {
           presence "enable ipv6-template";
           description "IPv6 template configuration";
           uses apply-advanced;
           list export-extension {
             key name;
             ordered-by user;
             description "IPv6 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_4 {
         container peer-as-billing-template {
           presence "enable peer-as-billing-template";
           description "Peer AS billing template configuration";
         }
       }
       case case_5 {
         container ipv4-template {
           presence "enable ipv4-template";
           description "IPv4 template configuration";
           uses apply-advanced;
           list export-extension {
             key name;
             ordered-by user;
             description "IPv4 template configuration with extra fields added to the template";
             leaf name {
               type enumeration {
                 enum "flow-dir" {
                   description "Applicationid field type";
                 }
                 enum "app-id" {
                   description "Applicationid field type";
                 }
               }
             }
             uses apply-advanced;
           }
           container nexthop-options {
             presence "enable nexthop-options";
             description "Additional information retrieved from nexthop";
             uses apply-advanced;
             choice nexthop-types {
               case case_1 {
                 container mpls {
                   presence "enable mpls";
                   description "MPLS information retrieved from nexthop";
                   uses apply-advanced;
                   leaf-list label-position {
                     ordered-by user;
                     description "One or more MPLS label positions";
                     type union {
                       type string {
                         pattern "<.*>|$.*";
                       }
                       type uint8 {
                         range "1 .. 3";
                       }
                     }
                     max-elements 3;
                   }
                 }
               }
             }
           }
         }
       }
       case case_6 {
         container vpls-template {
           presence "enable vpls-template";
           description "VPLS template configuration";
           status deprecated;
         }
       }
       case case_7 {
         container bridge-template {
           presence "enable bridge-template";
           description "BRIDGE template configuration";
         }
       }
     }
     container tunnel-observation {
       description "Tunnel observation";
       uses apply-advanced;
       leaf mpls-over-udp {
         description "Mpls-over-udp";
         type empty;
       }
       leaf ipv4 {
         description "IPv4";
         type empty;
       }
       leaf ipv6 {
         description "IPv6";
         type empty;
       }
     }
     container flow-key {
       description "Flow key for the template. Valid ONLY for INLINE-JFLOW";
       uses apply-advanced;
       leaf flow-direction {
         description "Include flow direction";
         type empty;
       }
       leaf vlan-id {
         description "Include vlan ID";
         type empty;
       }
       leaf output-interface {
         description "Include output interface";
         type empty;
       }
     }
   }
   grouping virtual-interface-indications-object {
     description "Virtual interface indications";
     uses apply-advanced;
     container virtual-interface-up {
       presence "enable virtual-interface-up";
       uses pgcp-virtual-interface-up-object;
     }
     container virtual-interface-down {
       presence "enable virtual-interface-down";
       uses pgcp-virtual-interface-down-object;
     }
   }
   grouping pgcp-virtual-interface-down-object {
     description "Virtual interface down";
     uses apply-advanced;
     leaf graceful {
       description "Configure graceful service change";
       type enumeration {
         enum "none" {
           description "Suppress graceful-905 service change";
         }
         enum "graceful-905" {
           description "Termination taken out of service";
         }
       }
     }
     leaf administrative {
       description "Configure administrative service change";
       type enumeration {
         enum "forced-905" {
           description "Termination taken out of service";
         }
         enum "forced-906" {
           description "Loss of lower layer connectivity";
         }
         enum "none" {
           description "Suppress service change";
         }
       }
     }
     leaf failure {
       description "Configure failure service change";
       status deprecated;
       type enumeration {
         enum "forced-904" {
           description "Termination malfunctioning";
           status deprecated;
         }
         enum "forced-906" {
           description "Loss of lower layer connectivity";
           status deprecated;
         }
         enum "none" {
           description "Suppress service change";
           status deprecated;
         }
       }
     }
     leaf link-loss {
       description "Configure link-loss service change";
       status deprecated;
       type enumeration {
         enum "forced-906" {
           description "Loss of lower layer connectivity";
           status deprecated;
         }
         enum "none" {
           description "Suppress forced-906 service change";
           status deprecated;
         }
       }
     }
   }
   grouping pgcp-virtual-interface-up-object {
     description "Virtual interface up";
     uses apply-advanced;
     leaf warm {
       description "Configure warm-boot service change";
       type enumeration {
         enum "restart-900" {
           description "Service restored";
         }
         enum "none" {
           description "Suppress restart-900 service change";
         }
       }
     }
     leaf cancel-graceful {
       description "Configure cancel-graceful service change";
       type enumeration {
         enum "none" {
           description "Suppress restart-918 service change";
         }
         enum "restart-918" {
           description "Cancel graceful";
         }
       }
     }
   }
 }
