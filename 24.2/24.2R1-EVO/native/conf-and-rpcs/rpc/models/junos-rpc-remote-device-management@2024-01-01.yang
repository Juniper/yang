/*
 * Copyright (c) 2024 Juniper Networks, Inc.
 * All rights reserved.
 */
 module junos-rpc-remote-device-management {
   namespace "http://yang.juniper.net/junos/rpc/remote-device-management";

   prefix remote-device-management;

   import junos-common-types {
     prefix jt;
     revision-date 2024-01-01;
   }

   organization "Juniper Networks, Inc.";

   contact "yang-support@juniper.net";

   description "Junos RPC YANG module for remote-device-management command(s)";

   revision 2024-01-01 {
     description "Junos: 24.2R1.18-EVO";
   }

   rpc get-rdm-summary {
     description "Show remote device management summary";
   }
   rpc get-rdm-statistics-summary {
     description "Show rdm summary statistics";
   }
   rpc get-rdm-statistics-sd {
     description "Show rdm service device statistics";
     input {
       leaf device-name {
         description "Service device name";
         type string;
         mandatory true;
       }
     }
   }
   rpc get-rdm-service-devices {
     description "Show service device information";
     input {
       leaf device-name {
         description "Service device name";
         type string;
       }
       leaf level {
         type enumeration {
           enum "terse" {
             description "Display terse output";
           }
           enum "detail" {
             description "Display detailed output";
           }
           enum "extensive" {
             description "Display extensive output";
           }
         }
       }
     }
   }
   rpc get-rdm-subscribers {
     description "Show subscriber service session information";
   }
   rpc get-rdm-subscriber-session-id {
     description "By subscriber session id";
     input {
       leaf id {
         description "Subscriber session id";
         type union {
           type string {
             pattern "<.*>|$.*";
           }
           type uint64 {
             range "1 .. 18446744073709551615";
           }
         }
         mandatory true;
       }
       leaf level {
         default "terse";
         type enumeration {
           enum "terse" {
             description "Display terse output";
           }
           enum "detail" {
             description "Display detailed output";
           }
         }
       }
     }
   }
   rpc get-rdm-services {
     description "Show service session information";
   }
   rpc get-rdm-service-session-id {
     description "By service session id";
     input {
       leaf id {
         description "Service session id";
         type union {
           type string {
             pattern "<.*>|$.*";
           }
           type uint64 {
             range "1 .. 18446744073709551615";
           }
         }
         mandatory true;
       }
       leaf level {
         default "terse";
         type enumeration {
           enum "terse" {
             description "Display terse output";
           }
           enum "detail" {
             description "Display detailed output";
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
 }
