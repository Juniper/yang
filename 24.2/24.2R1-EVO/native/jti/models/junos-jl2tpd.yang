module junos-jl2tpd {
  yang-version 1;
  namespace "http://juniper.net/yang/jl2tpd";
  prefix junos-jl2tpd;

  organization
    "Juniper Networks Inc.";
  contact
    "Juniper Networks, Inc.

     1133 Innovation Way
     Sunnyvale, CA

     +1 888 314-5822

     E-mail: yang-support@juniper.net";
  description
    "Juniper Networks definition of Junos native jl2tpd yang model";

  revision 2017-01-01 {
    description
      "Initial revision";
  }

  grouping l2tp-summary-group {
    description
      "The set of statistics associated with the L2TP module";
    leaf l2tp-stats-total-tunnels {
      description
        "The total number of tunnels formed";
      type uint32;
    }
    leaf l2tp-stats-total-sessions {
      description
        "The total number of sessions";
      type uint32;
    }
    leaf l2tp-stats-control-rx-packets {
      description
        "The number of control packets received";
      type uint32;
    }
    leaf l2tp-stats-control-rx-bytes {
      description
        "The number of control bytes received";
      type uint32;
    }
    leaf l2tp-stats-control-tx-packets {
      description
        "The number of control packets transmitted";
      type uint32;
    }
    leaf l2tp-stats-control-tx-bytes {
      description
        "The number of control bytes transmitted";
      type uint32;
    }
    leaf l2tp-era-type-icrq-inflight-count {
      description
        "The count of in-flight Incoming Call Request (ICRQ) sessions reported to the Event Rate Analyzer (ERA).";
      type uint32;
    }
    leaf l2tp-era-type-icrq-reported-successes {
      description
        "The count of successful Incoming Call Request (ICRQ) sessions reported to the Event Rate Analyzer (ERA).";
      type uint32;
    }
    leaf l2tp-era-type-icrq-reported-failures {
      description
        "The count of failed Incoming Call Request (ICRQ) sessions reported to the Event Rate Analyzer (ERA).";
      type uint32;
    }
    leaf l2tp-era-type-sccrq-inflight-count {
      description
        "The count of in-flight Start Control Connection Request (SCCRQ) sessions reported to the Event Rate Analyzer (ERA).";
      type uint32;
    }
    leaf l2tp-era-type-sccrq-reported-successes {
      description
        "The count of successful Start Control Connection Request (SCCRQ) sessions reported to the Event Rate Analyzer (ERA).";
      type uint32;
    }
    leaf l2tp-era-type-sccrq-reported-failures {
      description
        "The count of failed Start Control Connection Request (SCCRQ) sessions reported to the Event Rate Analyzer (ERA).";
      type uint32;
    }
  }

  grouping jl2tpd-top {
    description
      "Juniper Networks native jl2tpd statistics collection";
    container junos {
      description
        "All native jl2tpd statistics for JunOS";
      config false;
      container system {
        description
          "Container for system";
        container subscriber-management {
          description
            "Subscriber management collection";
          container client-protocols {
            description
              "Protocol collection";
            container l2tp {
              description
                "L2TP Protocol";
              container summary {
                description
                  "Container for summary";
                uses l2tp-summary-group;
              }
            }
          }
        }
      }
    }
  }

  uses jl2tpd-top;
}
