module jnx-openconfig-dev {
  yang-version "1";

  namespace "http://yang.juniper.net/openconfig/deviations"; 

  prefix "oc-dev";

  import openconfig-alarms { prefix oc-alarms; }
  import openconfig-platform { prefix oc-platform; }
  import openconfig-platform-integrated-circuit { prefix oc-ic; }
  import openconfig-platform-port { prefix oc-port; }
  import openconfig-platform-psu { prefix oc-platform-psu; }
  import openconfig-platform-transceiver { prefix oc-transceiver; }
  import openconfig-platform-pipeline-counters { prefix oc-ppc; }
  import openconfig-terminal-device { prefix oc-opt-term; }
  import openconfig-interfaces { prefix oc-if; }
  import openconfig-if-ethernet { prefix oc-eth; }
  import openconfig-if-8021x { prefix oc-1x; }
  import openconfig-if-tunnel { prefix oc-tun; }
  import openconfig-if-ip { prefix oc-ip; }
  import openconfig-if-ip-ext { prefix oc-ip-ext; }
  import openconfig-bgp-policy { prefix oc-bgp-pol; }
  import openconfig-rib-bgp-ext {prefix oc-bgprib-ext;}
  import openconfig-routing-policy { prefix oc-rpol; }
  import openconfig-ospf-policy {prefix oc-ospf-pol;}
  import openconfig-isis-policy {prefix oc-isis-pol;}

  import openconfig-acl { prefix oc-acl; }

  import ietf-inet-types { prefix inet; }
  import ietf-yang-types { prefix yang; }
  import openconfig-local-routing { prefix oc-loc-rt; }

  import openconfig-lldp { prefix oc-lldp; }

  import openconfig-vlan { prefix oc-vlan; }

  import openconfig-network-instance { prefix oc-ni; }

  import openconfig-aft-network-instance { prefix oc-aftni; }

  import openconfig-system { prefix oc-system; }

  import openconfig-messages { prefix oc-messages; }

  import openconfig-lacp { prefix oc-lacp; }

  import openconfig-bfd { prefix oc-bfd; }

  import openconfig-probes { prefix oc-probes; }

  import openconfig-qos { prefix oc-qos; }

  import openconfig-macsec { prefix oc-msec; }

  import junos-yang-types { prefix jnx-types; }

  import jnx-aug-openconfig-ni { prefix jnxocni; }

  import openconfig-system-grpc { prefix oc-sys-grpc; }

  import openconfig-telemetry { prefix oc-telemetry; }

  import openconfig-keychain { prefix oc-keychain; }

  import openconfig-sampling { prefix oc-sampling; }

  import openconfig-sampling-sflow { prefix oc-sflow; }

  import openconfig-spanning-tree { prefix oc-stp; }

  organization "Juniper Networks";
  contact "www.juniper.net";

  description
    "This module contains OpenConfig deviations for all modules";

  revision "2018-10-30" {
    description "Add deviation for specific to preference (MPLS TE)";
    reference "JUNOS 18.2X75-D30, 18.4 and above";
  }

  revision "2018-08-08" {
    description "Add deviations specific to associated-rsvp-session (MPLS TE)";
  }

  revision "2018-02-05" {
    description "add support for BGP Version 4.0.1";
    reference "TBD";
  }
  revision "2015-05-19" {
    description "Initial revision";
    reference "TBD";
  }

  deviation "/oc-keychain:keychains" {
      deviate not-supported;
  }

  deviation "/oc-ni:network-instances/oc-ni:network-instance/oc-ni:evpn"{
      deviate not-supported;
  }

  deviation "/oc-ni:network-instances/oc-ni:network-instance/oc-ni:route-limits/oc-ni:route-limit/oc-ni:config/oc-ni:maximum" {
      deviate replace {
	  type uint32 {
	      range 1..4294967295;
	  }
      }
  }

  deviation "/oc-ni:network-instances/oc-ni:network-instance/oc-ni:route-limits/oc-ni:route-limit/oc-ni:config/oc-ni:alarm-threshold" {
      description
	  "config support for alarm-threshold not supported";
      deviate not-supported;
  }

  deviation "/oc-ni:network-instances/oc-ni:network-instance/oc-ni:route-limits/oc-ni:route-limit/oc-ni:state/oc-ni:alarm-threshold" {
      description
	  "telemetry support for alarm-threshold not supported";
      deviate not-supported;
  }

  deviation "/oc-ni:network-instances/oc-ni:network-instance/oc-ni:route-limits/oc-ni:route-limit/oc-ni:state/oc-ni:threshold-exceeded" {
      description
	  "telemetry support for threshold-exceeded not supported";
      deviate not-supported;
  }

  deviation "/oc-ni:network-instances/oc-ni:network-instance/oc-ni:route-limits/oc-ni:route-limit/oc-ni:state/oc-ni:installed-routes" {
      description
	  "telemetry support for installed-routes not supported";
      deviate not-supported;
  }

  deviation "/oc-ni:network-instances/oc-ni:network-instance/oc-ni:interfaces/oc-ni:interface/oc-ni:config/oc-ni:irb-anycast-gateway"{
        description
          "irb-anycast-gateway not supported";
        deviate not-supported;
  }

  deviation "/oc-ni:network-instances/oc-ni:network-instance/oc-ni:interfaces/oc-ni:interface/oc-ni:state/oc-ni:irb-anycast-gateway"{
        description
          "telemetry support for irb-anycast-gateway not supported";
        deviate not-supported;
  }

  deviation "/oc-ni:network-instances/oc-ni:network-instance/oc-ni:fdb/oc-ni:mac-table/oc-ni:entries/oc-ni:entry/oc-ni:state/oc-ni:age"{
        deviate not-supported;
  }

  deviation "/oc-ni:network-instances/oc-ni:network-instance/oc-ni:fdb/oc-ni:l2rib/oc-ni:mac-table/oc-ni:entries/oc-ni:entry/oc-ni:producers/oc-ni:producer/oc-ni:state/oc-ni:seq-number"{
        deviate not-supported;
  }

  deviation "/oc-ni:network-instances/oc-ni:network-instance/oc-ni:fdb/oc-ni:l2rib/oc-ni:mac-table/oc-ni:entries/oc-ni:entry/oc-ni:producers/oc-ni:producer/oc-ni:state/oc-ni:mobility-state"{
        deviate not-supported;
  }

  deviation "/oc-ni:network-instances/oc-ni:network-instance/oc-ni:fdb/oc-ni:l2rib/oc-ni:mac-table/oc-ni:entries/oc-ni:entry/oc-ni:producers/oc-ni:producer/oc-ni:state/oc-ni:sticky"{
        deviate not-supported;
  }

  deviation "/oc-ni:network-instances/oc-ni:network-instance/oc-ni:fdb/oc-ni:l2rib/oc-ni:mac-table/oc-ni:entries/oc-ni:entry/oc-ni:producers/oc-ni:producer/oc-ni:state/oc-ni:derived-from-mac-ip"{
        deviate not-supported;
  }

  deviation "/oc-ni:network-instances/oc-ni:network-instance/oc-ni:fdb/oc-ni:l2rib/oc-ni:mac-table/oc-ni:entries/oc-ni:entry/oc-ni:producers/oc-ni:producer/oc-ni:state/oc-ni:directly-received"{
        deviate not-supported;
  }

  deviation "/oc-ni:network-instances/oc-ni:network-instance/oc-ni:fdb/oc-ni:l2rib/oc-ni:mac-table/oc-ni:next-hops/oc-ni:next-hop/oc-ni:state/oc-ni:label"{
        deviate not-supported;
  }

  deviation "/oc-ni:network-instances/oc-ni:network-instance/oc-ni:fdb/oc-ni:l2rib/oc-ni:mac-ip-table/oc-ni:entries/oc-ni:entry/oc-ni:state/oc-ni:l3-vni" {
        deviate not-supported;
  }

  deviation "/oc-ni:network-instances/oc-ni:network-instance/oc-ni:fdb/oc-ni:l2rib/oc-ni:mac-ip-table/oc-ni:entries/oc-ni:entry/oc-ni:producers/oc-ni:producer/oc-ni:state/oc-ni:seq-number"{
        deviate not-supported;
  }

  deviation "/oc-ni:network-instances/oc-ni:network-instance/oc-ni:fdb/oc-ni:l2rib/oc-ni:mac-ip-table/oc-ni:entries/oc-ni:entry/oc-ni:producers/oc-ni:producer/oc-ni:state/oc-ni:mobility-state"{
        deviate not-supported;
  }

  deviation "/oc-ni:network-instances/oc-ni:network-instance/oc-ni:fdb/oc-ni:l2rib/oc-ni:mac-ip-table/oc-ni:entries/oc-ni:entry/oc-ni:producers/oc-ni:producer/oc-ni:state/oc-ni:sticky"{
        deviate not-supported;
  }

  deviation "/oc-ni:network-instances/oc-ni:network-instance/oc-ni:fdb/oc-ni:l2rib/oc-ni:mac-ip-table/oc-ni:next-hops/oc-ni:next-hop/oc-ni:state/oc-ni:label"{
        deviate not-supported;
  }

  deviation "/oc-ni:network-instances/oc-ni:network-instance/oc-ni:fdb/oc-ni:mac-mobility"{
        description
          "mac-mobility not supported";
        deviate not-supported;
  }
  
  deviation "/oc-ni:network-instances/oc-ni:network-instance/oc-ni:fdb/oc-ni:arp-proxy"{
        description
          "arp-proxy not supported";
        deviate not-supported;
  }

  deviation "/oc-ni:network-instances/oc-ni:network-instance/oc-ni:fdb/oc-ni:nd-proxy"{
        description
          "nd-proxy not supported";
        deviate not-supported;
  }
  
  deviation "/oc-ni:network-instances/oc-ni:network-instance/oc-ni:fdb/oc-ni:config/oc-ni:anycast-gateway-mac"{
        description
          "anycast-gateway-mac not supported";
        deviate not-supported;
  }

  deviation "/oc-ni:network-instances/oc-ni:network-instance/oc-ni:fdb/oc-ni:config/oc-ni:flood-unknown-unicast-supression"{
        description
          "flood-unknown-unicast-supression not supported";
        deviate not-supported;
  }

  deviation "/oc-ni:network-instances/oc-ni:network-instance/oc-ni:fdb/oc-ni:state/oc-ni:anycast-gateway-mac"{
        deviate not-supported;
  }

  deviation "/oc-ni:network-instances/oc-ni:network-instance/oc-ni:fdb/oc-ni:state/oc-ni:flood-unknown-unicast-supression"{
        deviate not-supported;
  }

// OSPF deviation
  deviation "/oc-ni:network-instances/oc-ni:network-instance/oc-ni:protocols/oc-ni:protocol/oc-ni:ospfv2/" +
              "oc-ni:global/oc-ni:config/oc-ni:summary-route-cost-mode"{
        description
          "Not supported in this version";
        deviate not-supported;
  }
  deviation "/oc-ni:network-instances/oc-ni:network-instance/oc-ni:protocols/oc-ni:protocol/oc-ni:ospfv2/" +
              "oc-ni:global/oc-ni:config/oc-ni:hide-transit-only-networks"{
        description
          "Not supported in this version";
        deviate not-supported;
  }
  deviation "/oc-ni:network-instances/oc-ni:network-instance/oc-ni:protocols/oc-ni:protocol/oc-ni:ospfv2/" +
              "oc-ni:global/oc-ni:timers/oc-ni:max-metric/oc-ni:config/oc-ni:timeout"{
        deviate replace {
          type uint64 {
            range 60..3600;
          }
        }
  }
  deviation "/oc-ni:network-instances/oc-ni:network-instance/oc-ni:protocols/oc-ni:protocol/oc-ni:ospfv2/" +
              "oc-ni:global/oc-ni:timers/oc-ni:max-metric/oc-ni:state/oc-ni:timeout"{
        deviate replace {
          type uint64 {
            range 60..3600;
          }
        }
  }
  deviation "/oc-ni:network-instances/oc-ni:network-instance/oc-ni:protocols/oc-ni:protocol/oc-ni:ospfv2/" +
              "oc-ni:global/oc-ni:timers/oc-ni:spf/oc-ni:config/oc-ni:maximum-delay"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:config/oc-ni:initial-delay"{
        deviate replace {
          type uint32 {
            range 50..8000;
          }
        }
  }
  deviation "/oc-ni:network-instances/oc-ni:network-instance/oc-ni:protocols/oc-ni:protocol/oc-ni:ospfv2/" +
              "oc-ni:global/oc-ni:timers/oc-ni:spf/oc-ni:state/oc-ni:initial-delay"{
        deviate replace {
          type uint32 {
            range 50..8000;
          }
        }
  }
  deviation "/oc-ni:network-instances/oc-ni:network-instance/oc-ni:protocols/oc-ni:protocol/oc-ni:ospfv2/" +
              "oc-ni:global/oc-ni:timers/oc-ni:lsa-generation"{
        description
          "Not supported in this version";
        deviate not-supported;
  }
  deviation "/oc-ni:network-instances/oc-ni:network-instance/oc-ni:protocols/oc-ni:protocol/oc-ni:ospfv2/" +
              "oc-ni:global/oc-ni:timers/oc-ni:max-metric/oc-ni:config/oc-ni:trigger"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:hide-network"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:lsa-filter"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:neighbors/oc-ni:neighbor/oc-ni:config/oc-ni:metric"{
        description
          "Not supported in this version";
        deviate not-supported;
  }

  deviation "/oc-ni:network-instances/oc-ni:network-instance/oc-ni:protocols/oc-ni:protocol/oc-ni:ospfv2/" +
              "oc-ni:areas/oc-ni:area/oc-ni:interfaces/oc-ni:interface/oc-ni:interface-ref"{
        description
          "Not supported in this version";
        deviate not-supported;
  }
  deviation "/oc-ni:network-instances/oc-ni:network-instance/oc-ni:protocols/oc-ni:protocol/oc-ni:ospfv2/" +
              "oc-ni:global/oc-ni:mpls/oc-ni:igp-ldp-sync"{
        description
          "Not supported in this version";
        deviate not-supported;
  }
  deviation "/oc-ni:network-instances/oc-ni:network-instance/oc-ni:protocols/oc-ni:protocol/oc-ni:ospfv2/" +
              "oc-ni:global/oc-ni:inter-area-propagation-policies/oc-ni:inter-area-propagation-policy"{
        description
          "Not supported in this version";
        deviate not-supported;
  }
  deviation "/oc-ni:network-instances/oc-ni:network-instance/oc-ni:protocols/oc-ni:protocol/oc-ni:ospfv2/" +
              "oc-ni:areas/oc-ni:area/oc-ni:mpls"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:multi-area-adjacency-primary"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:config/oc-ni:authentication-type"{
        description
           "Not supported in this version";
        deviate not-supported;
  }
  deviation "/oc-ni:network-instances/oc-ni:network-instance/oc-ni:protocols/oc-ni:protocol/oc-ni:ospfv2/" +
              "oc-ni:areas/oc-ni:area/oc-ni:virtual-links/oc-ni:virtual-link/oc-ni:config/oc-ni:remote-router-id"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:timers/oc-ni:config/oc-ni:dead-interval"{
         deviate replace {
         type uint32 {
         range 1..65535;
         }
       }
  }

  deviation "/oc-ni:network-instances/oc-ni:network-instance/oc-ni:protocols/oc-ni:protocol/oc-ni:ospfv2/" +
              "oc-ni:areas/oc-ni:area/oc-ni:interfaces/oc-ni:interface/oc-ni:timers/oc-ni:state/oc-ni:dead-interval"{
         deviate replace {
         type uint32 {
         range 1..65535;
         }
       }
  }
  deviation "/oc-ni:network-instances/oc-ni:network-instance/oc-ni:protocols/oc-ni:protocol/oc-ni:ospfv2/" +
              "oc-ni:areas/oc-ni:area/oc-ni:interfaces/oc-ni:interface/oc-ni:timers/oc-ni:config/oc-ni:hello-interval"{
         deviate replace {
         type uint32 {
         range 1..255;
         }
       }
  }

  deviation "/oc-ni:network-instances/oc-ni:network-instance/oc-ni:protocols/oc-ni:protocol/oc-ni:ospfv2/" +
              "oc-ni:areas/oc-ni:area/oc-ni:interfaces/oc-ni:interface/oc-ni:timers/oc-ni:state/oc-ni:hello-interval"{
         deviate replace {
         type uint32 {
         range 1..255;
         }
       }
  }
  deviation "/oc-ni:network-instances/oc-ni:network-instance/oc-ni:protocols/oc-ni:protocol/oc-ni:ospfv2/" +
              "oc-ni:areas/oc-ni:area/oc-ni:interfaces/oc-ni:interface/oc-ni:timers/oc-ni:config/oc-ni:retransmission-interval"{
         deviate replace {
         type uint32 {
         range 1..65535;
         }
       }
  }

  deviation "/oc-ni:network-instances/oc-ni:network-instance/oc-ni:protocols/oc-ni:protocol/oc-ni:ospfv2/" +
              "oc-ni:areas/oc-ni:area/oc-ni:interfaces/oc-ni:interface/oc-ni:timers/oc-ni:state/oc-ni:retransmission-interval"{
         deviate replace {
         type uint32 {
         range 1..65535;
         }
       }
  }

  deviation "/oc-ni:network-instances/oc-ni:network-instance/oc-ni:protocols/oc-ni:protocol/oc-ni:ospfv2/" +
              "oc-ni:global/oc-ni:state/oc-ni:summary-route-cost-mode"{
        description
          "Not supported in this version";
        deviate not-supported;
  }
  deviation "/oc-ni:network-instances/oc-ni:network-instance/oc-ni:protocols/oc-ni:protocol/oc-ni:ospfv2/" +
              "oc-ni:global/oc-ni:state/oc-ni:hide-transit-only-networks"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:state/oc-ni:maximum-delay"{
        description
          "Not supported in this version";
        deviate not-supported;
  }
  deviation "/oc-ni:network-instances/oc-ni:network-instance/oc-ni:protocols/oc-ni:protocol/oc-ni:ospfv2/" +
              "oc-ni:global/oc-ni:timers/oc-ni:spf/oc-ni:state/oc-ni:timer-type"{
        description
          "Not supported in this version";
        deviate not-supported;
  }
  deviation "/oc-ni:network-instances/oc-ni:network-instance/oc-ni:protocols/oc-ni:protocol/oc-ni:ospfv2/" +
              "oc-ni:global/oc-ni:timers/oc-ni:max-metric/oc-ni:state/oc-ni:trigger"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:state/oc-ni:multi-area-adjacency-primary"{
        description
          "Not supported in this version";
        deviate not-supported;
  }
  deviation "/oc-ni:network-instances/oc-ni:network-instance/oc-ni:protocols/oc-ni:protocol/oc-ni:ospfv2/" +
              "oc-ni:areas/oc-ni:area/oc-ni:interfaces/oc-ni:interface/oc-ni:state/oc-ni:hide-network"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/" +
              "oc-ni:router-lsa/oc-ni:state/oc-ni:number-tos-metrics"{
        description
          "Not supported in this version";
        deviate not-supported;
  }
  
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:router-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:summary-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:as-external-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:nssa-external-lsa/oc-ni:types-of-service"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:administrative-groups"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:node-attribute"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:link-id"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:local-ip-address"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:unknown-type"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:unknown-value"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:link-type"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:remote-ip-address"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:metric"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:maximum-bandwidth"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:traffic-engineering/oc-ni:tlvs/oc-ni:tlv/oc-ni:link/oc-ni:sub-tlvs/oc-ni:sub-tlv/oc-ni:state/oc-ni:maximum-reservable-bandwidth"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:grace-lsa"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:router-information/oc-ni:tlvs/oc-ni:tlv/oc-ni:informational-capabilities"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/" +
              "oc-ni:router-information/oc-ni:tlvs/oc-ni:tlv/oc-ni:node-administrative-tags"{
        description
          "Not supported in this version";
        deviate not-supported;
  }
  deviation "/oc-ni:network-instances/oc-ni:network-instance/oc-ni:protocols/oc-ni:protocol/oc-ni:ospfv2/" +
              "oc-ni:areas/oc-ni:area/oc-ni:lsdb/oc-ni:lsa-types/oc-ni:lsa-type/oc-ni:lsas/oc-ni:lsa/oc-ni:opaque-lsa/oc-ni:extended-prefix"{
        description
          "Not supported in this version";
        deviate not-supported;
  }
  deviation "/oc-ni:network-instances/oc-ni:network-instance/oc-ni:protocols/oc-ni:protocol/oc-ni:ospfv2/" +
              "oc-ni:areas/oc-ni:area/oc-ni:virtual-links/oc-ni:virtual-link/oc-ni:state"{
        description
          "Not supported in this version";
        deviate not-supported;
  }
  // openconfig-vlan

  deviation "/oc-ni:network-instances/oc-ni:network-instance/oc-ni:vlans/oc-ni:vlan/oc-ni:config/oc-ni:name" {
      description
            "Junos mandates vlan name configuration.";
      deviate add {
          mandatory true;
      }
  }

  deviation "/oc-if:interfaces/oc-if:interface/oc-if:subinterfaces/oc-if:subinterface/oc-ip:ipv4/oc-ip:state/" +
            "oc-ip:dhcp-client" {
      description "Not supported";
      deviate not-supported;
  }

  deviation "/oc-if:interfaces/oc-if:interface/oc-if:subinterfaces/oc-if:subinterface/oc-ip:ipv6/oc-ip:state/" +
            "oc-ip:dhcp-client" {
      description "Not supported";
      deviate not-supported;
  }

  deviation "/oc-if:interfaces/oc-if:interface/oc-if:subinterfaces/oc-if:subinterface/oc-vlan:vlan/oc-vlan:match/" +
            "oc-vlan:double-tagged/oc-vlan:state" {
      description "Not supported";
      deviate not-supported;
  }

  deviation "/oc-if:interfaces/oc-if:interface/oc-if:subinterfaces/oc-if:subinterface/oc-vlan:vlan/oc-vlan:match/" +
            "oc-vlan:single-tagged/oc-vlan:state" {
      description "Not supported";
      deviate not-supported;
  }

  deviation "/oc-if:interfaces/oc-if:interface/oc-if:subinterfaces/oc-if:subinterface/oc-vlan:vlan/oc-vlan:state" {
      description "Not supported";
      deviate not-supported;
  }

  deviation "/oc-if:interfaces/oc-if:interface/oc-if:subinterfaces/oc-if:subinterface/oc-ip:ipv4/oc-ip:neighbors/" +
            "oc-ip:neighbor/oc-ip:config/oc-ip:ip" {
       deviate replace {
           type inet:ipv4-address-no-zone;
       }
  }

  deviation "/oc-if:interfaces/oc-if:interface/oc-if:subinterfaces/oc-if:subinterface/oc-ip:ipv6/oc-ip:neighbors/" +
            "oc-ip:neighbor/oc-ip:config/oc-ip:ip" {
       deviate replace {
           type inet:ipv6-address-no-zone;
       }
  }


  deviation "/oc-if:interfaces/oc-if:interface/oc-if:subinterfaces/oc-if:subinterface/oc-ip:ipv6/oc-ip:router-advertisement/" +
            "oc-ip:config/oc-ip:interval" {
      deviate replace {
	  type uint32 {
	      range 4..1800;
	  }
      }
  }

  deviation "/oc-if:interfaces/oc-if:interface/oc-if:subinterfaces/oc-if:subinterface/oc-ip:ipv6/oc-ip:router-advertisement/" +
            "oc-ip:config/oc-ip:lifetime" {
      deviate replace {
	  type uint32 {
	      range 0..9000;
	  }
      }
  }

  deviation "/oc-if:interfaces/oc-if:interface/oc-if:subinterfaces/oc-if:subinterface/oc-ip:ipv6/oc-ip:router-advertisement/" +
            "oc-ip:config/oc-ip:managed" {
      description "Not supported";
      deviate not-supported;
  }
  deviation "/oc-if:interfaces/oc-if:interface/oc-if:subinterfaces/oc-if:subinterface/oc-ip:ipv6/oc-ip:router-advertisement/" +
            "oc-ip:config/oc-ip:other-config" {
      description "Not supported";
      deviate not-supported;
  }
  deviation "/oc-if:interfaces/oc-if:interface/oc-if:subinterfaces/oc-if:subinterface/oc-ip:ipv6/oc-ip:router-advertisement/" +
            "oc-ip:state/oc-ip:managed" {
      description "Not supported";
      deviate not-supported;
  }
  deviation "/oc-if:interfaces/oc-if:interface/oc-if:subinterfaces/oc-if:subinterface/oc-ip:ipv6/oc-ip:router-advertisement/" +
            "oc-ip:state/oc-ip:other-config" {
      description "Not supported";
      deviate not-supported;
  }
  deviation "/oc-if:interfaces/oc-if:interface/oc-if:subinterfaces/oc-if:subinterface/oc-ip:ipv6/oc-ip:router-advertisement/" +
            "oc-ip:state/oc-ip:enable" {
      description "Not supported";
      deviate not-supported;
  }
  deviation "/oc-if:interfaces/oc-if:interface/oc-if:subinterfaces/oc-if:subinterface/oc-ip:ipv6/oc-ip:router-advertisement/" +
            "oc-ip:state/oc-ip:mode" {
      description "Not supported";
      deviate not-supported;
  }
  deviation "/oc-if:interfaces/oc-if:interface/oc-if:subinterfaces/oc-if:subinterface/oc-ip:ipv6/oc-ip:router-advertisement/" +
            "oc-ip:prefixes/oc-ip:prefix" {
      description "Not supported";
      deviate not-supported;
  }

  deviation "/oc-if:interfaces/oc-if:interface/oc-if:subinterfaces/oc-if:subinterface/oc-ip:ipv4/oc-ip:addresses/" +
            "oc-ip:address/oc-ip:vrrp/oc-ip:vrrp-group/oc-ip:config/oc-ip:virtual-address" {
       deviate replace {
           type inet:ipv4-address-no-zone;
       }
  }

  deviation "/oc-if:interfaces/oc-if:interface/oc-if:subinterfaces/oc-if:subinterface/oc-ip:ipv6/oc-ip:addresses/" +
            "oc-ip:address/oc-ip:vrrp/oc-ip:vrrp-group/oc-ip:config/oc-ip:virtual-address" {
       deviate replace {
           type inet:ipv6-address-no-zone;
       }
  }

  deviation "/oc-if:interfaces/oc-if:interface/oc-if:subinterfaces/oc-if:subinterface/oc-ip:ipv6/oc-ip:addresses/" +
            "oc-ip:address/oc-ip:vrrp/oc-ip:vrrp-group/oc-ip:config/oc-ip:virtual-link-local" {
       deviate replace {
           type inet:ipv6-address-no-zone;
       }
  }

  deviation "/oc-if:interfaces/oc-if:interface/oc-if:subinterfaces/oc-if:subinterface/oc-ip:ipv6/oc-ip:neighbors/" +
            "oc-ip:neighbor/oc-ip:state/oc-ip:is-router" {
    deviate replace {
        type boolean;
    }
    description "[adapted from IETF IP model RFC 7277]
                 Indicates that the neighbor node acts as a router.
                 Junos supports is-router as type boolean";
  }

  deviation /oc-if:interfaces/oc-if:interface/oc-if:subinterfaces/oc-if:subinterface/oc-ip:ipv6/oc-ip-ext:autoconf {
    description
          "Junos does not support ipv6 autoconf";
    deviate not-supported;
  }

  // deviate for opeconfig-interfaces.yang
  deviation /oc-if:interfaces/oc-if:interface/oc-if:state/oc-if:counters/oc-if:in-unknown-protos {
      description
          "Junos does not support in-unknown-protos at interface level";
      deviate not-supported;
  }

  deviation /oc-if:interfaces/oc-if:interface/oc-vlan:routed-vlan/oc-ip:ipv4/oc-ip:addresses/oc-ip:address/oc-ip:state {
      description
          "Not supported at interface level";
      deviate not-supported;
  }

  deviation /oc-if:interfaces/oc-if:interface/oc-vlan:routed-vlan/oc-ip:ipv4/oc-ip:neighbors/oc-ip:neighbor/oc-ip:state {
      description
          "Not supported at interface level";
      deviate not-supported;
  }

  deviation /oc-if:interfaces/oc-if:interface/oc-vlan:routed-vlan/oc-ip:ipv4/oc-ip:proxy-arp/oc-ip:state {
      description
          "Not supported at interface level";
      deviate not-supported;
  }

  deviation /oc-if:interfaces/oc-if:interface/oc-vlan:routed-vlan/oc-ip:ipv4/oc-ip:state {
      description
          "Not supported at interface level";
      deviate not-supported;
  }

  deviation /oc-if:interfaces/oc-if:interface/oc-vlan:routed-vlan/oc-ip:ipv4/oc-ip:unnumbered/oc-ip:state {
      description
          "Not supported at interface level";
      deviate not-supported;
  }

  deviation /oc-if:interfaces/oc-if:interface/oc-vlan:routed-vlan/oc-ip:ipv4/oc-ip:unnumbered/oc-ip:interface-ref/oc-ip:state {
      description
          "Not supported at interface level";
      deviate not-supported;
  }

  deviation /oc-if:interfaces/oc-if:interface/oc-vlan:routed-vlan/oc-ip:ipv6/oc-ip:addresses/oc-ip:address/oc-ip:state {
      description
          "Not supported at interface level";
      deviate not-supported;
  }

  deviation /oc-if:interfaces/oc-if:interface/oc-vlan:routed-vlan/oc-ip:ipv6/oc-ip:neighbors/oc-ip:neighbor/oc-ip:state {
      description
          "Not supported at interface level";
      deviate not-supported;
  }

  deviation /oc-if:interfaces/oc-if:interface/oc-vlan:routed-vlan/oc-ip:ipv6/oc-ip:router-advertisement {
      description
          "Not supported";
      deviate not-supported;
  }

  deviation /oc-if:interfaces/oc-if:interface/oc-vlan:routed-vlan/oc-ip:ipv6/oc-ip:state {
      description
          "Not supported at interface level";
      deviate not-supported;
  }

  deviation /oc-if:interfaces/oc-if:interface/oc-vlan:routed-vlan/oc-ip:ipv6/oc-ip:unnumbered/oc-ip:state {
      description
          "Not supported at interface level";
      deviate not-supported;
  }

  deviation /oc-if:interfaces/oc-if:interface/oc-vlan:routed-vlan/oc-ip:ipv6/oc-ip:unnumbered/oc-ip:interface-ref/oc-ip:state {
      description
          "Not supported at interface level";
      deviate not-supported;
  }

  deviation /oc-if:interfaces/oc-if:interface/oc-vlan:routed-vlan/oc-vlan:state {
      description
          "Not supported at interface level";
      deviate not-supported;
  }

  deviation /oc-if:interfaces/oc-if:interface/oc-if:subinterfaces/oc-if:subinterface/oc-if:state/oc-if:counters/oc-if:in-broadcast-pkts {
      description
          "Junos does not support in-broadcast-pkts at subinterface level";
      deviate not-supported;
  }
  deviation /oc-if:interfaces/oc-if:interface/oc-if:subinterfaces/oc-if:subinterface/oc-if:state/oc-if:counters/oc-if:in-unknown-protos {
      description
          "Junos does not support in-unknown-protos at subinterface level";
      deviate not-supported;
  }
  deviation /oc-if:interfaces/oc-if:interface/oc-if:subinterfaces/oc-if:subinterface/oc-if:state/oc-if:counters/oc-if:out-broadcast-pkts {
      description
          "Junos does not support out-broadcast-pkts at subinterface level";
      deviate not-supported;
  }
  deviation /oc-if:interfaces/oc-if:interface/oc-if:subinterfaces/oc-if:subinterface/oc-if:state/oc-if:counters/oc-if:in-fcs-errors {
      description "Not supported in this release";
      deviate not-supported;
  }

  // deviate for openconfig-if-ethernet.yang
  deviation /oc-if:interfaces/oc-if:interface/oc-eth:ethernet/oc-eth:state/oc-eth:standalone-link-training {
      description
          "Not supported in this release";
      deviate not-supported;
  }
  deviation /oc-if:interfaces/oc-if:interface/oc-eth:ethernet/oc-eth:state/oc-eth:fec-mode {
      description
          "Not supported in this release";
      deviate not-supported;
  }
  deviation /oc-if:interfaces/oc-if:interface/oc-eth:ethernet/oc-eth:state/oc-eth:counters/oc-eth:in-carrier-errors {
      description
          "Not supported in this release";
      deviate not-supported;
  }
  deviation /oc-if:interfaces/oc-if:interface/oc-eth:ethernet/oc-eth:state/oc-eth:counters/oc-eth:in-interrupted-tx {
      description
          "Not supported in this release";
      deviate not-supported;
  }
  deviation /oc-if:interfaces/oc-if:interface/oc-eth:ethernet/oc-eth:state/oc-eth:counters/oc-eth:in-late-collision {
      description
          "Not supported in this release";
      deviate not-supported;
  }
  deviation /oc-if:interfaces/oc-if:interface/oc-eth:ethernet/oc-eth:state/oc-eth:counters/oc-eth:in-mac-errors-rx {
      description
          "Not supported in this release";
      deviate not-supported;
  }
  deviation /oc-if:interfaces/oc-if:interface/oc-eth:ethernet/oc-eth:state/oc-eth:counters/oc-eth:in-single-collision {
      description
          "Not supported in this release";
      deviate not-supported;
  }
  deviation /oc-if:interfaces/oc-if:interface/oc-eth:ethernet/oc-eth:state/oc-eth:counters/oc-eth:in-symbol-error {
      description
          "Not supported in this release";
      deviate not-supported;
  }
  deviation /oc-if:interfaces/oc-if:interface/oc-eth:ethernet/oc-eth:state/oc-eth:counters/oc-eth:out-mac-errors-tx {
      description
          "Not supported in this release";
      deviate not-supported;
  }

  // Static protocol Deviations
   deviation "/oc-ni:network-instances/oc-ni:network-instance/oc-ni:protocols/oc-ni:protocol/oc-ni:static-routes/oc-ni:static/oc-ni:next-hops/oc-ni:next-hop/oc-ni:enable-bfd"
  {
      deviate not-supported;
  }

  // deviate for opeconfig-if-ip.yang
  deviation "/oc-if:interfaces/oc-if:interface/oc-if:subinterfaces/oc-if:subinterface/" +
            "oc-ip:ipv4/oc-ip:state/oc-ip:counters/oc-ip:in-error-pkts" {
    description
      "Junos does not support in-error-pkts at subinterface IPV4 family level";
    deviate not-supported;
  }
  deviation "/oc-if:interfaces/oc-if:interface/oc-if:subinterfaces/oc-if:subinterface/" +
            "oc-ip:ipv4/oc-ip:state/oc-ip:counters/oc-ip:in-discarded-pkts" {
    description
      "Junos does not support in-discarded-pkts at subinterface IPV4 family level";
    deviate not-supported;
  }
  deviation "/oc-if:interfaces/oc-if:interface/oc-if:subinterfaces/oc-if:subinterface/" +
            "oc-ip:ipv4/oc-ip:state/oc-ip:counters/oc-ip:out-error-pkts" {
    description
      "Junos does not support out-error-pkts at subinterface IPV4 family level";
    deviate not-supported;
  }
  deviation "/oc-if:interfaces/oc-if:interface/oc-if:subinterfaces/oc-if:subinterface/" +
            "oc-ip:ipv4/oc-ip:state/oc-ip:counters/oc-ip:out-discarded-pkts" {
    description
      "Junos does not support out-discarded-pkts at subinterface IPV4 family level";
    deviate not-supported;
  }
  deviation "/oc-if:interfaces/oc-if:interface/oc-if:subinterfaces/oc-if:subinterface/" +
            "oc-ip:ipv6/oc-ip:state/oc-ip:counters/oc-ip:in-error-pkts" {
    description
      "Junos does not support in-error-pkts at subinterface IPV6 family level";
    deviate not-supported;
  }
  deviation "/oc-if:interfaces/oc-if:interface/oc-if:subinterfaces/oc-if:subinterface/" +
            "oc-ip:ipv6/oc-ip:state/oc-ip:counters/oc-ip:in-discarded-pkts" {
    description
      "Junos does not support in-discarded-pkts at subinterface IPV6 family level";
    deviate not-supported;
  }
  deviation "/oc-if:interfaces/oc-if:interface/oc-if:subinterfaces/oc-if:subinterface/" +
            "oc-ip:ipv6/oc-ip:state/oc-ip:counters/oc-ip:out-error-pkts" {
    description
      "Junos does not support out-error-pkts at subinterface IPV6 family level";
    deviate not-supported;
  }
  deviation "/oc-if:interfaces/oc-if:interface/oc-if:subinterfaces/oc-if:subinterface/" +
            "oc-ip:ipv6/oc-ip:state/oc-ip:counters/oc-ip:out-discarded-pkts" {
    description
      "Junos does not support out-discarded-pkts at subinterface IPV6 family level";
    deviate not-supported;
  }

    //Network Instance

  deviation "/oc-ni:network-instances/oc-ni:network-instance/oc-ni:policy-forwarding/oc-ni:policies/oc-ni:policy/oc-ni:state/oc-ni:type"{
        deviate not-supported;
  }

  deviation "/oc-ni:network-instances/oc-ni:network-instance/oc-ni:policy-forwarding/oc-ni:policies/oc-ni:policy/oc-ni:rules/oc-ni:rule/oc-ni:action/oc-ni:config/oc-ni:decapsulate-gre"{
        deviate not-supported;
  }

  deviation "/oc-ni:network-instances/oc-ni:network-instance/oc-ni:policy-forwarding/oc-ni:policies/oc-ni:policy/oc-ni:rules/oc-ni:rule/oc-ni:action/oc-ni:state/oc-ni:decapsulate-gre"{
        deviate not-supported;
  }

  deviation "/oc-ni:network-instances/oc-ni:network-instance/oc-ni:policy-forwarding/oc-ni:policies/oc-ni:policy/oc-ni:rules/oc-ni:rule/oc-ni:action/oc-ni:config/oc-ni:decapsulate-mpls-in-udp"{
        deviate not-supported;
  }

  deviation "/oc-ni:network-instances/oc-ni:network-instance/oc-ni:policy-forwarding/oc-ni:policies/oc-ni:policy/oc-ni:rules/oc-ni:rule/oc-ni:action/oc-ni:state/oc-ni:decapsulate-mpls-in-udp"{
        deviate not-supported;
  }

  deviation "/oc-ni:network-instances/oc-ni:network-instance/oc-ni:policy-forwarding/oc-ni:policies/oc-ni:policy/oc-ni:rules/oc-ni:rule/oc-ni:action/oc-ni:config/oc-ni:decapsulate-gue"{
        deviate not-supported;
  }

  deviation "/oc-ni:network-instances/oc-ni:network-instance/oc-ni:policy-forwarding/oc-ni:policies/oc-ni:policy/oc-ni:rules/oc-ni:rule/oc-ni:action/oc-ni:state/oc-ni:decapsulate-gue"{
        deviate not-supported;
  }

  deviation "/oc-ni:network-instances/oc-ni:network-instance/oc-ni:policy-forwarding/oc-ni:policies/oc-ni:policy/oc-ni:rules/oc-ni:rule/oc-ni:action/oc-ni:config/oc-ni:path-selection-group" {
        deviate not-supported;
  }

  deviation "/oc-ni:network-instances/oc-ni:network-instance/oc-ni:policy-forwarding/oc-ni:policies/oc-ni:policy/oc-ni:rules/oc-ni:rule/oc-ni:action/oc-ni:state/oc-ni:path-selection-group" {
        deviate not-supported;
  }

  deviation "/oc-ni:network-instances/oc-ni:network-instance/oc-ni:policy-forwarding/oc-ni:policies/oc-ni:policy/oc-ni:rules/oc-ni:rule/oc-ni:action/oc-ni:config/oc-ni:next-hop" {
        deviate not-supported;
  }

  deviation "/oc-ni:network-instances/oc-ni:network-instance/oc-ni:policy-forwarding/oc-ni:policies/oc-ni:policy/oc-ni:rules/oc-ni:rule/oc-ni:action/oc-ni:state/oc-ni:next-hop" {
        deviate not-supported;
  }

  deviation "/oc-ni:network-instances/oc-ni:network-instance/oc-ni:policy-forwarding/oc-ni:policies/oc-ni:policy/oc-ni:rules/oc-ni:rule/oc-ni:action/oc-ni:encapsulate-gre/oc-ni:config" {
        deviate not-supported;
  }

  deviation "/oc-ni:network-instances/oc-ni:network-instance/oc-ni:policy-forwarding/oc-ni:policies/oc-ni:policy/oc-ni:rules/oc-ni:rule/oc-ni:action/oc-ni:encapsulate-gre/oc-ni:state" {
        deviate not-supported;
  }

  deviation "/oc-ni:network-instances/oc-ni:network-instance/oc-ni:policy-forwarding/oc-ni:policies/oc-ni:policy/oc-ni:rules/oc-ni:rule/oc-ni:action/oc-ni:encapsulate-gre/oc-ni:targets/oc-ni:target/oc-ni:config/oc-ni:ip-ttl" {
        deviate not-supported;
  }

  deviation "/oc-ni:network-instances/oc-ni:network-instance/oc-ni:policy-forwarding/oc-ni:policies/oc-ni:policy/oc-ni:rules/oc-ni:rule/oc-ni:action/oc-ni:encapsulate-gre/oc-ni:targets/oc-ni:target/oc-ni:state/oc-ni:ip-ttl" {
        deviate not-supported;
  }

  deviation "/oc-ni:network-instances/oc-ni:network-instance/oc-ni:policy-forwarding/oc-ni:policies/oc-ni:policy/oc-ni:rules/oc-ni:rule/oc-ni:l2"{
        deviate not-supported;
   }

  deviation "/oc-ni:network-instances/oc-ni:network-instance/oc-ni:policy-forwarding/oc-ni:policies/oc-ni:policy/oc-ni:rules/oc-ni:rule/oc-ni:transport"{
        deviate not-supported;
   }

  deviation "/oc-ni:network-instances/oc-ni:network-instance/oc-ni:policy-forwarding/oc-ni:policies/oc-ni:policy/oc-ni:rules/oc-ni:rule/oc-ni:ipv4/oc-ni:config/oc-ni:source-address" {
      deviate replace {
          type inet:ipv4-prefix;
      }
  }

  deviation "/oc-ni:network-instances/oc-ni:network-instance/oc-ni:policy-forwarding/oc-ni:policies/oc-ni:policy/oc-ni:rules/oc-ni:rule/oc-ni:ipv4/oc-ni:config/oc-ni:destination-address" {
      deviate replace {
          type inet:ipv4-prefix;
      }
  }

  deviation "/oc-ni:network-instances/oc-ni:network-instance/oc-ni:policy-forwarding/oc-ni:policies/oc-ni:policy/oc-ni:rules/oc-ni:rule/oc-ni:ipv6/oc-ni:config/oc-ni:source-address" {
      deviate replace {
          type inet:ipv6-prefix;
      }
  }

  deviation "/oc-ni:network-instances/oc-ni:network-instance/oc-ni:policy-forwarding/oc-ni:policies/oc-ni:policy/oc-ni:rules/oc-ni:rule/oc-ni:ipv6/oc-ni:config/oc-ni:destination-address" {
      deviate replace {
          type inet:ipv6-prefix;
      }
  }

  deviation "/oc-ni:network-instances/oc-ni:network-instance/oc-ni:policy-forwarding/oc-ni:policies/oc-ni:policy/oc-ni:rules/oc-ni:rule/oc-ni:ipv4/oc-ni:config/oc-ni:dscp" {
      deviate replace {
          type string;
      }
  }


  deviation "/oc-ni:network-instances/oc-ni:network-instance/oc-ni:policy-forwarding/oc-ni:policies/oc-ni:policy/oc-ni:rules/oc-ni:rule/oc-ni:ipv6/oc-ni:config/oc-ni:dscp" {
      deviate replace {
          type string;
      }
  }

  deviation "/oc-ni:network-instances/oc-ni:network-instance/oc-ni:policy-forwarding/oc-ni:policies/oc-ni:policy/oc-ni:rules/oc-ni:rule/oc-ni:ipv6/oc-ni:config/oc-ni:destination-flow-label" {
        description
          "destination-flow-label not supported";
        deviate not-supported;
  }

  deviation "/oc-ni:network-instances/oc-ni:network-instance/oc-ni:policy-forwarding/oc-ni:policies/oc-ni:policy/oc-ni:rules/oc-ni:rule/oc-ni:ipv6/oc-ni:config/oc-ni:source-flow-label" {
        description
          "source-flow-label not supported";
        deviate not-supported;
  }

  deviation "/oc-ni:network-instances/oc-ni:network-instance/oc-ni:policy-forwarding/oc-ni:path-selection-groups" {
        description
          "path-selection-groups is not supported";
        deviate not-supported;
  }


  deviation "/oc-ni:network-instances/oc-ni:network-instance/oc-ni:policy-forwarding/oc-ni:policies/oc-ni:policy/oc-ni:rules/oc-ni:rule/oc-ni:ipv6/oc-ni:state/oc-ni:source-flow-label" {
        description
          "source-flow-label not supported";
        deviate not-supported;
  }

  deviation "/oc-ni:network-instances/oc-ni:network-instance/oc-ni:policy-forwarding/oc-ni:policies/oc-ni:policy/oc-ni:rules/oc-ni:rule/oc-ni:ipv6/oc-ni:state/oc-ni:destination-flow-label" {
        description
          "destination-flow-label not supported";
        deviate not-supported;
  }
 
  // Policy Deviations

  deviation /oc-rpol:routing-policy/oc-rpol:defined-sets/oc-bgp-pol:bgp-defined-sets/oc-bgp-pol:as-path-sets {
      deviate not-supported;
  }
  deviation /oc-rpol:routing-policy/oc-rpol:defined-sets/oc-rpol:neighbor-sets/oc-rpol:neighbor-set/oc-rpol:config/oc-rpol:address {
      deviate replace {
          type inet:ip-address;
      }
  }
  deviation /oc-rpol:routing-policy/oc-rpol:policy-definitions/oc-rpol:policy-definition/oc-rpol:statements/oc-rpol:statement/oc-rpol:actions/oc-rpol:set-tag/oc-rpol:reference {
      deviate not-supported;
  }
  deviation /oc-rpol:routing-policy/oc-rpol:defined-sets/oc-bgp-pol:bgp-defined-sets/oc-bgp-pol:community-sets/oc-bgp-pol:community-set/oc-bgp-pol:state {
      description
          "Not supported in this release";
      deviate not-supported;
  }
  deviation /oc-rpol:routing-policy/oc-rpol:defined-sets/oc-bgp-pol:bgp-defined-sets/oc-bgp-pol:ext-community-sets/oc-bgp-pol:ext-community-set/oc-bgp-pol:state {
      description
          "Not supported in this release";
      deviate not-supported;
  }
  deviation /oc-rpol:routing-policy/oc-rpol:policy-definitions/oc-rpol:policy-definition/oc-rpol:statements/oc-rpol:statement/oc-rpol:actions/oc-bgp-pol:bgp-actions/oc-bgp-pol:set-as-path-prepend/oc-bgp-pol:state {
      description
          "Not supported in this release";
      deviate not-supported;
  }
  deviation /oc-rpol:routing-policy/oc-rpol:policy-definitions/oc-rpol:policy-definition/oc-rpol:statements/oc-rpol:statement/oc-rpol:actions/oc-bgp-pol:bgp-actions/oc-bgp-pol:set-community/oc-bgp-pol:state/oc-bgp-pol:method {
      description
          "Not supported in this release";
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:state/oc-bgp-pol:method {
      description
          "Not supported in this release";
      deviate not-supported;
  }
  deviation /oc-rpol:routing-policy/oc-rpol:policy-definitions/oc-rpol:policy-definition/oc-rpol:statements/oc-rpol:statement/oc-rpol:actions/oc-bgp-pol:bgp-actions/oc-bgp-pol:state {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:community-count/oc-bgp-pol:state {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:med-eq {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:origin-eq {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:next-hop-in {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:afi-safi-in {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:local-pref-eq {
      description
          "Not supported in this release";
      deviate not-supported;
  }
  deviation /oc-rpol:routing-policy/oc-rpol:policy-definitions/oc-rpol:policy-definition/oc-rpol:statements/oc-rpol:statement/oc-rpol:conditions/oc-bgp-pol:bgp-conditions/oc-bgp-pol:state/oc-bgp-pol:route-type {
      description
          "Not supported in this release";
      deviate not-supported;
  }
  deviation /oc-rpol:routing-policy/oc-rpol:policy-definitions/oc-rpol:policy-definition/oc-rpol:statements/oc-rpol:statement/oc-rpol:actions/oc-isis-pol:isis-actions/oc-isis-pol:state {
      description
          "Not supported in this release";
      deviate not-supported;
  }
  deviation /oc-rpol:routing-policy/oc-rpol:policy-definitions/oc-rpol:policy-definition/oc-rpol:statements/oc-rpol:statement/oc-rpol:conditions/oc-isis-pol:isis-conditions/oc-isis-pol:state {
      description
          "Not supported in this release";
      deviate not-supported;
  }
  deviation /oc-rpol:routing-policy/oc-rpol:defined-sets/oc-bgp-pol:bgp-defined-sets/oc-bgp-pol:community-sets/oc-bgp-pol:community-set/oc-bgp-pol:config/oc-bgp-pol:match-set-options {
      deviate not-supported;
  }
  deviation /oc-rpol:routing-policy/oc-rpol:defined-sets/oc-bgp-pol:bgp-defined-sets/oc-bgp-pol:ext-community-sets/oc-bgp-pol:ext-community-set/oc-bgp-pol:config/oc-bgp-pol:match-set-options {
      deviate not-supported;
  }
  deviation /oc-rpol:routing-policy/oc-rpol:policy-definitions/oc-rpol:policy-definition/oc-rpol:statements/oc-rpol:statement/oc-rpol:conditions/oc-bgp-pol:bgp-conditions/oc-bgp-pol:as-path-length {
      deviate not-supported;
  }
  deviation /oc-rpol:routing-policy/oc-rpol:policy-definitions/oc-rpol:policy-definition/oc-rpol:statements/oc-rpol:statement/oc-rpol:conditions/oc-bgp-pol:bgp-conditions/oc-bgp-pol:match-as-path-set {
      deviate not-supported;
  }
  deviation /oc-rpol:routing-policy/oc-rpol:policy-definitions/oc-rpol:policy-definition/oc-rpol:statements/oc-rpol:statement/oc-rpol:conditions/oc-bgp-pol:bgp-conditions/oc-bgp-pol:config/oc-bgp-pol:next-hop-in {
      deviate replace {
        type inet:ip-address-no-zone;
      }
  }
  deviation /oc-rpol:routing-policy/oc-rpol:policy-definitions/oc-rpol:policy-definition/oc-rpol:statements/oc-rpol:statement/oc-rpol:conditions/oc-bgp-pol:bgp-conditions/oc-bgp-pol:config/oc-bgp-pol:afi-safi-in {
      deviate add {
          max-elements 1;
      }
  }
  deviation /oc-rpol:routing-policy/oc-rpol:policy-definitions/oc-rpol:policy-definition/oc-rpol:statements/oc-rpol:statement/oc-rpol:actions/oc-bgp-pol:bgp-actions/oc-bgp-pol:config/oc-bgp-pol:set-next-hop {
      deviate replace {
        type inet:ip-address-no-zone;
      }
  }
  deviation /oc-rpol:routing-policy/oc-rpol:policy-definitions/oc-rpol:policy-definition/oc-rpol:statements/oc-rpol:statement/oc-rpol:actions/oc-bgp-pol:bgp-actions/oc-bgp-pol:config/oc-bgp-pol:set-med {
      deviate replace {
         type uint32;
      }
  }
  deviation /oc-rpol:routing-policy/oc-rpol:policy-definitions/oc-rpol:policy-definition/oc-rpol:statements/oc-rpol:statement/oc-rpol:actions/oc-bgp-pol:bgp-actions/oc-bgp-pol:set-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-community/oc-bgp-pol:config/oc-bgp-pol:method {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:inline {
      deviate not-supported;
  }
  deviation /oc-rpol:routing-policy/oc-rpol:policy-definitions/oc-rpol:policy-definition/oc-rpol:statements/oc-rpol:statement/oc-rpol:actions/oc-bgp-pol:bgp-actions/oc-bgp-pol:set-ext-community/oc-bgp-pol:config/oc-bgp-pol:method {
      deviate not-supported;
  }

  deviation /oc-rpol:routing-policy/oc-rpol:defined-sets/oc-rpol:prefix-sets/oc-rpol:prefix-set/oc-rpol:prefixes/oc-rpol:prefix/oc-rpol:config/oc-rpol:masklength-range {
    deviate replace {
      type string {
        pattern '([0-9]+\.\.[0-9]+)|exact';
      }
    }
  }

  deviation /oc-rpol:routing-policy/oc-rpol:defined-sets/oc-rpol:prefix-sets/oc-rpol:prefix-set/oc-rpol:config/oc-rpol:mode {
      deviate not-supported;
  }


  deviation /oc-rpol:routing-policy/oc-rpol:policy-definitions/oc-rpol:policy-definition/oc-rpol:statements/oc-rpol:statement/oc-rpol:conditions/oc-rpol:match-neighbor-set/oc-rpol:state/oc-rpol:match-set-options {
      deviate not-supported;
  }
  deviation /oc-rpol:routing-policy/oc-rpol:policy-definitions/oc-rpol:policy-definition/oc-rpol:statements/oc-rpol:statement/oc-rpol:conditions/oc-rpol:match-tag-set/oc-rpol:state/oc-rpol:tag-set {
      deviate not-supported;
  }
  deviation /oc-rpol:routing-policy/oc-rpol:policy-definitions/oc-rpol:policy-definition/oc-rpol:statements/oc-rpol:statement/oc-rpol:conditions/oc-rpol:match-tag-set/oc-rpol:state/oc-rpol:match-set-options {
      deviate not-supported;
  }
  deviation /oc-rpol:routing-policy/oc-rpol:defined-sets/oc-rpol:neighbor-sets/oc-rpol:neighbor-set/oc-rpol:state {
      deviate not-supported;
  }
  deviation /oc-rpol:routing-policy/oc-rpol:defined-sets/oc-rpol:tag-sets/oc-rpol:tag-set/oc-rpol:state {
      deviate not-supported;
  }
  deviation /oc-rpol:routing-policy/oc-rpol:policy-definitions/oc-rpol:policy-definition/oc-rpol:statements/oc-rpol:statement/oc-rpol:conditions/oc-rpol:match-neighbor-set/oc-rpol:state {
      deviate not-supported;
  }
  deviation /oc-rpol:routing-policy/oc-rpol:policy-definitions/oc-rpol:policy-definition/oc-rpol:statements/oc-rpol:statement/oc-rpol:conditions/oc-rpol:match-tag-set/oc-rpol:state {
      deviate not-supported;
  }


  // OSPF policy Deviation

  deviation "/oc-rpol:routing-policy/oc-rpol:policy-definitions/oc-rpol:policy-definition/oc-rpol:statements/oc-rpol:statement/" +
             "oc-rpol:actions/oc-ospf-pol:ospf-actions" {
      description
        "Not supported in this version";
      deviate not-supported;
  }

  deviation "/oc-rpol:routing-policy/oc-rpol:policy-definitions/oc-rpol:policy-definition/oc-rpol:statements/oc-rpol:statement/" +
             "oc-rpol:conditions/oc-ospf-pol:ospf-conditions" {
      description
        "Not supported in this version";
      deviate not-supported;
  }

  deviation "/oc-ni:network-instances/oc-ni:network-instance/oc-ni:policy-forwarding/oc-ni:interfaces/oc-ni:interface/oc-ni:interface-ref/oc-ni:config/oc-ni:interface"{
      deviate add {
          mandatory true;
      }
  }

  deviation "/oc-ni:network-instances/oc-ni:network-instance/oc-ni:policy-forwarding/oc-ni:interfaces/oc-ni:interface/oc-ni:interface-ref/oc-ni:config/oc-ni:subinterface"{
      deviate add {
          mandatory true;
      }
  }

  // Deviations of oc-vlan under oc-if

  deviation "/oc-if:interfaces/oc-if:interface/oc-if:subinterfaces/oc-if:subinterface/oc-vlan:vlan/" +
            "oc-vlan:match/oc-vlan:double-tagged-outer-list" {
    description
      "Junos support is not yet added for double-tagged-outer-list";
    deviate not-supported;
  }

  deviation "/oc-if:interfaces/oc-if:interface/oc-if:subinterfaces/oc-if:subinterface/oc-vlan:vlan/" +
            "oc-vlan:match/oc-vlan:double-tagged-outer-range" {
    description
      "Junos support is not yet added for double-tagged-outer-range";
    deviate not-supported;
  }

  deviation "/oc-if:interfaces/oc-if:interface/oc-if:subinterfaces/oc-if:subinterface/oc-vlan:vlan/" +
            "oc-vlan:match/oc-vlan:double-tagged-inner-outer-range" {
    description
      "Junos support is not yet added for double-tagged-inner-outer-range";
    deviate not-supported;
  }

  // Deviations of oc-tun under oc-if

  deviation "/oc-if:interfaces/oc-if:interface/oc-tun:tunnel/oc-tun:state" {
    description
      "Junos support tunnels at subinterfaces level";
      deviate not-supported;
  }

  deviation "/oc-if:interfaces/oc-if:interface/oc-tun:tunnel/oc-tun:ipv4/oc-tun:addresses/" +
            "oc-tun:address/oc-tun:ip" {
      deviate replace {
          type inet:ipv4-address-no-zone;
      }
  }

  deviation "/oc-if:interfaces/oc-if:interface/oc-tun:tunnel/oc-tun:ipv4/oc-tun:addresses/" +
            "oc-tun:address/oc-tun:state" {
    description
      "Junos support tunnels at subinterfaces level";
      deviate not-supported;
  }

  deviation "/oc-if:interfaces/oc-if:interface/oc-tun:tunnel/oc-tun:ipv4/oc-tun:proxy-arp" {
    description
      "Feature not supported in this release";
    deviate not-supported;
  }

  deviation "/oc-if:interfaces/oc-if:interface/oc-tun:tunnel/oc-tun:ipv4/oc-tun:neighbors" {
    description
      "Feature not supported in this release";
    deviate not-supported;
  }

  deviation "/oc-if:interfaces/oc-if:interface/oc-tun:tunnel/oc-tun:ipv4/oc-tun:unnumbered" {
    description
      "Junos support tunnels at subinterfaces level";
    deviate not-supported;
  }

  deviation "/oc-if:interfaces/oc-if:interface/oc-tun:tunnel/oc-tun:ipv4/oc-tun:config/oc-tun:dhcp-client" {
    description
      "Feature not supported in this release";
    deviate not-supported;
  }

  deviation "/oc-if:interfaces/oc-if:interface/oc-tun:tunnel/oc-tun:ipv4/oc-tun:state" {
    description
      "Junos support tunnels at subinterfaces level";
    deviate not-supported;
  }

  deviation "/oc-if:interfaces/oc-if:interface/oc-tun:tunnel/oc-tun:ipv6/oc-tun:addresses/" +
            "oc-tun:address/oc-tun:state" {
    description
      "Junos support tunnels at subinterfaces level";
      deviate not-supported;
  }

  deviation "/oc-if:interfaces/oc-if:interface/oc-tun:tunnel/oc-tun:ipv6/oc-tun:router-advertisement" {
    description
      "Feature not supported in this release";
    deviate not-supported;
  }

  deviation "/oc-if:interfaces/oc-if:interface/oc-tun:tunnel/oc-tun:ipv6/oc-tun:neighbors" {
    description
      "Feature not supported in this release";
    deviate not-supported;
  }

  deviation "/oc-if:interfaces/oc-if:interface/oc-tun:tunnel/oc-tun:ipv6/oc-tun:unnumbered" {
    description
      "Junos support tunnels at subinterfaces level";
    deviate not-supported;
  }

  deviation "/oc-if:interfaces/oc-if:interface/oc-tun:tunnel/oc-tun:ipv6/oc-tun:config/oc-tun:dup-addr-detect-transmits" {
    description
      "Feature not supported in this release";
    deviate not-supported;
  }

  deviation "/oc-if:interfaces/oc-if:interface/oc-tun:tunnel/oc-tun:ipv6/oc-tun:config/oc-tun:dhcp-client" {
    description
      "Feature Not supported in this release";
    deviate not-supported;
  }

  deviation "/oc-if:interfaces/oc-if:interface/oc-tun:tunnel/oc-tun:ipv6/oc-tun:state" {
    description
      "Junos support tunnels at subinterfaces level";
    deviate not-supported;
  }

  // NETWORK-INSTANCE Deviations

  deviation /oc-ni:network-instances/oc-ni:network-instance/oc-ni:encapsulation {
      deviate not-supported;
  }

  deviation /oc-ni:network-instances/oc-ni:network-instance/oc-ni:tables {
      deviate not-supported;
  }

  // Network instance - Segment-routing deviations

  // Te-policy
  deviation /oc-ni:network-instances/oc-ni:network-instance/oc-ni:segment-routing/oc-ni:te-policies/oc-ni:te-policy/oc-ni:state/oc-ni:name {
      deviate not-supported;
  }

  deviation /oc-ni:network-instances/oc-ni:network-instance/oc-ni:segment-routing/oc-ni:te-policies/oc-ni:te-policy/oc-ni:candidate-paths/oc-ni:candidate-path/oc-ni:segment-lists/oc-ni:segment-list/oc-ni:next-hops {
          deviate not-supported;
  }

  deviation /oc-ni:network-instances/oc-ni:network-instance/oc-ni:segment-routing/oc-ni:te-policies/oc-ni:te-policy/oc-ni:state/oc-ni:counters/oc-ni:out-pkts {
        deviate not-supported;
  }

  deviation /oc-ni:network-instances/oc-ni:network-instance/oc-ni:segment-routing/oc-ni:te-policies/oc-ni:te-policy/oc-ni:state/oc-ni:counters/oc-ni:out-octets {
        deviate not-supported;
  }

  deviation /oc-ni:network-instances/oc-ni:network-instance/oc-ni:segment-routing/oc-ni:te-policies/oc-ni:te-policy/oc-ni:state/oc-ni:counters/oc-ni:out-labeled-pkts {
        deviate not-supported;
  }

  deviation /oc-ni:network-instances/oc-ni:network-instance/oc-ni:segment-routing/oc-ni:te-policies/oc-ni:te-policy/oc-ni:state/oc-ni:counters/oc-ni:out-labeled-octets {
        deviate not-supported;
  }

  // Segment routing: sr-structural
  deviation /oc-ni:network-instances/oc-ni:network-instance/oc-ni:segment-routing/oc-ni:srgbs {
      deviate not-supported;
  }

  deviation /oc-ni:network-instances/oc-ni:network-instance/oc-ni:segment-routing/oc-ni:srlbs {
      deviate not-supported;
  }

  deviation /oc-ni:network-instances/oc-ni:network-instance/oc-ni:table-connections {
      deviate not-supported;
  }

  deviation /oc-ni:network-instances/oc-ni:network-instance/oc-ni:connection-points {
      deviate not-supported;
  }

  // Network-instance config and state
  deviation /oc-ni:network-instances/oc-ni:network-instance/oc-ni:config/oc-ni:fallback-network-instance {
      deviate not-supported;
  }
  deviation /oc-ni:network-instances/oc-ni:network-instance/oc-ni:state/oc-ni:fallback-network-instance {
      deviate not-supported;
  }
  deviation /oc-ni:network-instances/oc-ni:network-instance/oc-ni:config/oc-ni:enabled-address-families {
      deviate not-supported;
  }
  deviation /oc-ni:network-instances/oc-ni:network-instance/oc-ni:state/oc-ni:enabled-address-families {
      deviate not-supported;
  }

  deviation /oc-ni:network-instances/oc-ni:network-instance/oc-ni:config/oc-ni:mtu {
      deviate not-supported;
  }
  deviation /oc-ni:network-instances/oc-ni:network-instance/oc-ni:state/oc-ni:mtu {
      deviate not-supported;
  }

  deviation /oc-ni:network-instances/oc-ni:network-instance/oc-ni:config/oc-ni:type {
      description
            "Junos does not support network-instance name without specifying network-instance type.";
      deviate add {
          mandatory true;
      }
  }

  deviation /oc-ni:network-instances/oc-ni:network-instance/oc-ni:protocols/oc-ni:protocol/oc-ni:state/oc-ni:default-metric {
      deviate not-supported;
  }

  // NETWORK-INSTANCE INTERFACE CONFIG/STATES DEVIATION:

  deviation "/oc-ni:network-instances/oc-ni:network-instance/oc-ni:interfaces/oc-ni:interface/oc-ni:config/oc-ni:associated-address-families"{
        description
          "associated-address-families not supported";
        deviate not-supported;
  }

  deviation "/oc-ni:network-instances/oc-ni:network-instance/oc-ni:interfaces/oc-ni:interface/oc-ni:state/oc-ni:associated-address-families"{
        description
          "associated-address-families telemetry not supported";
        deviate not-supported;
  }  


  // ISIS deviation
  deviation  "/oc-ni:network-instances/oc-ni:network-instance/oc-ni:protocols/oc-ni:protocol" +
  "/oc-ni:isis/oc-ni:global/oc-ni:afi-safi/oc-ni:af/oc-ni:multi-topology" {
    deviate not-supported;
  }

  deviation  "/oc-ni:network-instances/oc-ni:network-instance/oc-ni:protocols/oc-ni:protocol" +
  "/oc-ni:isis/oc-ni:global/oc-ni:graceful-restart" {
    deviate not-supported;
  }

  deviation  "/oc-ni:network-instances/oc-ni:network-instance/oc-ni:protocols/oc-ni:protocol" +
  "/oc-ni:isis/oc-ni:global/oc-ni:igp-shortcuts" {
    deviate not-supported;
  }

  deviation  "/oc-ni:network-instances/oc-ni:network-instance/oc-ni:protocols/oc-ni:protocol" +
  "/oc-ni:isis/oc-ni:global/oc-ni:inter-level-propagation-policies" {
    deviate not-supported;
  }

  deviation  "/oc-ni:network-instances/oc-ni:network-instance/oc-ni:protocols/oc-ni:protocol" +
  "/oc-ni:isis/oc-ni:global/oc-ni:mpls/oc-ni:igp-ldp-sync/oc-ni:state" {
    deviate not-supported;
  }

  deviation  "/oc-ni:network-instances/oc-ni:network-instance/oc-ni:protocols/oc-ni:protocol" +
  "/oc-ni:isis/oc-ni:global/oc-ni:nsr" {
    deviate not-supported;
  }

  deviation  "/oc-ni:network-instances/oc-ni:network-instance/oc-ni:protocols/oc-ni:protocol" +
  "/oc-ni:isis/oc-ni:global/oc-ni:segment-routing" {
    deviate not-supported;
  }


  deviation  "/oc-ni:network-instances/oc-ni:network-instance/oc-ni:protocols/oc-ni:protocol" +
  "/oc-ni:isis/oc-ni:global/oc-ni:config/oc-ni:fast-flooding" {
    deviate not-supported;
  }

  deviation  "/oc-ni:network-instances/oc-ni:network-instance/oc-ni:protocols/oc-ni:protocol" +
  "/oc-ni:isis/oc-ni:global/oc-ni:config/oc-ni:iid-tlv" {
    deviate not-supported;
  }

  deviation  "/oc-ni:network-instances/oc-ni:network-instance/oc-ni:protocols/oc-ni:protocol" +
  "/oc-ni:isis/oc-ni:global/oc-ni:config/oc-ni:max-ecmp-paths" {
    deviate not-supported;
  }

  deviation  "/oc-ni:network-instances/oc-ni:network-instance/oc-ni:protocols/oc-ni:protocol" +
  "/oc-ni:isis/oc-ni:global/oc-ni:config/oc-ni:poi-tlv" {
    deviate not-supported;
  }

  deviation  "/oc-ni:network-instances/oc-ni:network-instance/oc-ni:protocols/oc-ni:protocol" +
  "/oc-ni:isis/oc-ni:global/oc-ni:timers/oc-ni:lsp-generation" {
    deviate not-supported;
  }


  deviation  "/oc-ni:network-instances/oc-ni:network-instance/oc-ni:protocols/oc-ni:protocol" +
  "/oc-ni:isis/oc-ni:global/oc-ni:timers/oc-ni:spf/oc-ni:config/oc-ni:spf-second-interval" {
    deviate not-supported;
  }

  deviation  "/oc-ni:network-instances/oc-ni:network-instance/oc-ni:protocols/oc-ni:protocol" +
  "/oc-ni:isis/oc-ni:global/oc-ni:lsp-bit/oc-ni:attached-bit/oc-ni:state/oc-ni:suppress-bit" {
    deviate not-supported;
  }

  deviation  "/oc-ni:network-instances/oc-ni:network-instance/oc-ni:protocols/oc-ni:protocol" +
  "/oc-ni:isis/oc-ni:global/oc-ni:lsp-bit/oc-ni:overload-bit/oc-ni:reset-triggers/oc-ni:reset-trigger/oc-ni:state" {
    deviate not-supported;
  }

  deviation "/oc-ni:network-instances/oc-ni:network-instance/oc-ni:protocols/oc-ni:protocol/" +
  "oc-ni:isis/oc-ni:global/oc-ni:lsp-bit/oc-ni:overload-bit/oc-ni:state/" +
  "oc-ni:set-bit-on-boot" {
      deviate not-supported;
  }

  deviation "/oc-ni:network-instances/oc-ni:network-instance/oc-ni:protocols/oc-ni:protocol/" +
  "oc-ni:isis/oc-ni:global/oc-ni:timers/oc-ni:spf/oc-ni:state/oc-ni:spf-second-interval" {
      deviate not-supported;
  }

  deviation "/oc-ni:network-instances/oc-ni:network-instance/oc-ni:protocols/oc-ni:protocol/" +
  "oc-ni:isis/oc-ni:global/oc-ni:timers/oc-ni:spf/oc-ni:state/oc-ni:adaptive-timer" {
      deviate not-supported;
  }

  deviation  "/oc-ni:network-instances/oc-ni:network-instance/oc-ni:protocols/oc-ni:protocol" +
   "/oc-ni:isis/oc-ni:global/oc-ni:state/oc-ni:max-ecmp-paths" {
      deviate not-supported;
  }

  deviation  "/oc-ni:network-instances/oc-ni:network-instance/oc-ni:protocols/oc-ni:protocol" +
   "/oc-ni:isis/oc-ni:global/oc-ni:state/oc-ni:poi-tlv" {
      deviate not-supported;
  }

  deviation "/oc-ni:network-instances/oc-ni:network-instance/oc-ni:protocols/oc-ni:protocol" +
   "/oc-ni:isis/oc-ni:global/oc-ni:state/oc-ni:iid-tlv" {
      deviate not-supported;
  }

  deviation  "/oc-ni:network-instances/oc-ni:network-instance/oc-ni:protocols/oc-ni:protocol" +
   "/oc-ni:isis/oc-ni:global/oc-ni:state/oc-ni:fast-flooding" {
      deviate not-supported;
  }

  deviation  "/oc-ni:network-instances/oc-ni:network-instance/oc-ni:protocols/oc-ni:protocol" +
   "/oc-ni:isis/oc-ni:global/oc-ni:afi-safi/oc-ni:af/oc-ni:state/oc-ni:metric" {
      deviate not-supported;
  }

  deviation  "/oc-ni:network-instances/oc-ni:network-instance/oc-ni:protocols/oc-ni:protocol" +
   "/oc-ni:isis/oc-ni:global/oc-ni:config/oc-ni:csnp-enable-on-p2p-links" {
      deviate not-supported;
  }

  deviation  "/oc-ni:network-instances/oc-ni:network-instance/oc-ni:protocols/oc-ni:protocol" +
   "/oc-ni:isis/oc-ni:global/oc-ni:state/oc-ni:csnp-enable-on-p2p-links" {
      deviate not-supported;
  }

  deviation  "/oc-ni:network-instances/oc-ni:network-instance/oc-ni:protocols/oc-ni:protocol" +
   "/oc-ni:isis/oc-ni:global/oc-ni:afi-safi/oc-ni:af/oc-ni:config/oc-ni:max-ecmp-paths" {
      deviate not-supported;
  }

  deviation  "/oc-ni:network-instances/oc-ni:network-instance/oc-ni:protocols/oc-ni:protocol" +
   "/oc-ni:isis/oc-ni:global/oc-ni:afi-safi/oc-ni:af/oc-ni:state/oc-ni:max-ecmp-paths" {
      deviate not-supported;
  }

  deviation  "/oc-ni:network-instances/oc-ni:network-instance/oc-ni:protocols/oc-ni:protocol" +
   "/oc-ni:isis/oc-ni:global/oc-ni:config/oc-ni:instance-id" {
      deviate not-supported;
  }

  deviation  "/oc-ni:network-instances/oc-ni:network-instance/oc-ni:protocols/oc-ni:protocol" +
   "/oc-ni:isis/oc-ni:global/oc-ni:state/oc-ni:instance-id" {
      deviate not-supported;
  }

  deviation  "/oc-ni:network-instances/oc-ni:network-instance/oc-ni:protocols/oc-ni:protocol" +
   "/oc-ni:isis/oc-ni:global/oc-ni:config/oc-ni:weighted-ecmp" {
      deviate not-supported;
  }

  deviation  "/oc-ni:network-instances/oc-ni:network-instance/oc-ni:protocols/oc-ni:protocol" +
   "/oc-ni:isis/oc-ni:global/oc-ni:state/oc-ni:weighted-ecmp" {
      deviate not-supported;
  }

  deviation  "/oc-ni:network-instances/oc-ni:network-instance/oc-ni:protocols/oc-ni:protocol" +
   "/oc-ni:isis/oc-ni:interfaces/oc-ni:interface/oc-ni:weighted-ecmp" {
      deviate not-supported;
  }

  deviation  "/oc-ni:network-instances/oc-ni:network-instance/oc-ni:protocols/oc-ni:protocol" +
   "/oc-ni:isis/oc-ni:levels/oc-ni:level/oc-ni:authentication/oc-ni:state/oc-ni:keychain" {
      deviate not-supported;
  }

  deviation  "/oc-ni:network-instances/oc-ni:network-instance/oc-ni:protocols/oc-ni:protocol" +
   "/oc-ni:isis/oc-ni:interfaces/oc-ni:interface/oc-ni:levels/oc-ni:level/oc-ni:afi-safi/oc-ni:af/oc-ni:state/oc-ni:enabled" {
      deviate not-supported;
  }

  deviation  "/oc-ni:network-instances/oc-ni:network-instance/oc-ni:protocols/oc-ni:protocol" +
    "/oc-ni:isis/oc-ni:interfaces/oc-ni:interface/oc-ni:levels/oc-ni:level/oc-ni:hello-authentication/oc-ni:state/oc-ni:keychain" {
      deviate not-supported;
  }

  deviation  "/oc-ni:network-instances/oc-ni:network-instance/oc-ni:protocols/oc-ni:protocol" +
  "/oc-ni:isis/oc-ni:interfaces/oc-ni:interface/oc-ni:levels/oc-ni:level/oc-ni:afi-safi" +
  "/oc-ni:af/oc-ni:segment-routing" {
     deviate not-supported;
  }


  deviation  "/oc-ni:network-instances/oc-ni:network-instance/oc-ni:protocols/oc-ni:protocol" +
  "/oc-ni:isis/oc-ni:levels/oc-ni:level/oc-ni:link-state-database/oc-ni:lsp/oc-ni:tlvs" +
  "/oc-ni:tlv/oc-ni:extended-is-reachability/oc-ni:neighbors/oc-ni:neighbor/oc-ni:instances/oc-ni:instance" +
  "/oc-ni:state/oc-ni:id" {

    deviate not-supported;
  }


  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:instance-ids" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:purge-oi" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:authentication" {
      
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:isis-neighbor-attribute" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isis-neighbor-attribute" {
     
      deviate not-supported;
  }  

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:is-alias-id" {
     
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:link-protection-type" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-is-reachability/oc-ni:neighbors/oc-ni:neighbor/oc-ni:instances/oc-ni:instance/oc-ni:subtlvs/oc-ni:subtlv" +
  "/oc-ni:unconstrained-lsp" {

      deviate not-supported;
  }

  deviation "/oc-ni:network-instances/oc-ni:network-instance/oc-ni:protocols/oc-ni:protocol"  +
  "/oc-ni:isis/oc-ni:levels/oc-ni:level/oc-ni:authentication/oc-ni:config" +
  "/oc-ni:keychain" {
        deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:extended-ipv4-reachability/oc-ni:prefixes/oc-ni:prefix/oc-ni:subtlvs/oc-ni:subtlv" +
  "/oc-ni:tag64" {
      
      deviate not-supported;
  } 


  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:ipv6-reachability/oc-ni:prefixes/oc-ni:prefix/oc-ni:subtlvs/oc-ni:subtlv" +
  "/oc-ni:tag64" {
      
      deviate not-supported;
  } 


  deviation "/oc-ni:network-instances/oc-ni:network-instance/oc-ni:protocols/oc-ni:protocol" +
  "/oc-ni:isis/oc-ni:levels/oc-ni:level/oc-ni:state/oc-ni:authentication-check" {
      
      deviate not-supported;
  }

  deviation "/oc-ni:network-instances/oc-ni:network-instance/oc-ni:protocols/oc-ni:protocol" +
  "/oc-ni:isis/oc-ni:levels/oc-ni:level/oc-ni:traffic-engineering" {
      
      deviate not-supported;
  }

  deviation "/oc-ni:network-instances/oc-ni:network-instance/oc-ni:protocols/oc-ni:protocol" +
  "/oc-ni:isis/oc-ni:levels/oc-ni:level/oc-ni:route-preference/oc-ni:state" {
      deviate not-supported;
  }

  deviation "/oc-ni:network-instances/oc-ni:network-instance/oc-ni:protocols/oc-ni:protocol" +
  "/oc-ni:isis/oc-ni:levels/oc-ni:level/oc-ni:route-preference/oc-ni:config/oc-ni:external-route-preference" {
      deviate not-supported;
  }

  deviation "/oc-ni:network-instances/oc-ni:network-instance/oc-ni:protocols/oc-ni:protocol" +
  "/oc-ni:isis/oc-ni:levels/oc-ni:level/oc-ni:config/oc-ni:authentication-check" {

      deviate not-supported;
  }

  deviation "/oc-ni:network-instances/oc-ni:network-instance/oc-ni:protocols/oc-ni:protocol" +
  "/oc-ni:isis/oc-ni:interfaces/oc-ni:interface/oc-ni:levels/oc-ni:level" +
  "/oc-ni:hello-authentication/oc-ni:config/oc-ni:keychain" {
     deviate not-supported;
   }

  deviation "/oc-ni:network-instances/oc-ni:network-instance/oc-ni:protocols/oc-ni:protocol" +
  "/oc-ni:isis/oc-ni:interfaces/oc-ni:interface/oc-ni:bfd/oc-ni:config" {

      deviate not-supported;
  }

  deviation "/oc-ni:network-instances/oc-ni:network-instance/oc-ni:protocols/oc-ni:protocol" +
  "/oc-ni:isis/oc-ni:interfaces/oc-ni:interface/oc-ni:interface-ref" {
      
      deviate not-supported;
  }

  deviation "/oc-ni:network-instances/oc-ni:network-instance/oc-ni:protocols/oc-ni:protocol/" +
  "oc-ni:isis/oc-ni:interfaces/oc-ni:interface/oc-ni:authentication/oc-ni:state" {
      deviate not-supported;
  }

  deviation "/oc-ni:network-instances/oc-ni:network-instance/oc-ni:protocols/oc-ni:protocol/" +
  "oc-ni:isis/oc-ni:interfaces/oc-ni:interface/oc-ni:enable-bfd/oc-ni:state" {
      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isn/oc-ni:neighbors/oc-ni:neighbor/oc-ni:instances/oc-ni:instance/oc-ni:subtlvs/" +
  "oc-ni:subtlv/oc-ni:link-protection-type" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-isn/oc-ni:neighbors/oc-ni:neighbor/oc-ni:instances/oc-ni:instance/oc-ni:subtlvs/" +
  "oc-ni:subtlv/oc-ni:unconstrained-lsp" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv4-reachability/oc-ni:prefixes/oc-ni:prefix/oc-ni:subtlvs/oc-ni:subtlv/oc-ni:tag64" {

      deviate not-supported;
  }

  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv4-reachability/oc-ni:prefixes/oc-ni:prefix/oc-ni:undefined-subtlvs" {

      deviate not-supported;
  }


  deviation "/oc-ni:network-instances/oc-ni:network-instance/oc-ni:protocols/oc-ni:protocol" +
  "/oc-ni:isis/oc-ni:levels/oc-ni:level/oc-ni:link-state-database/oc-ni:lsp/oc-ni:tlvs/oc-ni:tlv" +
  "/oc-ni:mt-ipv6-reachability/oc-ni:prefixes/oc-ni:prefix/oc-ni:subtlvs/oc-ni:subtlv/oc-ni:tag64" {

      deviate not-supported;
  }

  deviation /oc-if:interfaces/oc-if:interface/oc-if:config/oc-if:type {
    description
        "Right now multi-level identityref is not supported in Junos,
         Till this support is added, we can't use identityref for leaf type";
    deviate replace {
       type string;
    }
 }

  // Network-Instance - MPLS Deviations
  
  // Global
  deviation /oc-ni:network-instances/oc-ni:network-instance/oc-ni:mpls/oc-ni:global/oc-ni:interface-attributes/oc-ni:interface/oc-ni:interface-ref/oc-ni:config {
      deviate not-supported;
  }
  deviation /oc-ni:network-instances/oc-ni:network-instance/oc-ni:mpls/oc-ni:global/oc-ni:reserved-label-blocks {
      deviate not-supported;
  }
  deviation /oc-ni:network-instances/oc-ni:network-instance/oc-ni:mpls/oc-ni:global/oc-ni:config/oc-ni:pw-encapsulation {
      deviate not-supported;
      description "Not supported in this release";
  }
  deviation /oc-ni:network-instances/oc-ni:network-instance/oc-ni:mpls/oc-ni:global/oc-ni:state/oc-ni:pw-encapsulation {
      deviate not-supported;
  }

  // Signaling-Protocols

  deviation /oc-ni:network-instances/oc-ni:network-instance/oc-ni:mpls/oc-ni:signaling-protocols/oc-ni:segment-routing/oc-ni:aggregate-sid-counters/oc-ni:aggregate-sid-counter/oc-ni:state/oc-ni:mpls-label {
     deviate not-supported;
  }

  deviation /oc-ni:network-instances/oc-ni:network-instance/oc-ni:mpls/oc-ni:signaling-protocols/oc-ni:segment-routing/oc-ni:aggregate-sid-counters/oc-ni:aggregate-sid-counter/oc-ni:state/oc-ni:out-pkts {
     deviate not-supported;
  }

  deviation /oc-ni:network-instances/oc-ni:network-instance/oc-ni:mpls/oc-ni:signaling-protocols/oc-ni:segment-routing/oc-ni:aggregate-sid-counters/oc-ni:aggregate-sid-counter/oc-ni:state/oc-ni:out-octets {
     deviate not-supported;
  }

  deviation /oc-ni:network-instances/oc-ni:network-instance/oc-ni:mpls/oc-ni:signaling-protocols/oc-ni:ldp/oc-ni:global/oc-ni:graceful-restart/oc-ni:config/oc-ni:forwarding-holdtime {
       deviate not-supported;
  }
  deviation /oc-ni:network-instances/oc-ni:network-instance/oc-ni:mpls/oc-ni:signaling-protocols/oc-ni:ldp/oc-ni:interface-attributes/oc-ni:interfaces/oc-ni:interface/oc-ni:interface-ref/oc-ni:config {
       deviate not-supported;
   }
  deviation /oc-ni:network-instances/oc-ni:network-instance/oc-ni:mpls/oc-ni:signaling-protocols/oc-ni:ldp/oc-ni:interface-attributes/oc-ni:interfaces/oc-ni:interface/oc-ni:state/oc-ni:counters {
       deviate not-supported;
   }
    deviation /oc-ni:network-instances/oc-ni:network-instance/oc-ni:mpls/oc-ni:signaling-protocols/oc-ni:ldp/oc-ni:interface-attributes/oc-ni:interfaces/oc-ni:interface/oc-ni:address-families/oc-ni:address-family/oc-ni:config {
       deviate not-supported;
   }
   deviation /oc-ni:network-instances/oc-ni:network-instance/oc-ni:mpls/oc-ni:signaling-protocols/oc-ni:ldp/oc-ni:targeted/oc-ni:address-families/oc-ni:address-family/oc-ni:config {
       deviate not-supported;
   }
   deviation /oc-ni:network-instances/oc-ni:network-instance/oc-ni:mpls/oc-ni:signaling-protocols/oc-ni:ldp/oc-ni:targeted/oc-ni:address-families/oc-ni:address-family/oc-ni:targets/oc-ni:target/oc-ni:config {
       deviate not-supported;
   }

  // Signaling-Protocols - RSVP - Global
  deviation /oc-ni:network-instances/oc-ni:network-instance/oc-ni:mpls/oc-ni:signaling-protocols/oc-ni:rsvp-te/oc-ni:global/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:global/oc-ni:soft-preemption/oc-ni:config/oc-ni:soft-preemption-timeout {
      deviate replace {
          type uint16 {
              range 1..180;
          }
          default 30;
      }
  }
  deviation /oc-ni:network-instances/oc-ni:network-instance/oc-ni:mpls/oc-ni:signaling-protocols/oc-ni:rsvp-te/oc-ni:global/oc-ni:graceful-restart/oc-ni:config/oc-ni:restart-time {
      deviate replace {
          type uint32 {
              range 1..1800;
          }
      }
  }
  deviation /oc-ni:network-instances/oc-ni:network-instance/oc-ni:mpls/oc-ni:signaling-protocols/oc-ni:rsvp-te/oc-ni:global/oc-ni:graceful-restart/oc-ni:config/oc-ni:recovery-time {
      deviate replace {
          type uint32 {
              range 1..3600;
          }
      }
  }

  // Signaling-Protocols - RSVP - Sessions
  deviation /oc-ni:network-instances/oc-ni:network-instance/oc-ni:mpls/oc-ni:signaling-protocols/oc-ni:rsvp-te/oc-ni:sessions/oc-ni:session/oc-ni:state/oc-ni:local-index {
      deviate replace {
          type uint32;
      }
  }
  deviation /oc-ni:network-instances/oc-ni:network-instance/oc-ni:mpls/oc-ni:signaling-protocols/oc-ni:rsvp-te/oc-ni:sessions/oc-ni:session/oc-ni:explicit-route-objects/oc-ni:explicit-route-object/oc-ni:state/oc-ni:asn {
      deviate not-supported;
  }
  deviation /oc-ni:network-instances/oc-ni:network-instance/oc-ni:mpls/oc-ni:signaling-protocols/oc-ni:rsvp-te/oc-ni:sessions/oc-ni:session/oc-ni:explicit-route-objects/oc-ni:explicit-route-object/oc-ni:state/oc-ni:label {
      deviate not-supported;
  }

  // Signaling-Protocols - RSVP - Interface Attributes
  deviation /oc-ni:network-instances/oc-ni:network-instance/oc-ni:mpls/oc-ni:signaling-protocols/oc-ni:rsvp-te/oc-ni:interface-attributes/oc-ni:interface/oc-ni:hellos/oc-ni:config/oc-ni:hello-interval {
      deviate replace {
          type uint16 {
              range 1..60;
          }
          units seconds;
          default 9;
      }
  }
  deviation /oc-ni:network-instances/oc-ni:network-instance/oc-ni:mpls/oc-ni:signaling-protocols/oc-ni:rsvp-te/oc-ni:interface-attributes/oc-ni:interface/oc-ni:interface-ref/oc-ni:config {
      deviate not-supported;
  }
  deviation /oc-ni:network-instances/oc-ni:network-instance/oc-ni:mpls/oc-ni:signaling-protocols/oc-ni:rsvp-te/oc-ni:interface-attributes/oc-ni:interface/oc-ni:state/oc-ni:counters/oc-ni:errors/oc-ni:transmit-queue-full {
      deviate not-supported;
  }
  deviation /oc-ni:network-instances/oc-ni:network-instance/oc-ni:mpls/oc-ni:signaling-protocols/oc-ni:rsvp-te/oc-ni:interface-attributes/oc-ni:interface/oc-ni:state/oc-ni:counters/oc-ni:rate-limited-messages {
      deviate not-supported;
  }
  // TE Global Attributes
  deviation /oc-ni:network-instances/oc-ni:network-instance/oc-ni:mpls/oc-ni:te-global-attributes/oc-ni:srlgs/oc-ni:srlg/oc-ni:static-srlg-members/oc-ni:members-list/oc-ni:config/oc-ni:to-address {
	  deviate replace {
		  type inet:ip-address;
	  }
  }
  deviation /oc-ni:network-instances/oc-ni:network-instance/oc-ni:mpls/oc-ni:te-global-attributes/oc-ni:srlgs/oc-ni:srlg/oc-ni:config/oc-ni:cost {
      deviate replace {
          type uint32 {
              range 1..65535;
          }
      }
  }
  deviation /oc-ni:network-instances/oc-ni:network-instance/oc-ni:mpls/oc-ni:te-global-attributes/oc-ni:srlgs/oc-ni:srlg/oc-ni:config/oc-ni:value {
      deviate replace {
          type uint32 {
              range 1..max;
          }
      }
  }
  deviation /oc-ni:network-instances/oc-ni:network-instance/oc-ni:mpls/oc-ni:te-global-attributes/oc-ni:srlgs/oc-ni:srlg/oc-ni:config/oc-ni:name {
      deviate replace {
          type string {
              length 1..64;
          }
      }
  }
  deviation /oc-ni:network-instances/oc-ni:network-instance/oc-ni:mpls/oc-ni:te-global-attributes/oc-ni:te-lsp-timers/oc-ni:config/oc-ni:install-delay {
      deviate replace {
          type uint16 {
              range 1..900;
          }
      }
  }
  // TE Interface Attributes
  deviation /oc-ni:network-instances/oc-ni:network-instance/oc-ni:mpls/oc-ni:te-interface-attributes/oc-ni:interface/oc-ni:config/oc-ni:te-metric {
      deviate not-supported;
  }
  deviation /oc-ni:network-instances/oc-ni:network-instance/oc-ni:mpls/oc-ni:te-interface-attributes/oc-ni:interface/oc-ni:state/oc-ni:te-metric {
      deviate not-supported;
  }
  deviation /oc-ni:network-instances/oc-ni:network-instance/oc-ni:mpls/oc-ni:te-interface-attributes/oc-ni:interface/oc-ni:igp-flooding-bandwidth/oc-ni:config/oc-ni:threshold-specification {
      deviate not-supported;
  }
  deviation /oc-ni:network-instances/oc-ni:network-instance/oc-ni:mpls/oc-ni:te-interface-attributes/oc-ni:interface/oc-ni:igp-flooding-bandwidth/oc-ni:state/oc-ni:threshold-specification {
      deviate not-supported;
  }
  deviation /oc-ni:network-instances/oc-ni:network-instance/oc-ni:mpls/oc-ni:te-interface-attributes/oc-ni:interface/oc-ni:igp-flooding-bandwidth/oc-ni:config/oc-ni:delta-percentage {
      deviate replace {
        type uint8 {
            range 1..20;
        }
      }
  }
  deviation /oc-ni:network-instances/oc-ni:network-instance/oc-ni:mpls/oc-ni:te-interface-attributes/oc-ni:interface/oc-ni:igp-flooding-bandwidth/oc-ni:config/oc-ni:up-thresholds {
      deviate not-supported;
  }
  deviation /oc-ni:network-instances/oc-ni:network-instance/oc-ni:mpls/oc-ni:te-interface-attributes/oc-ni:interface/oc-ni:igp-flooding-bandwidth/oc-ni:state/oc-ni:up-thresholds {
      deviate not-supported;
  }
  deviation /oc-ni:network-instances/oc-ni:network-instance/oc-ni:mpls/oc-ni:te-interface-attributes/oc-ni:interface/oc-ni:igp-flooding-bandwidth/oc-ni:config/oc-ni:down-thresholds {
      deviate not-supported;
  }
  deviation /oc-ni:network-instances/oc-ni:network-instance/oc-ni:mpls/oc-ni:te-interface-attributes/oc-ni:interface/oc-ni:igp-flooding-bandwidth/oc-ni:state/oc-ni:down-thresholds {
      deviate not-supported;
  }
  deviation /oc-ni:network-instances/oc-ni:network-instance/oc-ni:mpls/oc-ni:te-interface-attributes/oc-ni:interface/oc-ni:igp-flooding-bandwidth/oc-ni:config/oc-ni:up-down-thresholds {
      deviate not-supported;
  }
  deviation /oc-ni:network-instances/oc-ni:network-instance/oc-ni:mpls/oc-ni:te-interface-attributes/oc-ni:interface/oc-ni:igp-flooding-bandwidth/oc-ni:state/oc-ni:up-down-thresholds {
      deviate not-supported;
  }
  // LSPs
  deviation /oc-ni:network-instances/oc-ni:network-instance/oc-ni:mpls/oc-ni:lsps/oc-ni:static-lsps/oc-ni:static-lsp/oc-ni:config {
      deviate not-supported;
  }
  deviation /oc-ni:network-instances/oc-ni:network-instance/oc-ni:mpls/oc-ni:lsps/oc-ni:static-lsps/oc-ni:static-lsp/oc-ni:ingress/oc-ni:config {
      deviate not-supported;
  }
  deviation /oc-ni:network-instances/oc-ni:network-instance/oc-ni:mpls/oc-ni:lsps/oc-ni:static-lsps/oc-ni:static-lsp/oc-ni:transit/oc-ni:config {
      deviate not-supported;
  }
  deviation /oc-ni:network-instances/oc-ni:network-instance/oc-ni:mpls/oc-ni:lsps/oc-ni:static-lsps/oc-ni:static-lsp/oc-ni:egress/oc-ni:config {
      deviate not-supported;
  }
  deviation /oc-ni:network-instances/oc-ni:network-instance/oc-ni:mpls/oc-ni:lsps/oc-ni:unconstrained-path {
      deviate not-supported;
  }
  deviation /oc-ni:network-instances/oc-ni:network-instance/oc-ni:mpls/oc-ni:lsps/oc-ni:constrained-path/oc-ni:named-explicit-paths/oc-ni:named-explicit-path/oc-ni:config/oc-ni:name {
      deviate replace {
          type string {
              length 1..64;
          }
      }
  }
  deviation /oc-ni:network-instances/oc-ni:network-instance/oc-ni:mpls/oc-ni:lsps/oc-ni:constrained-path/oc-ni:named-explicit-paths/oc-ni:named-explicit-path/oc-ni:config/oc-ni:sid-selection-mode {
      deviate not-supported;
      description "Not supported in this release.";
  }
  deviation /oc-ni:network-instances/oc-ni:network-instance/oc-ni:mpls/oc-ni:lsps/oc-ni:constrained-path/oc-ni:named-explicit-paths/oc-ni:named-explicit-path/oc-ni:config/oc-ni:sid-protection-required {
      deviate not-supported;
      description "Not supported in this release.";
  }
  deviation /oc-ni:network-instances/oc-ni:network-instance/oc-ni:mpls/oc-ni:lsps/oc-ni:constrained-path/oc-ni:named-explicit-paths/oc-ni:named-explicit-path/oc-ni:state/oc-ni:sid-selection-mode {
      deviate not-supported;
  }
  deviation /oc-ni:network-instances/oc-ni:network-instance/oc-ni:mpls/oc-ni:lsps/oc-ni:constrained-path/oc-ni:named-explicit-paths/oc-ni:named-explicit-path/oc-ni:state/oc-ni:sid-protection-required {
      deviate not-supported;
  }
  deviation /oc-ni:network-instances/oc-ni:network-instance/oc-ni:mpls/oc-ni:lsps/oc-ni:constrained-path/oc-ni:tunnels/oc-ni:tunnel/oc-ni:config/oc-ni:name {
      deviate replace {
          type string {
              length 1..64;
          }
      }
  }
  deviation /oc-ni:network-instances/oc-ni:network-instance/oc-ni:mpls/oc-ni:lsps/oc-ni:constrained-path/oc-ni:tunnels/oc-ni:tunnel/oc-ni:state/oc-ni:role {
      deviate not-supported;
  }
  deviation /oc-ni:network-instances/oc-ni:network-instance/oc-ni:mpls/oc-ni:lsps/oc-ni:constrained-path/oc-ni:tunnels/oc-ni:tunnel/oc-ni:config/oc-ni:type {
      deviate not-supported;
  }
  deviation /oc-ni:network-instances/oc-ni:network-instance/oc-ni:mpls/oc-ni:lsps/oc-ni:constrained-path/oc-ni:tunnels/oc-ni:tunnel/oc-ni:config/oc-ni:signaling-protocol {
      deviate not-supported;
  }
  deviation /oc-ni:network-instances/oc-ni:network-instance/oc-ni:mpls/oc-ni:lsps/oc-ni:constrained-path/oc-ni:tunnels/oc-ni:tunnel/oc-ni:config/oc-ni:metric-type {
      deviate not-supported;
  }
  deviation /oc-ni:network-instances/oc-ni:network-instance/oc-ni:mpls/oc-ni:lsps/oc-ni:constrained-path/oc-ni:tunnels/oc-ni:tunnel/oc-ni:config/oc-ni:metric {
      deviate replace {
          type int32 {
              range 1..16777215;
          }
      }
  }
  deviation /oc-ni:network-instances/oc-ni:network-instance/oc-ni:mpls/oc-ni:lsps/oc-ni:constrained-path/oc-ni:tunnels/oc-ni:tunnel/oc-ni:config/oc-ni:shortcut-eligible {
      deviate not-supported;
  }
  deviation /oc-ni:network-instances/oc-ni:network-instance/oc-ni:mpls/oc-ni:lsps/oc-ni:constrained-path/oc-ni:tunnels/oc-ni:tunnel/oc-ni:state/oc-ni:shortcut-eligible {
      deviate not-supported;
  }
  deviation /oc-ni:network-instances/oc-ni:network-instance/oc-ni:mpls/oc-ni:lsps/oc-ni:constrained-path/oc-ni:tunnels/oc-ni:tunnel/oc-ni:bandwidth/oc-ni:config/oc-ni:set-bandwidth {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:min-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-interval {
      deviate replace {
          type uint32 {
              range 300..315360000;
          }
      }
      deviate add {
          units seconds;
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:adjust-threshold {
      deviate replace {
        type uint8 {
            range 0..50;
        }
      }
  }
  deviation /oc-ni:network-instances/oc-ni:network-instance/oc-ni:mpls/oc-ni:lsps/oc-ni:constrained-path/oc-ni:tunnels/oc-ni:tunnel/oc-ni:bandwidth/oc-ni:auto-bandwidth/oc-ni:config/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:state/oc-ni:max-bw {
      deviate replace {
          type uint64;
      }
      deviate add {
          units bps;
      }
  }
  deviation /oc-ni:network-instances/oc-ni:network-instance/oc-ni:mpls/oc-ni:lsps/oc-ni:constrained-path/oc-ni:tunnels/oc-ni:tunnel/oc-ni:bandwidth/oc-ni:auto-bandwidth/oc-ni:overflow/oc-ni:config/oc-ni:overflow-threshold {
      deviate not-supported;
  }
  deviation /oc-ni:network-instances/oc-ni:network-instance/oc-ni:mpls/oc-ni:lsps/oc-ni:constrained-path/oc-ni:tunnels/oc-ni:tunnel/oc-ni:bandwidth/oc-ni:auto-bandwidth/oc-ni:underflow/oc-ni:config/oc-ni:underflow-threshold {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path {
      deviate add {
          max-elements 1;
      }
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:config/oc-ni:retry-timer {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:candidate-secondary-paths {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:spf-metric {
      deviate not-supported;
      description "Not supported in this release.";
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:cspf-tiebreaker {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:path-computation-method {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:path-computation-server {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:explicit-path-name {
      deviate not-supported;
  }
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:config/oc-ni:retry-timer {
      deviate not-supported;
  }
deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:spf-metric {
      deviate not-supported;
      description "Not supported in this release.";
  }

  // JUNOS preference is uint32 [range 0:4294967295]
  deviation /oc-ni:network-instances/oc-ni:network-instance/oc-ni:mpls/oc-ni:lsps/oc-ni:constrained-path/oc-ni:tunnels/oc-ni:tunnel/oc-ni:state/oc-ni:preference {
      deviate replace {
          type uint32 {
              range 0..4294967295;
          }
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-primary-path/oc-ni:p2p-primary-path/oc-ni:state/oc-ni:preference {
      deviate replace {
          type uint32 {
              range 0..4294967295;
          }
      }
  }
  // JUNOS preference is uint32 [range 0:4294967295]
  deviation /oc-ni:network-instances/oc-ni:network-instance/oc-ni:mpls/oc-ni:lsps/oc-ni:constrained-path/oc-ni:tunnels/oc-ni:tunnel/oc-ni:p2p-tunnel-attributes/oc-ni:p2p-secondary-paths/oc-ni:p2p-secondary-path/oc-ni:state/oc-ni:preference {
      deviate replace {
          type uint32 {
              range 0..4294967295;
          }
      }
  }
  deviation "/oc-ni:network-instances/oc-ni:network-instance/oc-ni:mpls/oc-ni:signaling-protocols/" +
  "oc-ni:segment-routing/oc-ni:interfaces/oc-ni:interface/oc-ni:sid-counters" {
      deviate not-supported;
  }

  // Network-Instance - BGP Deviations

  // BGP Deviations

  deviation /oc-platform:components/oc-platform:component/oc-platform:state/oc-platform:pcie {
      description "Not supported in this release";
      deviate not-supported;
  }

  deviation /oc-platform:components/oc-platform:component/oc-platform:state/oc-platform:clei-code {
      description "Not supported";
      deviate not-supported;
  }

  deviation /oc-platform:components/oc-platform:component/oc-platform:chassis/oc-platform:state {
      description "Not supported in this release";
      deviate not-supported;
  }

  deviation /oc-platform:components/oc-platform:component/oc-platform:storage/oc-platform:config {
      description "Not supported in this release";
      deviate not-supported;
  }

  deviation /oc-platform:components/oc-platform:component/oc-platform:storage/oc-platform:state {
      description "Not supported in this release";
      deviate not-supported;
  }

  deviation /oc-platform:components/oc-platform:component/oc-platform:backplane/oc-platform:config {
      description "Not supported in this release";
      deviate not-supported;
  }

  deviation /oc-platform:components/oc-platform:component/oc-platform:backplane/oc-platform:state {
      description "Not supported in this release";
      deviate not-supported;
  }

  deviation /oc-platform:components/oc-platform:component/oc-platform:software-module/oc-platform:config {
      description "Not supported in this release";
      deviate not-supported;
  }

  deviation /oc-platform:components/oc-platform:component/oc-platform:software-module/oc-platform:state {
      description "Not supported in this release";
      deviate not-supported;
  }

  deviation /oc-platform:components/oc-platform:component/oc-platform:cpu/oc-platform:config {
      description "Not supported in this release";
      deviate not-supported;
  }

  deviation /oc-platform:components/oc-platform:component/oc-platform:cpu/oc-platform:state {
      description "Not supported in this release";
      deviate not-supported;
  }

  deviation /oc-platform:components/oc-platform:component/oc-platform:fan/oc-platform:config {
      description "Not supported in this release";
      deviate not-supported;
  }

  deviation /oc-platform:components/oc-platform:component/oc-platform:port/oc-platform:state {
      description "Not supported in this release";
      deviate not-supported;
  }

  deviation /oc-platform:components/oc-platform:component/oc-platform:power-supply/oc-platform:state/oc-platform-psu:enabled {
      description "Not supported in this release";
      deviate not-supported;
  }

  deviation /oc-platform:components/oc-platform:component/oc-platform:properties/oc-platform:property/oc-platform:state/oc-platform:name {
      description "Not supported in this release";
      deviate not-supported;
  }

  deviation /oc-platform:components/oc-platform:component/oc-transceiver:transceiver/oc-transceiver:config {
      description "Not supported in this release";
      deviate not-supported;
  }

  deviation /oc-platform:components/oc-platform:component/oc-transceiver:transceiver/oc-transceiver:state/oc-transceiver:fec-uncorrectable-words {
      description "Not supported in this release";
      deviate not-supported;
  }

  deviation /oc-platform:components/oc-platform:component/oc-transceiver:transceiver/oc-transceiver:state/oc-transceiver:fec-corrected-bytes {
      description "Not supported in this release";
      deviate not-supported;
  }

  deviation /oc-platform:components/oc-platform:component/oc-transceiver:transceiver/oc-transceiver:state/oc-transceiver:pre-fec-ber {
      description "Not supported in this release";
      deviate not-supported;
  }

  deviation /oc-platform:components/oc-platform:component/oc-transceiver:transceiver/oc-transceiver:state/oc-transceiver:post-fec-ber {
      description "Not supported in this release";
      deviate not-supported;
  }

  deviation /oc-platform:components/oc-platform:component/oc-transceiver:transceiver/oc-transceiver:state/oc-transceiver:input-power/oc-transceiver:avg {
      description "Not supported in this release";
      deviate not-supported;
  }

  deviation /oc-platform:components/oc-platform:component/oc-transceiver:transceiver/oc-transceiver:state/oc-transceiver:input-power/oc-transceiver:interval {
      description "Not supported in this release";
      deviate not-supported;
  }

  deviation /oc-platform:components/oc-platform:component/oc-transceiver:transceiver/oc-transceiver:state/oc-transceiver:input-power/oc-transceiver:max {
      description "Not supported in this release";
      deviate not-supported;
  }

  deviation /oc-platform:components/oc-platform:component/oc-transceiver:transceiver/oc-transceiver:state/oc-transceiver:input-power/oc-transceiver:max-time {
      description "Not supported in this release";
      deviate not-supported;
  }

  deviation /oc-platform:components/oc-platform:component/oc-transceiver:transceiver/oc-transceiver:state/oc-transceiver:input-power/oc-transceiver:min {
      description "Not supported in this release";
      deviate not-supported;
  }

  deviation /oc-platform:components/oc-platform:component/oc-transceiver:transceiver/oc-transceiver:state/oc-transceiver:input-power/oc-transceiver:min-time {
      description "Not supported in this release";
      deviate not-supported;
  }

  deviation /oc-platform:components/oc-platform:component/oc-transceiver:transceiver/oc-transceiver:state/oc-transceiver:laser-bias-current/oc-transceiver:avg {
      description "Not supported in this release";
      deviate not-supported;
  }

  deviation /oc-platform:components/oc-platform:component/oc-transceiver:transceiver/oc-transceiver:state/oc-transceiver:laser-bias-current/oc-transceiver:interval {
      description "Not supported in this release";
      deviate not-supported;
  }

  deviation /oc-platform:components/oc-platform:component/oc-transceiver:transceiver/oc-transceiver:state/oc-transceiver:laser-bias-current/oc-transceiver:max {
      description "Not supported in this release";
      deviate not-supported;
  }

  deviation /oc-platform:components/oc-platform:component/oc-transceiver:transceiver/oc-transceiver:state/oc-transceiver:laser-bias-current/oc-transceiver:max-time {
      description "Not supported in this release";
      deviate not-supported;
  }

  deviation /oc-platform:components/oc-platform:component/oc-transceiver:transceiver/oc-transceiver:state/oc-transceiver:laser-bias-current/oc-transceiver:min {
      description "Not supported in this release";
      deviate not-supported;
  }

  deviation /oc-platform:components/oc-platform:component/oc-transceiver:transceiver/oc-transceiver:state/oc-transceiver:laser-bias-current/oc-transceiver:min-time {
      description "Not supported in this release";
      deviate not-supported;
  }

  deviation /oc-platform:components/oc-platform:component/oc-transceiver:transceiver/oc-transceiver:state/oc-transceiver:output-power/oc-transceiver:avg {
      description "Not supported in this release";
      deviate not-supported;
  }

  deviation /oc-platform:components/oc-platform:component/oc-transceiver:transceiver/oc-transceiver:state/oc-transceiver:output-power/oc-transceiver:interval {
      description "Not supported in this release";
      deviate not-supported;
  }

  deviation /oc-platform:components/oc-platform:component/oc-transceiver:transceiver/oc-transceiver:state/oc-transceiver:output-power/oc-transceiver:max {
      description "Not supported in this release";
      deviate not-supported;
  }

  deviation /oc-platform:components/oc-platform:component/oc-transceiver:transceiver/oc-transceiver:state/oc-transceiver:output-power/oc-transceiver:max-time {
      description "Not supported in this release";
      deviate not-supported;
  }

  deviation /oc-platform:components/oc-platform:component/oc-transceiver:transceiver/oc-transceiver:state/oc-transceiver:output-power/oc-transceiver:min {
      description "Not supported in this release";
      deviate not-supported;
  }

  deviation /oc-platform:components/oc-platform:component/oc-transceiver:transceiver/oc-transceiver:state/oc-transceiver:output-power/oc-transceiver:min-time {
      description "Not supported in this release";
      deviate not-supported;
  }

  deviation /oc-platform:components/oc-platform:component/oc-transceiver:transceiver/oc-transceiver:physical-channels/oc-transceiver:channel/oc-transceiver:config {
      description "Not supported in this release";
      deviate not-supported;
  }

  deviation /oc-platform:components/oc-platform:component/oc-transceiver:transceiver/oc-transceiver:physical-channels/oc-transceiver:channel/oc-transceiver:state/oc-transceiver:input-power/oc-transceiver:avg {
      description "Not supported in this release";
      deviate not-supported;
  }

  deviation /oc-platform:components/oc-platform:component/oc-transceiver:transceiver/oc-transceiver:physical-channels/oc-transceiver:channel/oc-transceiver:state/oc-transceiver:input-power/oc-transceiver:interval {
      description "Not supported in this release";
      deviate not-supported;
  }

  deviation /oc-platform:components/oc-platform:component/oc-transceiver:transceiver/oc-transceiver:physical-channels/oc-transceiver:channel/oc-transceiver:state/oc-transceiver:input-power/oc-transceiver:max {
      description "Not supported in this release";
      deviate not-supported;
  }

  deviation /oc-platform:components/oc-platform:component/oc-transceiver:transceiver/oc-transceiver:physical-channels/oc-transceiver:channel/oc-transceiver:state/oc-transceiver:input-power/oc-transceiver:max-time {
      description "Not supported in this release";
      deviate not-supported;
  }

  deviation /oc-platform:components/oc-platform:component/oc-transceiver:transceiver/oc-transceiver:physical-channels/oc-transceiver:channel/oc-transceiver:state/oc-transceiver:input-power/oc-transceiver:min {
      description "Not supported in this release";
      deviate not-supported;
  }

  deviation /oc-platform:components/oc-platform:component/oc-transceiver:transceiver/oc-transceiver:physical-channels/oc-transceiver:channel/oc-transceiver:state/oc-transceiver:input-power/oc-transceiver:min-time {
      description "Not supported in this release";
      deviate not-supported;
  }

  deviation /oc-platform:components/oc-platform:component/oc-transceiver:transceiver/oc-transceiver:physical-channels/oc-transceiver:channel/oc-transceiver:state/oc-transceiver:laser-bias-current/oc-transceiver:avg {
      description "Not supported in this release";
      deviate not-supported;
  }

  deviation /oc-platform:components/oc-platform:component/oc-transceiver:transceiver/oc-transceiver:physical-channels/oc-transceiver:channel/oc-transceiver:state/oc-transceiver:laser-bias-current/oc-transceiver:interval {
      description "Not supported in this release";
      deviate not-supported;
  }

  deviation /oc-platform:components/oc-platform:component/oc-transceiver:transceiver/oc-transceiver:physical-channels/oc-transceiver:channel/oc-transceiver:state/oc-transceiver:laser-bias-current/oc-transceiver:max {
      description "Not supported in this release";
      deviate not-supported;
  }

  deviation /oc-platform:components/oc-platform:component/oc-transceiver:transceiver/oc-transceiver:physical-channels/oc-transceiver:channel/oc-transceiver:state/oc-transceiver:laser-bias-current/oc-transceiver:max-time {
      description "Not supported in this release";
      deviate not-supported;
  }

  deviation /oc-platform:components/oc-platform:component/oc-transceiver:transceiver/oc-transceiver:physical-channels/oc-transceiver:channel/oc-transceiver:state/oc-transceiver:laser-bias-current/oc-transceiver:min {
      description "Not supported in this release";
      deviate not-supported;
  }

  deviation /oc-platform:components/oc-platform:component/oc-transceiver:transceiver/oc-transceiver:physical-channels/oc-transceiver:channel/oc-transceiver:state/oc-transceiver:laser-bias-current/oc-transceiver:min-time {
      description "Not supported in this release";
      deviate not-supported;
  }

  deviation /oc-platform:components/oc-platform:component/oc-transceiver:transceiver/oc-transceiver:physical-channels/oc-transceiver:channel/oc-transceiver:state/oc-transceiver:output-power/oc-transceiver:avg {
      description "Not supported in this release";
      deviate not-supported;
  }

  deviation /oc-platform:components/oc-platform:component/oc-transceiver:transceiver/oc-transceiver:physical-channels/oc-transceiver:channel/oc-transceiver:state/oc-transceiver:output-power/oc-transceiver:interval {
      description "Not supported in this release";
      deviate not-supported;
  }

  deviation /oc-platform:components/oc-platform:component/oc-transceiver:transceiver/oc-transceiver:physical-channels/oc-transceiver:channel/oc-transceiver:state/oc-transceiver:output-power/oc-transceiver:max {
      description "Not supported in this release";
      deviate not-supported;
  }

  deviation /oc-platform:components/oc-platform:component/oc-transceiver:transceiver/oc-transceiver:physical-channels/oc-transceiver:channel/oc-transceiver:state/oc-transceiver:output-power/oc-transceiver:max-time {
      description "Not supported in this release";
      deviate not-supported;
  }

  deviation /oc-platform:components/oc-platform:component/oc-transceiver:transceiver/oc-transceiver:physical-channels/oc-transceiver:channel/oc-transceiver:state/oc-transceiver:output-power/oc-transceiver:min {
      description "Not supported in this release";
      deviate not-supported;
  }

  deviation /oc-platform:components/oc-platform:component/oc-transceiver:transceiver/oc-transceiver:physical-channels/oc-transceiver:channel/oc-transceiver:state/oc-transceiver:output-power/oc-transceiver:min-time {
      description "Not supported in this release";
      deviate not-supported;
  }

  deviation /oc-platform:components/oc-platform:component/oc-transceiver:transceiver/oc-transceiver:state/oc-transceiver:supply-voltage {
      description "Not supported in this release";
      deviate not-supported;
  }

  deviation /oc-platform:components/oc-platform:component/oc-transceiver:transceiver/oc-transceiver:physical-channels/oc-transceiver:channel/oc-transceiver:state/oc-transceiver:laser-age {
      description "Not supported in this release";
      deviate not-supported;
  }

  deviation /oc-platform:components/oc-platform:component/oc-transceiver:transceiver/oc-transceiver:physical-channels/oc-transceiver:channel/oc-transceiver:state/oc-transceiver:laser-temperature {
      description "Not supported in this release";
      deviate not-supported;
  }

  deviation /oc-platform:components/oc-platform:component/oc-transceiver:transceiver/oc-transceiver:physical-channels/oc-transceiver:channel/oc-transceiver:state/oc-transceiver:target-frequency-deviation {
      description "Not supported in this release";
      deviate not-supported;
  }

  deviation /oc-platform:components/oc-platform:component/oc-transceiver:transceiver/oc-transceiver:physical-channels/oc-transceiver:channel/oc-transceiver:state/oc-transceiver:tec-current {
      description "Not supported in this release";
      deviate not-supported;
  }


  deviation /oc-platform:components/oc-platform:component/oc-opt-term:optical-channel/oc-opt-term:config/oc-opt-term:line-port {
      description "Not supported in this release";
      deviate not-supported;
  }

  deviation /oc-platform:components/oc-platform:component/oc-opt-term:optical-channel/oc-opt-term:config/oc-opt-term:operational-mode {
      description "Not supported in this release";
      deviate not-supported;
  }

  deviation /oc-platform:components/oc-platform:component/oc-opt-term:optical-channel/oc-opt-term:config/oc-opt-term:target-output-power {
      description "Not supported in this release";
      deviate not-supported;
  }

  deviation /oc-platform:components/oc-platform:component/oc-opt-term:optical-channel/oc-opt-term:state/oc-opt-term:target-output-power {
      description "Not supported in this release";
      deviate not-supported;
  }

  deviation /oc-platform:components/oc-platform:component/oc-opt-term:optical-channel/oc-opt-term:state/oc-opt-term:operational-mode {
      description "Not supported in this release";
      deviate not-supported;
  }

  deviation /oc-platform:components/oc-platform:component/oc-opt-term:optical-channel/oc-opt-term:state/oc-opt-term:group-id {
      description "Not supported in this release";
      deviate not-supported;
  }

  deviation /oc-platform:components/oc-platform:component/oc-opt-term:optical-channel/oc-opt-term:state/oc-opt-term:polarization-mode-dispersion {
      description "Not supported in this release";
      deviate not-supported;
  }

  deviation /oc-platform:components/oc-platform:component/oc-opt-term:optical-channel/oc-opt-term:state/oc-opt-term:modulation-error-ratio {
      description "Not supported in this release";
      deviate not-supported;
  }

  deviation /oc-platform:components/oc-platform:component/oc-opt-term:optical-channel/oc-opt-term:state/oc-opt-term:fec-uncorrectable-blocks {
      description "Not supported in this release";
      deviate not-supported;
  }

  deviation /oc-platform:components/oc-platform:component/oc-opt-term:optical-channel/oc-opt-term:state/oc-opt-term:post-fec-ber {
      description "Not supported in this release";
      deviate not-supported;
  }

  deviation /oc-platform:components/oc-platform:component/oc-opt-term:optical-channel/oc-opt-term:state/oc-opt-term:q-value {
      description "Not supported in this release";
      deviate not-supported;
  }

  deviation /oc-opt-term:terminal-device {
      description "Not supported in this release";
      deviate not-supported;
  }

  deviation /oc-platform:components/oc-platform:component/oc-platform:integrated-circuit/oc-ic:memory {
      description "Not supported";
      deviate not-supported;
  }

  deviation /oc-platform:components/oc-platform:component/oc-platform:integrated-circuit/oc-platform:utilization/oc-platform:resources/oc-platform:resource/oc-platform:state {
      description "Not supported";
      deviate not-supported;
  }

  deviation /oc-platform:components/oc-platform:component/oc-platform:integrated-circuit/oc-ppc:pipeline-counters/oc-ppc:control-plane-traffic {
      description "Not supported";
      deviate not-supported;
  }

  deviation /oc-platform:components/oc-platform:component/oc-platform:integrated-circuit/oc-ppc:pipeline-counters/oc-ppc:drop/oc-ppc:fabric-block {
      description "Not supported";
      deviate not-supported;
  }

 deviation /oc-platform:components/oc-platform:component/oc-platform:integrated-circuit/oc-ppc:pipeline-counters/oc-ppc:drop/oc-ppc:host-interface-block/oc-ppc:state/oc-ppc:fragment-punt {
      description "Not supported";
      deviate not-supported;
  }

  deviation /oc-platform:components/oc-platform:component/oc-platform:integrated-circuit/oc-ppc:pipeline-counters/oc-ppc:drop/oc-ppc:host-interface-block/oc-ppc:state/oc-ppc:in-high-priority {
      description "Not supported";
      deviate not-supported;
  }

  deviation /oc-platform:components/oc-platform:component/oc-platform:integrated-circuit/oc-ppc:pipeline-counters/oc-ppc:drop/oc-ppc:host-interface-block/oc-ppc:state/oc-ppc:in-low-priority {
      description "Not supported";
      deviate not-supported;
  }

  deviation /oc-platform:components/oc-platform:component/oc-platform:integrated-circuit/oc-ppc:pipeline-counters/oc-ppc:drop/oc-ppc:host-interface-block/oc-ppc:state/oc-ppc:oversubscription {
      description "Not supported";
      deviate not-supported;
  }

  deviation /oc-platform:components/oc-platform:component/oc-platform:integrated-circuit/oc-ppc:pipeline-counters/oc-ppc:drop/oc-ppc:host-interface-block/oc-ppc:state/oc-ppc:rate-limit {
      description "Not supported";
      deviate not-supported;
  }

  deviation /oc-platform:components/oc-platform:component/oc-platform:integrated-circuit/oc-ppc:pipeline-counters/oc-ppc:drop/oc-ppc:lookup-block/oc-ppc:state/oc-ppc:oversubscription {
      description "Not supported";
      deviate not-supported;
  }

  deviation /oc-platform:components/oc-platform:component/oc-platform:integrated-circuit/oc-ppc:pipeline-counters/oc-ppc:drop/oc-ppc:state/oc-ppc:congestion-aggregate {
      description "Not supported";
      deviate not-supported;
  }

  deviation /oc-platform:components/oc-platform:component/oc-platform:integrated-circuit/oc-ppc:pipeline-counters/oc-ppc:drop/oc-ppc:state/oc-ppc:no-route {
      description "Not supported";
      deviate not-supported;
  }

  deviation /oc-platform:components/oc-platform:component/oc-platform:integrated-circuit/oc-ppc:pipeline-counters/oc-ppc:drop/oc-ppc:vendor {
      description "Not supported";
      deviate not-supported;
  }

  deviation /oc-platform:components/oc-platform:component/oc-platform:integrated-circuit/oc-ppc:pipeline-counters/oc-ppc:packet/oc-ppc:fabric-block/oc-ppc:state/oc-ppc:in-packets {
      description "Not supported";
      deviate not-supported;
  }

  deviation /oc-platform:components/oc-platform:component/oc-platform:integrated-circuit/oc-ppc:pipeline-counters/oc-ppc:packet/oc-ppc:fabric-block/oc-ppc:state/oc-ppc:out-packets {
      description "Not supported";
      deviate not-supported;
  }

  deviation /oc-platform:components/oc-platform:component/oc-platform:integrated-circuit/oc-ppc:pipeline-counters/oc-ppc:packet/oc-ppc:fabric-block/oc-ppc:state/oc-ppc:in-high-priority-cells {
      description "Not supported";
      deviate not-supported;
  }

  deviation /oc-platform:components/oc-platform:component/oc-platform:integrated-circuit/oc-ppc:pipeline-counters/oc-ppc:packet/oc-ppc:fabric-block/oc-ppc:state/oc-ppc:in-high-priority-packets {
      description "Not supported";
      deviate not-supported;
  }

  deviation /oc-platform:components/oc-platform:component/oc-platform:integrated-circuit/oc-ppc:pipeline-counters/oc-ppc:packet/oc-ppc:fabric-block/oc-ppc:state/oc-ppc:in-low-priority-cells {
      description "Not supported";
      deviate not-supported;
  }

  deviation /oc-platform:components/oc-platform:component/oc-platform:integrated-circuit/oc-ppc:pipeline-counters/oc-ppc:packet/oc-ppc:fabric-block/oc-ppc:state/oc-ppc:in-low-priority-packets {
      description "Not supported";
      deviate not-supported;
  }

  deviation /oc-platform:components/oc-platform:component/oc-platform:integrated-circuit/oc-ppc:pipeline-counters/oc-ppc:packet/oc-ppc:fabric-block/oc-ppc:state/oc-ppc:out-high-priority-cells {
      description "Not supported";
      deviate not-supported;
  }

  deviation /oc-platform:components/oc-platform:component/oc-platform:integrated-circuit/oc-ppc:pipeline-counters/oc-ppc:packet/oc-ppc:fabric-block/oc-ppc:state/oc-ppc:out-high-priority-packets {
      description "Not supported";
      deviate not-supported;
  }

  deviation /oc-platform:components/oc-platform:component/oc-platform:integrated-circuit/oc-ppc:pipeline-counters/oc-ppc:packet/oc-ppc:fabric-block/oc-ppc:state/oc-ppc:out-low-priority-cells {
      description "Not supported";
      deviate not-supported;
  }

  deviation /oc-platform:components/oc-platform:component/oc-platform:integrated-circuit/oc-ppc:pipeline-counters/oc-ppc:packet/oc-ppc:fabric-block/oc-ppc:state/oc-ppc:out-low-priority-packets {
      description "Not supported";
      deviate not-supported;
  }

deviation /oc-platform:components/oc-platform:component/oc-platform:integrated-circuit/oc-ppc:pipeline-counters/oc-ppc:packet/oc-ppc:host-interface-block/oc-ppc:state/oc-ppc:fragment-punt-pkts {
      description "Not supported";
      deviate not-supported;
  }

  deviation /oc-platform:components/oc-platform:component/oc-platform:integrated-circuit/oc-ppc:pipeline-counters/oc-ppc:packet/oc-ppc:host-interface-block/oc-ppc:state/oc-ppc:in-high-priority-packets {
      description "Not supported";
      deviate not-supported;
  }

  deviation /oc-platform:components/oc-platform:component/oc-platform:integrated-circuit/oc-ppc:pipeline-counters/oc-ppc:packet/oc-ppc:host-interface-block/oc-ppc:state/oc-ppc:in-low-priority-packets {
      description "Not supported";
      deviate not-supported;
  }

  deviation /oc-platform:components/oc-platform:component/oc-platform:integrated-circuit/oc-ppc:pipeline-counters/oc-ppc:packet/oc-ppc:host-interface-block/oc-ppc:state/oc-ppc:out-high-priority-packets {
      description "Not supported";
      deviate not-supported;
  }

  deviation /oc-platform:components/oc-platform:component/oc-platform:integrated-circuit/oc-ppc:pipeline-counters/oc-ppc:packet/oc-ppc:host-interface-block/oc-ppc:state/oc-ppc:out-low-priority-packets {
      description "Not supported";
      deviate not-supported;
  }

  deviation /oc-platform:components/oc-platform:component/oc-platform:integrated-circuit/oc-ppc:pipeline-counters/oc-ppc:packet/oc-ppc:lookup-block/oc-ppc:state/oc-ppc:fragment-total-pkts {
      description "Not supported";
      deviate not-supported;
  }

  deviation /oc-platform:components/oc-platform:component/oc-platform:integrated-circuit/oc-ppc:pipeline-counters/oc-ppc:packet/oc-ppc:lookup-block/oc-ppc:state/oc-ppc:in-bytes {
      description "Not supported";
      deviate not-supported;
  }

  deviation /oc-platform:components/oc-platform:component/oc-platform:integrated-circuit/oc-ppc:pipeline-counters/oc-ppc:packet/oc-ppc:lookup-block/oc-ppc:state/oc-ppc:out-bytes {
      description "Not supported";
      deviate not-supported;
  }

  deviation /oc-platform:components/oc-platform:component/oc-platform:integrated-circuit/oc-ppc:pipeline-counters/oc-ppc:packet/oc-ppc:queueing-block/oc-ppc:state/oc-ppc:in-bytes {
      description "Not supported";
      deviate not-supported;
  }

  deviation /oc-platform:components/oc-platform:component/oc-platform:integrated-circuit/oc-ppc:pipeline-counters/oc-ppc:packet/oc-ppc:queueing-block/oc-ppc:state/oc-ppc:out-bytes {
      description "Not supported";
      deviate not-supported;
  }

  deviation /oc-platform:components/oc-platform:component/oc-platform:integrated-circuit/oc-ppc:pipeline-counters/oc-ppc:packet/oc-ppc:queueing-block/oc-ppc:state/oc-ppc:loopback-bytes {
      description "Not supported";
      deviate not-supported;
  }

  deviation /oc-platform:components/oc-platform:component/oc-platform:controller-card/oc-platform:config {
      description "Not supported";
      deviate not-supported;
  }

  deviation /oc-ni:network-instances/oc-ni:network-instance/oc-ni:protocols/oc-ni:protocol/oc-ni:bgp/oc-ni:rib/oc-ni:attr-sets/oc-ni:attr-set/oc-ni:tunnel-encapsulation {
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:loc-rib/oc-ni:state {
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-in-pre/oc-ni:state {
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-in-post/oc-ni:state {
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-out-pre/oc-ni:state {
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-out-post/oc-ni:state {
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:loc-rib/oc-ni:state {
      deviate not-supported;
  }
  deviation /oc-ni:network-instances/oc-ni:network-instance/oc-ni:protocols/oc-ni:protocol/oc-ni:bgp/oc-ni:rib/oc-ni:afi-safis/oc-ni:afi-safi/oc-ni:ipv4-srte-policy {
      deviate not-supported;
  }
  deviation /oc-ni:network-instances/oc-ni:network-instance/oc-ni:protocols/oc-ni:protocol/oc-ni:bgp/oc-ni:rib/oc-ni:afi-safis/oc-ni:afi-safi/oc-ni:ipv6-srte-policy {
      deviate not-supported;
  }

  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:state"{
        description
          "Not supported in this version.";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:routes/oc-ni:route-distinguisher/" +
              "oc-ni:type-one-ethernet-auto-discovery/oc-ni:type-one-route/oc-ni:paths/oc-ni:path/oc-ni:state/oc-ni:advertised-to-peer"{
        description
          "Not supported in this version";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:routes/oc-ni:route-distinguisher/" +
              "oc-ni:type-two-mac-ip-advertisement/oc-ni:type-two-route/oc-ni:paths/oc-ni:path/oc-ni:state/oc-ni:advertised-to-peer"{
        description
          "Not supported in this version";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:routes/oc-ni:route-distinguisher/" +
              "oc-ni:type-three-inclusive-multicast-ethernet-tag/oc-ni:type-three-route/oc-ni:paths/oc-ni:path/oc-ni:state/oc-ni:advertised-to-peer"{
        description
          "Not supported in this version";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:routes/oc-ni:route-distinguisher/" +
              "oc-ni:type-four-ethernet-segment/oc-ni:type-four-route/oc-ni:paths/oc-ni:path/oc-ni:state/oc-ni:advertised-to-peer"{
        description
          "Not supported in this version";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:loc-rib/oc-ni:routes/oc-ni:route-distinguisher/" +
              "oc-ni:type-five-ip-prefix/oc-ni:type-five-route/oc-ni:paths/oc-ni:path/oc-ni:state/oc-ni:advertised-to-peer"{
        description
          "Not supported in this version";
        deviate not-supported;
  }
  deviation "/oc-ni:network-instances/oc-ni:network-instance/oc-ni:protocols/oc-ni:protocol/oc-ni:bgp/" +
              "oc-ni:rib/oc-ni:afi-safis/oc-ni:afi-safi/oc-ni:l2vpn-evpn/oc-ni:neighbors"{
        description
          "Not supported in this version";
        deviate not-supported;
  }
  deviation /oc-ni:network-instances/oc-ni:network-instance/oc-ni:protocols/oc-ni:protocol/oc-ni:bgp/oc-ni:global/oc-ni:default-route-distance {
      description
          "Junos does not support separate external and internal default-route-distance config knobs.";
      deviate not-supported;
  }
  deviation /oc-ni:network-instances/oc-ni:network-instance/oc-ni:protocols/oc-ni:protocol/oc-ni:bgp/oc-ni:global/oc-ni:use-multiple-paths/oc-ni:ebgp/oc-ni:config/oc-ni:maximum-paths {
      description
          "There is no protocol level config knob for this in Junos.";
      deviate not-supported;
  }
  deviation /oc-ni:network-instances/oc-ni:network-instance/oc-ni:protocols/oc-ni:protocol/oc-ni:bgp/oc-ni:global/oc-ni:use-multiple-paths/oc-ni:ibgp/oc-ni:config/oc-ni:maximum-paths {
      deviate not-supported;
  }
  deviation /oc-ni:network-instances/oc-ni:network-instance/oc-ni:protocols/oc-ni:protocol/oc-ni:bgp/oc-ni:global/oc-ni:afi-safis/oc-ni:afi-safi/oc-ni:ipv4-unicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv6-unicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv6-labeled-unicast/oc-ni:prefix-limit/oc-ni:state/oc-ni:prefix-limit-exceeded {
      deviate not-supported;
  }
 deviation /oc-ni:network-instances/oc-ni:network-instance/oc-ni:protocols/oc-ni:protocol/oc-ni:bgp/oc-ni:global/oc-ni:afi-safis/oc-ni:afi-safi/oc-ni:ipv4-labeled-unicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv4-unicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv6-unicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv4-multicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv6-multicast/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l2vpn-vpls/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l2vpn-evpn/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:srte-policy-ipv4/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:srte-policy-ipv6/oc-ni:prefix-limit/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv4-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv6-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv6-labeled-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:ipv4-labeled-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv4-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv6-unicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv4-multicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l3vpn-ipv6-multicast/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l2vpn-vpls/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:l2vpn-evpn/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:srte-policy-ipv4/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:afi-safis/oc-ni:afi-safi/oc-ni:srte-policy-ipv6/oc-ni:prefix-limit-received/oc-ni:state/oc-ni:prefix-limit-exceeded {
      deviate not-supported;
  }
  deviation /oc-ni:network-instances/oc-ni:network-instance/oc-ni:protocols/oc-ni:protocol/oc-ni:bgp/oc-ni:global/oc-ni:route-selection-options/oc-ni:config/oc-ni:enable-aigp {
      deviate not-supported;
  }
  deviation /oc-ni:network-instances/oc-ni:network-instance/oc-ni:protocols/oc-ni:protocol/oc-ni:bgp/oc-ni:global/oc-ni:route-selection-options/oc-ni:state/oc-ni:enable-aigp {
      deviate not-supported;
  }
  deviation /oc-ni:network-instances/oc-ni:network-instance/oc-ni:protocols/oc-ni:protocol/oc-ni:bgp/oc-ni:global/oc-ni:route-selection-options/oc-ni:config/oc-ni:ignore-next-hop-igp-metric {
      deviate not-supported;
  }
  deviation /oc-ni:network-instances/oc-ni:network-instance/oc-ni:protocols/oc-ni:protocol/oc-ni:bgp/oc-ni:global/oc-ni:route-selection-options/oc-ni:state/oc-ni:ignore-next-hop-igp-metric {
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:advertise-inactive-routes {
      deviate not-supported;
  }
 deviation /oc-ni:network-instances/oc-ni:network-instance/oc-ni:protocols/oc-ni:protocol/oc-ni:bgp/oc-ni:global/oc-ni:afi-safis/oc-ni:afi-safi/oc-ni:route-selection-options/oc-ni:state/oc-ni:advertise-inactive-routes {
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:always-compare-med {
      description 
          "In Junos, -always-compare-med- can not be set per address family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:state/oc-ni:always-compare-med {
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:external-compare-router-id {
      deviate not-supported;
  }
  deviation /oc-ni:network-instances/oc-ni:network-instance/oc-ni:protocols/oc-ni:protocol/oc-ni:bgp/oc-ni:global/oc-ni:afi-safis/oc-ni:afi-safi/oc-ni:route-selection-options/oc-ni:state/oc-ni:external-compare-router-id {
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-as-path-length {
      description 
          "In Junos, -ignore-as-path-length- can not be set per address 
           family.";
      deviate not-supported;
  }
  deviation /oc-ni:network-instances/oc-ni:network-instance/oc-ni:protocols/oc-ni:protocol/oc-ni:bgp/oc-ni:global/oc-ni:afi-safis/oc-ni:afi-safi/oc-ni:route-selection-options/oc-ni:state/oc-ni:ignore-as-path-length {
      deviate not-supported;
  }
  deviation /oc-ni:network-instances/oc-ni:network-instance/oc-ni:protocols/oc-ni:protocol/oc-ni:bgp/oc-ni:global/oc-ni:afi-safis/oc-ni:afi-safi/oc-ni:route-selection-options/oc-ni:config/oc-ni:ignore-next-hop-igp-metric {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:global/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:config/oc-ni:send-community {
      description 
          "There is no BGP specific config knob for this in Junos.";
      deviate not-supported;
  }
  deviation /oc-ni:network-instances/oc-ni:network-instance/oc-ni:protocols/oc-ni:protocol/oc-ni:bgp/oc-ni:global/oc-ni:afi-safis/oc-ni:afi-safi/oc-ni:graceful-restart/oc-ni:config/oc-ni:enabled {
      deviate not-supported;
  }
  deviation /oc-ni:network-instances/oc-ni:network-instance/oc-ni:protocols/oc-ni:protocol/oc-ni:bgp/oc-ni:peer-groups/oc-ni:peer-group/oc-ni:afi-safis/oc-ni:afi-safi/oc-ni:graceful-restart/oc-ni:config/oc-ni:enabled {
      description
        "Graceful-restart configuration under afi-safi level is not supported in Junos";
      deviate not-supported;
  }
  deviation /oc-ni:network-instances/oc-ni:network-instance/oc-ni:protocols/oc-ni:protocol/oc-ni:bgp/oc-ni:neighbors/oc-ni:neighbor/oc-ni:afi-safis/oc-ni:afi-safi/oc-ni:graceful-restart/oc-ni:config/oc-ni:enabled {
      description
        "Graceful-restart configuration under afi-safi level is not supported in Junos";
      deviate not-supported;
  }
  deviation /oc-ni:network-instances/oc-ni:network-instance/oc-ni:protocols/oc-ni:protocol/oc-ni:bgp/oc-ni:peer-groups/oc-ni:peer-group/oc-ni:enable-bfd/oc-ni:config/oc-ni:enabled {
      deviate not-supported;
  }
  deviation /oc-ni:network-instances/oc-ni:network-instance/oc-ni:protocols/oc-ni:protocol/oc-ni:bgp/oc-ni:peer-groups/oc-ni:peer-group/oc-ni:as-path-options/oc-ni:state/oc-ni:disable-peer-as-filter {
      description
        "This xpath is not supported under peer-group hierarchy";
      deviate not-supported;
  }
  deviation /oc-ni:network-instances/oc-ni:network-instance/oc-ni:protocols/oc-ni:protocol/oc-ni:bgp/oc-ni:peer-groups/oc-ni:peer-group/oc-ni:use-multiple-paths/oc-ni:ebgp/oc-ni:config/oc-ni:maximum-paths {
      description
        "There is no BGP specific config knob at the peer-group level for this in Junos.";
      deviate not-supported;
  }
  deviation /oc-ni:network-instances/oc-ni:network-instance/oc-ni:protocols/oc-ni:protocol/oc-ni:bgp/oc-ni:peer-groups/oc-ni:peer-group/oc-ni:use-multiple-paths/oc-ni:ibgp/oc-ni:config/oc-ni:maximum-paths {
      description
        "There is no BGP specific config knob at the peer-group level for this in Junos.";
      deviate not-supported;
  }
  deviation /oc-ni:network-instances/oc-ni:network-instance/oc-ni:protocols/oc-ni:protocol/oc-ni:bgp/oc-ni:peer-groups/oc-ni:peer-group/oc-ni:timers/oc-ni:config/oc-ni:restart-time {
       deviate replace {
          type uint16 {
            range 60..65535;
          }
      }
  }
  deviation /oc-ni:network-instances/oc-ni:network-instance/oc-ni:protocols/oc-ni:protocol/oc-ni:bgp/oc-ni:neighbors/oc-ni:neighbor/oc-ni:timers/oc-ni:config/oc-ni:restart-time {
      deviate replace {
         type uint16 {
           range 60..65535;
         }
      }
  }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:peer-groups/oc-ni:peer-group/oc-ni:afi-safis/oc-ni:afi-safi/oc-ni:add-paths/oc-ni:config/oc-ni:send {
      deviate add {
          must '(. = "false" or send-max)' {
           error-message
             "When 'send' is true, send-max must be configured.";
          }
      }  
   }
  deviation /oc-ni:network-instances/oc-ni:network-instance/oc-ni:protocols/oc-ni:protocol/oc-ni:bgp/oc-ni:peer-groups/oc-ni:peer-group/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:prefix-limit/oc-ni:config/oc-ni:prevent-teardown {
      deviate add {
          must '(. = "true" or max-prefix)' {
           error-message
             "When 'prevent-teardown' is true, max-prefix must be configured.";
          }
      }  
   }
   deviation /oc-ni:network-instances/oc-ni:network-instance/oc-ni:protocols/oc-ni:protocol/oc-ni:bgp/oc-ni:peer-groups/oc-ni:peer-group/oc-ni:afi-safis/oc-ni:afi-safi/oc-ni:ipv4-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv6-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv6-labeled-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv4-labeled-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv4-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv6-unicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv4-multicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv6-multicast/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l2vpn-vpls/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l2vpn-evpn/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:srte-policy-ipv4/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:srte-policy-ipv6/oc-ni:prefix-limit/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv4-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv6-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv6-labeled-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:ipv4-labeled-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv4-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv6-unicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv4-multicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l3vpn-ipv6-multicast/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l2vpn-vpls/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:l2vpn-evpn/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:srte-policy-ipv4/oc-ni:prefix-limit-received/oc-ni:state/oc-ni:prefix-limit-exceeded {
       description
       "In Junos, prefix-limit-exceeded is not supported per group";
       deviate not-supported;
   }
   deviation /oc-ni:network-instances/oc-ni:network-instance/oc-ni:protocols/oc-ni:protocol/oc-ni:bgp/oc-ni:peer-groups/oc-ni:peer-group/oc-ni:afi-safis/oc-ni:afi-safi/oc-ni:srte-policy-ipv6/oc-ni:prefix-limit-received/oc-ni:state/oc-ni:prefix-limit-exceeded {
       description
       "In Junos, prefix-limit-exceeded is not supported per group";
       deviate not-supported;
   }
  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:peer-groups/oc-ni:peer-group/oc-ni:route-reflector/oc-ni:config/oc-ni:route-reflector-client {
      deviate not-supported;
  }
  deviation /oc-ni:network-instances/oc-ni:network-instance/oc-ni:protocols/oc-ni:protocol/oc-ni:bgp/oc-ni:neighbors/oc-ni:neighbor/oc-ni:route-reflector/oc-ni:config/oc-ni:route-reflector-client {
      deviate not-supported;
  }
  deviation /oc-ni:network-instances/oc-ni:network-instance/oc-ni:protocols/oc-ni:protocol/oc-ni:bgp/oc-ni:neighbors/oc-ni:neighbor/oc-ni:config/oc-ni:send-community {
      deviate not-supported;
  }
  deviation /oc-ni:network-instances/oc-ni:network-instance/oc-ni:protocols/oc-ni:protocol/oc-ni:bgp/oc-ni:neighbors/oc-ni:neighbor/oc-ni:state/oc-ni:send-community {
      deviate not-supported;
  }
  deviation /oc-ni:network-instances/oc-ni:network-instance/oc-ni:protocols/oc-ni:protocol/oc-ni:bgp/oc-ni:neighbors/oc-ni:neighbor/oc-ni:config/oc-ni:peer-type {
       deviate not-supported;
  }
  deviation /oc-ni:network-instances/oc-ni:network-instance/oc-ni:protocols/oc-ni:protocol/oc-ni:bgp/oc-ni:neighbors/oc-ni:neighbor/oc-ni:config/oc-ni:neighbor-port {
      deviate not-supported;
  }
  deviation /oc-ni:network-instances/oc-ni:network-instance/oc-ni:protocols/oc-ni:protocol/oc-ni:bgp/oc-ni:neighbors/oc-ni:neighbor/oc-ni:state/oc-ni:last-prefix-limit-exceeded {
       deviate not-supported;
  }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send-max {
      deviate replace {
          type uint8 {
              range 2..6;
          }
      }  
   }
  deviation /oc-ni:network-instances/oc-ni:network-instance/oc-ni:protocols/oc-ni:protocol/oc-ni:bgp/oc-ni:neighbors/oc-ni:neighbor/oc-ni:afi-safis/oc-ni:afi-safi/oc-ni:add-paths/oc-ni:config/oc-ni:send {
      deviate add {
           must '(. = "false" or ../send-max )' {
           error-message
             "When 'send' is true, send-max must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:use-multiple-paths {
      description 
          "In Junos, -multipath- config cannot be set per address family.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:prefix-limit/oc-ni:config/oc-ni:prevent-teardown {
      deviate add {
          must '(. = "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:prefix-limit/oc-ni:config/oc-ni:prevent-teardown {
      deviate add {
          must '(. = "true" or max-prefix)' {
           error-message
             "When 'prevent-teardown' is true, max-prefix must be configured.";
          }
      }  
   }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:config/oc-ni:send-default-route {
      description 
          "There is no BGP specific config knob for this in Junos.";
      deviate not-supported;
  }
  deviation /oc-ni:network-instances/oc-ni:network-instance/oc-ni:protocols/oc-ni:protocol/oc-ni:bgp/oc-ni:global/oc-ni:config/oc-ni:router-id {
      deviate replace {
          type yang:dotted-quad;
      }
  }
  deviation /oc-ni:network-instances/oc-ni:network-instance/oc-ni:protocols/oc-ni:protocol/oc-ni:bgp/oc-ni:global/oc-ni:afi-safis/oc-ni:afi-safi/oc-ni:route-selection-options/oc-ni:state/oc-ni:enable-aigp {
      description
          "In Junos, -enable-aigp- is supported only for labeled-unicast.";
      deviate not-supported;
  }
  deviation /oc-ni:network-instances/oc-ni:network-instance/oc-ni:protocols/oc-ni:protocol/oc-ni:bgp/oc-ni:global/oc-ni:afi-safis/oc-ni:afi-safi/oc-ni:route-selection-options/oc-ni:state/oc-ni:ignore-next-hop-igp-metric {
      description
          "There is no BGP specific state for this in Junos.";
      deviate not-supported;
  }
  deviation /oc-ni:network-instances/oc-ni:network-instance/oc-ni:protocols/oc-ni:protocol/oc-ni:bgp/oc-ni:global/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:global/oc-ni:dynamic-neighbor-prefixes/oc-ni:dynamic-neighbor-prefix {
      description
          "Junos supports dynamic-neighbors at peer-group level, not in global.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:state/oc-ni:send-default-route {
      description
          "There is no BGP specific state for this in Junos.";
      deviate not-supported;
  }

  deviation /oc-ni:network-instances/oc-ni:network-instance/oc-ni:protocols/oc-ni:protocol/oc-ni:bgp/oc-ni:peer-groups/oc-ni:peer-group/oc-ni:afi-safis/oc-ni:afi-safi/oc-ni:ipv4-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:state/oc-ni:send-default-route {
      description
          "There is no BGP specific state for this in Junos.";
      deviate not-supported;
  }
  deviation /oc-ni:network-instances/oc-ni:network-instance/oc-ni:protocols/oc-ni:protocol/oc-ni:bgp/oc-ni:global/oc-ni:afi-safis/oc-ni:afi-safi/oc-ni:ipv6-unicast/oc-ni:state {
      description
          "Not supported in this release";
      deviate not-supported;
  }
  deviation /oc-ni:network-instances/oc-ni:network-instance/oc-ni:protocols/oc-ni:protocol/oc-ni:bgp/oc-ni:global/oc-ni:afi-safis/oc-ni:afi-safi/oc-ni:route-selection-options/oc-ni:state {
      description
          "Not supported in this release";
      deviate not-supported;
  }
  deviation /oc-ni:network-instances/oc-ni:network-instance/oc-ni:protocols/oc-ni:protocol/oc-ni:bgp/oc-ni:neighbors/oc-ni:neighbor/oc-ni:afi-safis/oc-ni:afi-safi/oc-ni:ipv6-unicast/oc-ni:state {
      description
          "Not supported in this release";
      deviate not-supported;
  }
  deviation /oc-ni:network-instances/oc-ni:network-instance/oc-ni:protocols/oc-ni:protocol/oc-ni:bgp/oc-ni:peer-groups/oc-ni:peer-group/oc-ni:afi-safis/oc-ni:afi-safi/oc-ni:ipv6-unicast/oc-ni:state {
      description
          "Not supported in this release";
      deviate not-supported;
  }
  deviation /oc-ni:network-instances/oc-ni:network-instance/oc-ni:protocols/oc-ni:protocol/oc-ni:bgp/oc-ni:peer-groups/oc-ni:peer-group/oc-ni:state/oc-ni:send-community {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-in-post/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-in-pre/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-out-post/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:neighbors/oc-ni:neighbor/oc-ni:adj-rib-out-pre/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:neighbors/oc-ni:neighbor/oc-ni:adj-rib-in-post/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:neighbors/oc-ni:neighbor/oc-ni:adj-rib-in-pre/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:neighbors/oc-ni:neighbor/oc-ni:adj-rib-out-post/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:neighbors/oc-ni:neighbor/oc-ni:adj-rib-out-pre/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv4-unicast/oc-ni:loc-rib/oc-ni:routes/oc-ni:route/oc-ni:state/oc-bgprib-ext:reject-reason {
      description
          "Not supported in this release";
      deviate not-supported;
  }
  deviation /oc-ni:network-instances/oc-ni:network-instance/oc-ni:protocols/oc-ni:protocol/oc-ni:bgp/oc-ni:rib/oc-ni:afi-safis/oc-ni:afi-safi/oc-ni:ipv6-unicast/oc-ni:loc-rib/oc-ni:routes/oc-ni:route/oc-ni:state/oc-bgprib-ext:reject-reason {
      description
          "Not supported in this release";
      deviate not-supported;
  }

  // openconfig-system deviations
  deviation /oc-system:system/oc-sys-grpc:grpc-servers/oc-sys-grpc:grpc-server/oc-sys-grpc:config/oc-sys-grpc:listen-addresses {
      deviate add {
          max-elements 1;
      }
  }
  deviation /oc-system:system/oc-system:ntp/oc-system:config/oc-system:enable-ntp-auth {
      deviate not-supported;
  }
  deviation /oc-system:system/oc-system:ntp/oc-system:servers/oc-system:server/oc-system:config/oc-system:port {
      deviate replace {
          type uint16 {
              range 123;
          }
      }
  }
  deviation /oc-system:system/oc-system:ntp/oc-system:servers/oc-system:server/oc-system:config/oc-system:association-type {
       deviate not-supported;
  }
  deviation /oc-system:system/oc-system:ntp/oc-system:servers/oc-system:server/oc-system:config/oc-system:iburst {
      deviate not-supported;
  }
  deviation /oc-system:system/oc-system:ntp/oc-system:servers/oc-system:server/oc-system:config/oc-system:source-address {
      deviate not-supported;
  }
  deviation /oc-system:system/oc-system:dns/oc-system:config/oc-system:search {
      deviate add {
          max-elements 6;
      }
  }
  deviation /oc-system:system/oc-system:dns/oc-system:servers/oc-system:server/oc-system:config/oc-system:port {
      deviate replace {
          type uint16 {
              range 53;
          }
      }
  }
  deviation /oc-system:system/oc-system:telnet-server/oc-system:config/oc-system:timeout {
      deviate not-supported;
  }
  deviation /oc-system:system/oc-system:memory/oc-system:config {
      deviate not-supported;
  }
  deviation /oc-system:system/oc-system:memory/oc-system:state/oc-system:counters {
      deviate not-supported;
  }
  deviation /oc-system:system/oc-system:processes/oc-system:process/oc-system:state/oc-system:args {
      deviate not-supported;
  }
  deviation /oc-system:system/oc-system:logging/oc-system:console/oc-system:state {
      deviate not-supported;
  }
  deviation /oc-system:system/oc-system:logging/oc-system:files {
      deviate not-supported;
  }
  deviation /oc-system:system/oc-system:logging/oc-system:vty {
      deviate not-supported;
  }
  deviation /oc-system:system/oc-system:aaa/oc-system:config {
      deviate not-supported;
  }
  deviation /oc-system:system/oc-system:aaa/oc-system:authorization/oc-system:config {
      deviate not-supported;
  }
  deviation /oc-system:system/oc-system:aaa/oc-system:authorization/oc-system:events {
      deviate not-supported;
  }
  deviation /oc-system:system/oc-system:aaa/oc-system:accounting/oc-system:events/oc-system:event/oc-system:config/oc-system:record {
        deviate not-supported;
  }
  deviation /oc-system:system/oc-system:aaa/oc-system:authentication/oc-system:users/oc-system:user/oc-system:config/oc-system:ssh-key {
      deviate not-supported;
  }
  deviation /oc-system:system/oc-system:aaa/oc-system:server-groups/oc-system:server-group/oc-system:servers/oc-system:server/oc-system:radius/oc-system:config/oc-system:source-address {
      deviate replace {
          type inet:ip-address;
      }
  }
  deviation /oc-system:system/oc-system:aaa/oc-system:server-groups/oc-system:server-group/oc-system:servers/oc-system:server/oc-system:tacacs/oc-system:config/oc-system:source-address {
      deviate replace {
          type inet:ip-address;
      }
  }
  deviation /oc-system:system/oc-system:aaa/oc-system:server-groups/oc-system:server-group/oc-system:servers/oc-system:server/oc-system:config/oc-system:address {
      deviate replace {
          type inet:ip-address;
      }
  }
deviation /oc-system:system/oc-system:aaa/oc-system:server-groups/oc-system:server-group/oc-system:servers/oc-system:server/oc-system:tacacs/oc-system:config/oc-system:secret-key-hashed {
	deviate not-supported;
}

deviation /oc-system:system/oc-system:aaa/oc-system:server-groups/oc-system:server-group/oc-system:servers/oc-system:server/oc-system:radius/oc-system:config/oc-system:secret-key-hashed {
        deviate not-supported;
}
  // openconfig-lacp deviations
  deviation /oc-lacp:lacp/oc-lacp:interfaces/oc-lacp:interface/oc-lacp:config/oc-lacp:system-id-mac {
      deviate replace {
          type yang:mac-address;
      }
  }

  deviation /oc-bfd:bfd/oc-bfd:interfaces/oc-bfd:interface/oc-bfd:micro-bfd-sessions/oc-bfd:micro-bfd-session/oc-bfd:config/oc-bfd:local-address {
      deviate replace {
          type inet:ip-address;
      }
  }
  deviation /oc-bfd:bfd/oc-bfd:interfaces/oc-bfd:interface/oc-bfd:micro-bfd-sessions/oc-bfd:micro-bfd-session/oc-bfd:config/oc-bfd:remote-address {
      deviate replace {
          type inet:ip-address;
      }
  }
  // JUNOS preference BFD timer configs in milliseconds.
  deviation /oc-bfd:bfd/oc-bfd:interfaces/oc-bfd:interface/oc-bfd:config/oc-bfd:desired-minimum-tx-interval {
      deviate replace {
	  units milliseconds;
      }
  }
  deviation /oc-bfd:bfd/oc-bfd:interfaces/oc-bfd:interface/oc-bfd:config/oc-bfd:required-minimum-receive {
      deviate replace {
          units milliseconds;
      }
   }
  deviation /oc-bfd:bfd/oc-bfd:interfaces/oc-bfd:interface/oc-bfd:config/oc-bfd:enabled {
    description
      "Junos does not support BFD configuration on member interface";
    deviate not-supported;
   }
  deviation /oc-bfd:bfd/oc-bfd:interfaces/oc-bfd:interface/oc-bfd:config/oc-bfd:id {
    description
      "Junos does not support BFD member id config";
    deviate not-supported;
   }
  deviation /oc-bfd:bfd/oc-bfd:interfaces/oc-bfd:interface/oc-bfd:config/oc-bfd:local-address {
    description
      "Junos does not support BFD member-link local-address config";
    deviate not-supported;
   }
  deviation /oc-bfd:bfd/oc-bfd:interfaces/oc-bfd:interface/oc-bfd:micro-bfd-sessions/oc-bfd:micro-bfd-session/oc-bfd:config/oc-bfd:member-interface {
    description
      "Junos does not support BFD individual AE member interface config";
    deviate not-supported;
   }
  deviation /oc-bfd:bfd/oc-bfd:interfaces/oc-bfd:interface/oc-bfd:interface-ref{
    description
      "Junos does not support interface-ref config";
    deviate not-supported;
   }

    deviation /oc-bfd:bfd/oc-bfd:interfaces/oc-bfd:interface/oc-bfd:micro-bfd-sessions/oc-bfd:micro-bfd-session/oc-bfd:state/oc-bfd:async {
	description
	    "Junos does not support per bfd session stats";
	deviate not-supported;
    }
    deviation /oc-bfd:bfd/oc-bfd:interfaces/oc-bfd:interface/oc-bfd:peers/oc-bfd:peer/oc-bfd:state/oc-bfd:echo/oc-bfd:last-packet-transmitted {
	description
	    "Junos does not support per bfd session stats";
	deviate not-supported;
    }
    deviation /oc-bfd:bfd/oc-bfd:interfaces/oc-bfd:interface/oc-bfd:peers/oc-bfd:peer/oc-bfd:state/oc-bfd:echo/oc-bfd:last-packet-received {
	description
	    "Junos does not support per bfd session stats";
	deviate not-supported;
    }
    deviation /oc-bfd:bfd/oc-bfd:interfaces/oc-bfd:interface/oc-bfd:peers/oc-bfd:peer/oc-bfd:state/oc-bfd:echo/oc-bfd:transmitted-packets {
	description
	    "Junos does not support per bfd session stats";
	deviate not-supported;
    }
    deviation /oc-bfd:bfd/oc-bfd:interfaces/oc-bfd:interface/oc-bfd:peers/oc-bfd:peer/oc-bfd:state/oc-bfd:echo/oc-bfd:received-packets {
	description
	    "Junos does not support per bfd session stats";
	deviate not-supported;
    }
    deviation /oc-bfd:bfd/oc-bfd:interfaces/oc-bfd:interface/oc-bfd:peers/oc-bfd:peer/oc-bfd:state/oc-bfd:echo/oc-bfd:up-transitions {
	description
	    "Junos does not support per bfd session stats";
	deviate not-supported;
    }
    deviation /oc-bfd:bfd/oc-bfd:interfaces/oc-bfd:interface/oc-bfd:peers/oc-bfd:peer/oc-bfd:state/oc-bfd:async {
	description
	    "Junos does not support per bfd session stats";
	deviate not-supported;
    }
  deviation /oc-if:interfaces/oc-if:interface/oc-eth:ethernet/oc-eth:state/oc-eth:duplex-mode {
      deviate replace {
          type enumeration {
              enum HALF {
                  description "Full duplex mode";
              }
              enum FULL {
                  description "Half duplex mode";
              }
              enum NOT-NEGOTIATED {
                  description "Duplex mode not negotiated yet";
              }
          }
      }
  }
  deviation /oc-if:interfaces/oc-if:interface/oc-eth:ethernet/oc-eth:state/oc-eth:negotiated-duplex-mode {
      deviate replace {
          type enumeration {
              enum HALF {
                  description "Full duplex mode";
              }
              enum FULL {
                  description "Half duplex mode";
              }
              enum NOT-NEGOTIATED {
                  description "Duplex mode not negotiated yet";
              }
          }
      }
  }

  deviation /oc-platform:components/oc-platform:component/oc-transceiver:transceiver/oc-transceiver:state/oc-transceiver:date-code {
      deviate replace {
          type string;
      }
  }
  deviation /oc-platform:components/oc-platform:component/oc-transceiver:transceiver/oc-transceiver:state/oc-transceiver:ethernet-pmd {
      deviate replace {
          type string;
      }
  }
  deviation /oc-platform:components/oc-platform:component/oc-transceiver:transceiver/oc-transceiver:state/oc-transceiver:ethernet-pmd-preconf {
      deviate replace {
          type string;
      }
  }
  deviation /oc-platform:components/oc-platform:component/oc-transceiver:transceiver/oc-transceiver:state/oc-transceiver:form-factor {
      deviate replace {
          type string;
      }
  }
  deviation /oc-platform:components/oc-platform:component/oc-transceiver:transceiver/oc-transceiver:state/oc-transceiver:form-factor-preconf {
      deviate replace {
          type string;
      }
  }
  deviation /oc-platform:components/oc-platform:component/oc-transceiver:transceiver/oc-transceiver:state/oc-transceiver:sonet-sdh-compliance-code {
      deviate replace {
          type string;
      }
  }
  deviation /oc-platform:components/oc-platform:component/oc-transceiver:transceiver/oc-transceiver:state/oc-transceiver:otn-compliance-code {
      deviate replace {
          type string;
      }
  }
  deviation /oc-platform:components/oc-platform:component/oc-transceiver:transceiver/oc-transceiver:state/oc-transceiver:vendor-rev {
      deviate replace {
          type string {
              length 1..10;
          }
      }
  }

  deviation "/oc-acl:acl/oc-acl:acl-sets/oc-acl:acl-set/oc-acl:acl-entries/oc-acl:acl-entry/oc-acl:ipv6/oc-acl:config/oc-acl:source-address"{
        deviate replace {
           type inet:ipv6-prefix;
        }
  }

  deviation "/oc-acl:acl/oc-acl:acl-sets/oc-acl:acl-set/oc-acl:acl-entries/oc-acl:acl-entry/oc-acl:ipv6/oc-acl:config/oc-acl:destination-address"{
        deviate replace {
           type inet:ipv6-prefix;
        }
  }

  deviation "/oc-acl:acl/oc-acl:acl-sets/oc-acl:acl-set/oc-acl:acl-entries/oc-acl:acl-entry/oc-acl:ipv6/oc-acl:config/oc-acl:dscp"{
        deviate replace {
           type string;
        }
  }

  deviation "/oc-acl:acl/oc-acl:acl-sets/oc-acl:acl-set/oc-acl:acl-entries/oc-acl:acl-entry/oc-acl:ipv4/oc-acl:config/oc-acl:dscp"{
        deviate replace {
           type string;
        }
  }

  deviation "/oc-acl:acl/oc-acl:acl-sets/oc-acl:acl-set/oc-acl:acl-entries/oc-acl:acl-entry/oc-acl:l2/oc-acl:config/oc-acl:destination-mac"{
        deviate replace {
           type jnx-types:mac-address-prefix;
        }
  }

  deviation "/oc-acl:acl/oc-acl:acl-sets/oc-acl:acl-set/oc-acl:acl-entries/oc-acl:acl-entry/oc-acl:l2/oc-acl:config/oc-acl:destination-mac-mask"{
        deviate not-supported;
  }

  deviation "/oc-acl:acl/oc-acl:acl-sets/oc-acl:acl-set/oc-acl:acl-entries/oc-acl:acl-entry/oc-acl:l2/oc-acl:state/oc-acl:destination-mac-mask"{
        deviate not-supported;
  }


 deviation "/oc-acl:acl/oc-acl:acl-sets/oc-acl:acl-set/oc-acl:acl-entries/oc-acl:acl-entry/oc-acl:ipv6/oc-acl:config/oc-acl:destination-flow-label"{
        deviate not-supported;
  }

 deviation "/oc-acl:acl/oc-acl:acl-sets/oc-acl:acl-set/oc-acl:acl-entries/oc-acl:acl-entry/oc-acl:ipv6/oc-acl:state/oc-acl:destination-flow-label"{
        deviate not-supported;
  }

  deviation "/oc-acl:acl/oc-acl:acl-sets/oc-acl:acl-set/oc-acl:acl-entries/oc-acl:acl-entry/oc-acl:ipv6/oc-acl:config/oc-acl:source-flow-label"{
        deviate not-supported;
  }

  deviation "/oc-acl:acl/oc-acl:acl-sets/oc-acl:acl-set/oc-acl:acl-entries/oc-acl:acl-entry/oc-acl:ipv6/oc-acl:state/oc-acl:source-flow-label"{
        deviate not-supported;
  }

  deviation "/oc-acl:acl/oc-acl:acl-sets/oc-acl:acl-set/oc-acl:acl-entries/oc-acl:acl-entry/oc-acl:l2/oc-acl:config/oc-acl:source-mac"{
        deviate replace {
           type jnx-types:mac-address-prefix;
        }
  }

  deviation "/oc-acl:acl/oc-acl:acl-sets/oc-acl:acl-set/oc-acl:acl-entries/oc-acl:acl-entry/oc-acl:l2/oc-acl:config/oc-acl:source-mac-mask"{
        deviate not-supported;
  }

  deviation "/oc-acl:acl/oc-acl:acl-sets/oc-acl:acl-set/oc-acl:acl-entries/oc-acl:acl-entry/oc-acl:l2/oc-acl:state/oc-acl:source-mac-mask"{
        deviate not-supported;
  }


  deviation "/oc-acl:acl/oc-acl:interfaces/oc-acl:interface/oc-acl:ingress-acl-sets/oc-acl:ingress-acl-set/oc-acl:acl-entries"{
        deviate not-supported;
  }

  deviation "/oc-acl:acl/oc-acl:interfaces/oc-acl:interface/oc-acl:egress-acl-sets/oc-acl:egress-acl-set/oc-acl:acl-entries"{
        deviate not-supported;
  }


deviation "/oc-acl:acl/oc-acl:acl-sets/oc-acl:acl-set/oc-acl:acl-entries/oc-acl:acl-entry/oc-acl:actions/oc-acl:config/oc-acl:forwarding-action"{
        deviate replace {
           mandatory false;
        }
  }

  deviation "/oc-acl:acl/oc-acl:interfaces/oc-acl:interface/oc-acl:interface-ref/oc-acl:config/oc-acl:interface"{
        deviate add {
           mandatory true;
        }
  }

  deviation "/oc-acl:acl/oc-acl:interfaces/oc-acl:interface/oc-acl:interface-ref/oc-acl:config/oc-acl:subinterface"{
        deviate add {
           mandatory true;
        }
  }

  deviation "/oc-acl:acl/oc-acl:acl-sets/oc-acl:acl-set/oc-acl:acl-entries/oc-acl:acl-entry/oc-acl:input-interface/oc-acl:interface-ref/oc-acl:config/oc-acl:interface"{
        deviate add {
           mandatory true;
        }
  }


  deviation "/oc-acl:acl/oc-acl:acl-sets/oc-acl:acl-set/oc-acl:acl-entries/oc-acl:acl-entry/oc-acl:input-interface/oc-acl:interface-ref/oc-acl:config/oc-acl:subinterface"{
        deviate add {
           mandatory true;
        }
  }

  deviation "/oc-acl:acl/oc-acl:acl-sets/oc-acl:acl-set/oc-acl:acl-entries/oc-acl:acl-entry/oc-acl:transport/oc-acl:config/oc-acl:destination-port"{
        deviate replace {
           type union {
               type inet:port-number;
               type jnx-types:port-range;
           }
        }
  }

  deviation "/oc-acl:acl/oc-acl:acl-sets/oc-acl:acl-set/oc-acl:acl-entries/oc-acl:acl-entry/oc-acl:transport/oc-acl:config/oc-acl:source-port"{
        deviate replace {
           type union {
               type inet:port-number;
               type jnx-types:port-range;
           }
        }
  }
 
  // openconfig-qos deviations
  deviation "/oc-qos:qos/oc-qos:config" {
      description
          "Qos config is not supported";
      deviate not-supported;
  }
    deviation "/oc-qos:qos/oc-qos:state" {
      description
          "Qos state is not supported";
      deviate not-supported;
  }
    deviation "/oc-qos:qos/oc-qos:forwarding-groups/oc-qos:forwarding-group/oc-qos:config/oc-qos:unicast-output-queue" {
      description
          "Not supported in this release";
      deviate not-supported;
  }
    deviation "/oc-qos:qos/oc-qos:forwarding-groups/oc-qos:forwarding-group/oc-qos:config/oc-qos:multicast-output-queue" {
      description
          "Not supported in this release";
      deviate not-supported;
  }
    deviation "/oc-qos:qos/oc-qos:forwarding-groups/oc-qos:forwarding-group/oc-qos:state/oc-qos:unicast-output-queue" {
      description
          "Not supported in this release";
      deviate not-supported;
  }
    deviation "/oc-qos:qos/oc-qos:forwarding-groups/oc-qos:forwarding-group/oc-qos:state/oc-qos:multicast-output-queue" {
      description
          "Not supported in this release";
      deviate not-supported;
  }
    deviation "/oc-qos:qos/oc-qos:classifiers/oc-qos:classifier/oc-qos:terms/oc-qos:term/oc-qos:conditions/oc-qos:l2" {
      description
          "Not supported in this release";
      deviate not-supported;
  }
    deviation "/oc-qos:qos/oc-qos:classifiers/oc-qos:classifier/oc-qos:terms/oc-qos:term/oc-qos:conditions/oc-qos:ipv4/oc-qos:config/oc-qos:source-address" {
      description
          "Not supported in this release";
      deviate not-supported;
  }
    deviation "/oc-qos:qos/oc-qos:classifiers/oc-qos:classifier/oc-qos:terms/oc-qos:term/oc-qos:conditions/oc-qos:ipv4/oc-qos:config/oc-qos:destination-address" {
      description
          "Not supported in this release";
      deviate not-supported;
  }
    deviation "/oc-qos:qos/oc-qos:classifiers/oc-qos:classifier/oc-qos:terms/oc-qos:term/oc-qos:conditions/oc-qos:ipv4/oc-qos:config/oc-qos:protocol" {
      description
          "Not supported in this release";
      deviate not-supported;
  }
    deviation "/oc-qos:qos/oc-qos:classifiers/oc-qos:classifier/oc-qos:terms/oc-qos:term/oc-qos:conditions/oc-qos:ipv4/oc-qos:config/oc-qos:hop-limit" {
      description
          "Not supported in this release";
      deviate not-supported;
  }
    deviation "/oc-qos:qos/oc-qos:classifiers/oc-qos:classifier/oc-qos:terms/oc-qos:term/oc-qos:conditions/oc-qos:ipv4/oc-qos:state/oc-qos:source-address" {
      description
          "Not supported in this release";
      deviate not-supported;
  }
    deviation "/oc-qos:qos/oc-qos:classifiers/oc-qos:classifier/oc-qos:terms/oc-qos:term/oc-qos:conditions/oc-qos:ipv4/oc-qos:state/oc-qos:destination-address" {
      description
          "Not supported in this release";
      deviate not-supported;
  }
    deviation "/oc-qos:qos/oc-qos:classifiers/oc-qos:classifier/oc-qos:terms/oc-qos:term/oc-qos:conditions/oc-qos:ipv4/oc-qos:state/oc-qos:protocol" {
      description
          "Not supported in this release";
      deviate not-supported;
  }
    deviation "/oc-qos:qos/oc-qos:classifiers/oc-qos:classifier/oc-qos:terms/oc-qos:term/oc-qos:conditions/oc-qos:ipv4/oc-qos:state/oc-qos:hop-limit" {
      description
          "Not supported in this release";
      deviate not-supported;
  }
    deviation "/oc-qos:qos/oc-qos:classifiers/oc-qos:classifier/oc-qos:terms/oc-qos:term/oc-qos:conditions/oc-qos:ipv6/oc-qos:config/oc-qos:source-address" {
      description
          "Not supported in this release";
      deviate not-supported;
  }
    deviation "/oc-qos:qos/oc-qos:classifiers/oc-qos:classifier/oc-qos:terms/oc-qos:term/oc-qos:conditions/oc-qos:ipv6/oc-qos:config/oc-qos:source-flow-label" {
      description
          "Not supported in this release";
      deviate not-supported;
  }
    deviation "/oc-qos:qos/oc-qos:classifiers/oc-qos:classifier/oc-qos:terms/oc-qos:term/oc-qos:conditions/oc-qos:ipv6/oc-qos:config/oc-qos:destination-address" {
      description
          "Not supported in this release";
      deviate not-supported;
  }
    deviation "/oc-qos:qos/oc-qos:classifiers/oc-qos:classifier/oc-qos:terms/oc-qos:term/oc-qos:conditions/oc-qos:ipv6/oc-qos:config/oc-qos:destination-flow-label" {
      description
          "Not supported in this release";
      deviate not-supported;
  }
    deviation "/oc-qos:qos/oc-qos:classifiers/oc-qos:classifier/oc-qos:terms/oc-qos:term/oc-qos:conditions/oc-qos:ipv6/oc-qos:config/oc-qos:protocol" {
      description
          "Not supported in this release";
      deviate not-supported;
  }
    deviation "/oc-qos:qos/oc-qos:classifiers/oc-qos:classifier/oc-qos:terms/oc-qos:term/oc-qos:conditions/oc-qos:ipv6/oc-qos:config/oc-qos:hop-limit" {
      description
          "Not supported in this release";
      deviate not-supported;
  }
    deviation "/oc-qos:qos/oc-qos:classifiers/oc-qos:classifier/oc-qos:terms/oc-qos:term/oc-qos:conditions/oc-qos:ipv6/oc-qos:state/oc-qos:source-address" {
      description
          "Not supported in this release";
      deviate not-supported;
  }
    deviation "/oc-qos:qos/oc-qos:classifiers/oc-qos:classifier/oc-qos:terms/oc-qos:term/oc-qos:conditions/oc-qos:ipv6/oc-qos:state/oc-qos:source-flow-label" {
      description
          "Not supported in this release";
      deviate not-supported;
  }
    deviation "/oc-qos:qos/oc-qos:classifiers/oc-qos:classifier/oc-qos:terms/oc-qos:term/oc-qos:conditions/oc-qos:ipv6/oc-qos:state/oc-qos:destination-address" {
      description
          "Not supported in this release";
      deviate not-supported;
  }
    deviation "/oc-qos:qos/oc-qos:classifiers/oc-qos:classifier/oc-qos:terms/oc-qos:term/oc-qos:conditions/oc-qos:ipv6/oc-qos:state/oc-qos:destination-flow-label" {
      description
          "Not supported in this release";
      deviate not-supported;
  }
    deviation "/oc-qos:qos/oc-qos:classifiers/oc-qos:classifier/oc-qos:terms/oc-qos:term/oc-qos:conditions/oc-qos:ipv6/oc-qos:state/oc-qos:protocol" {
      description
          "Not supported in this release";
      deviate not-supported;
  }
    deviation "/oc-qos:qos/oc-qos:classifiers/oc-qos:classifier/oc-qos:terms/oc-qos:term/oc-qos:conditions/oc-qos:ipv6/oc-qos:state/oc-qos:hop-limit" {
      description
          "Not supported in this release";
      deviate not-supported;
  }
    deviation "/oc-qos:qos/oc-qos:classifiers/oc-qos:classifier/oc-qos:terms/oc-qos:term/oc-qos:conditions/oc-qos:transport" {
      description
          "Not supported in this release";
      deviate not-supported;
  }
    deviation "/oc-qos:qos/oc-qos:classifiers/oc-qos:classifier/oc-qos:terms/oc-qos:term/oc-qos:conditions/oc-qos:mpls/oc-qos:config/oc-qos:start-label-value" {
      description
          "Not supported in this release";
      deviate not-supported;
  }
    deviation "/oc-qos:qos/oc-qos:classifiers/oc-qos:classifier/oc-qos:terms/oc-qos:term/oc-qos:conditions/oc-qos:mpls/oc-qos:config/oc-qos:end-label-value" {
      description
          "Not supported in this release";
      deviate not-supported;
  }
    deviation "/oc-qos:qos/oc-qos:classifiers/oc-qos:classifier/oc-qos:terms/oc-qos:term/oc-qos:conditions/oc-qos:mpls/oc-qos:config/oc-qos:ttl-value" {
      description
          "Not supported in this release";
      deviate not-supported;
  }
    deviation "/oc-qos:qos/oc-qos:classifiers/oc-qos:classifier/oc-qos:terms/oc-qos:term/oc-qos:conditions/oc-qos:mpls/oc-qos:state/oc-qos:start-label-value" {
      description
          "Not supported in this release";
      deviate not-supported;
  }
    deviation "/oc-qos:qos/oc-qos:classifiers/oc-qos:classifier/oc-qos:terms/oc-qos:term/oc-qos:conditions/oc-qos:mpls/oc-qos:state/oc-qos:end-label-value" {
      description
          "Not supported in this release";
      deviate not-supported;
  }
    deviation "/oc-qos:qos/oc-qos:classifiers/oc-qos:classifier/oc-qos:terms/oc-qos:term/oc-qos:conditions/oc-qos:mpls/oc-qos:state/oc-qos:ttl-value" {
      description
          "Not supported in this release";
      deviate not-supported;
  }
  deviation "/oc-qos:qos/oc-qos:scheduler-policies/oc-qos:scheduler-policy/oc-qos:schedulers/oc-qos:scheduler/oc-qos:state/oc-qos:type" {
      description
          "Not supported in this release";
      deviate not-supported;
  }
  deviation "/oc-qos:qos/oc-qos:scheduler-policies/oc-qos:scheduler-policy/oc-qos:schedulers/oc-qos:scheduler/oc-qos:output/oc-qos:config/oc-qos:output-type" {
      description
          "Not supported in this release";
      deviate not-supported;
  }
  deviation "/oc-qos:qos/oc-qos:scheduler-policies/oc-qos:scheduler-policy/oc-qos:schedulers/oc-qos:scheduler/oc-qos:output/oc-qos:state/oc-qos:output-type" {
      description
          "Not supported in this release";
      deviate not-supported;
  }
  deviation "/oc-qos:qos/oc-qos:scheduler-policies/oc-qos:scheduler-policy/oc-qos:schedulers/oc-qos:scheduler/oc-qos:output/oc-qos:config/oc-qos:child-scheduler" {
      description
          "Not supported in this release";
      deviate not-supported;
  }
  deviation "/oc-qos:qos/oc-qos:scheduler-policies/oc-qos:scheduler-policy/oc-qos:schedulers/oc-qos:scheduler/oc-qos:output/oc-qos:state/oc-qos:child-scheduler" {
      description
          "Not supported in this release";
      deviate not-supported;
  }
  deviation "/oc-qos:qos/oc-qos:scheduler-policies/oc-qos:scheduler-policy/oc-qos:schedulers/oc-qos:scheduler/oc-qos:one-rate-two-color/oc-qos:state/oc-qos:cir-pct" {
      description
          "Not supported in this release";
      deviate not-supported;
  }
  deviation "/oc-qos:qos/oc-qos:scheduler-policies/oc-qos:scheduler-policy/oc-qos:schedulers/oc-qos:scheduler/oc-qos:two-rate-three-color/oc-qos:config/oc-qos:cir-pct-remaining" {
      description
          "Not supported in this release";
      deviate not-supported;
  }
  deviation "/oc-qos:qos/oc-qos:scheduler-policies/oc-qos:scheduler-policy/oc-qos:schedulers/oc-qos:scheduler/oc-qos:two-rate-three-color/oc-qos:config/oc-qos:pir-pct-remaining" {
      description
          "Not supported in this release";
      deviate not-supported;
  }
  deviation "/oc-qos:qos/oc-qos:scheduler-policies/oc-qos:scheduler-policy/oc-qos:schedulers/oc-qos:scheduler/oc-qos:two-rate-three-color/oc-qos:state/oc-qos:cir-pct-remaining" {
      description
          "Not supported in this release";
      deviate not-supported;
  }
  deviation "/oc-qos:qos/oc-qos:scheduler-policies/oc-qos:scheduler-policy/oc-qos:schedulers/oc-qos:scheduler/oc-qos:two-rate-three-color/oc-qos:state/oc-qos:pir-pct-remaining" {
      description
          "Not supported in this release";
      deviate not-supported;
  }
  deviation "/oc-qos:qos/oc-qos:scheduler-policies/oc-qos:scheduler-policy/oc-qos:schedulers/oc-qos:scheduler/oc-qos:two-rate-three-color/oc-qos:config/oc-qos:be" {
      description
          "Not supported in this release";
      deviate not-supported;
  }
  deviation "/oc-qos:qos/oc-qos:scheduler-policies/oc-qos:scheduler-policy/oc-qos:schedulers/oc-qos:scheduler/oc-qos:two-rate-three-color/oc-qos:state/oc-qos:be" {
      description
          "Not supported in this release";
      deviate not-supported;
  }
  deviation "/oc-qos:qos/oc-qos:scheduler-policies/oc-qos:scheduler-policy/oc-qos:schedulers/oc-qos:scheduler/oc-qos:two-rate-three-color/oc-qos:conform-action" {
      description
          "Not supported in this release";
      deviate not-supported;
  }
  deviation "/oc-qos:qos/oc-qos:scheduler-policies/oc-qos:scheduler-policy/oc-qos:schedulers/oc-qos:scheduler/oc-qos:two-rate-three-color/oc-qos:exceed-action" {
      description
          "Not supported in this release";
      deviate not-supported;
  }
  deviation "/oc-qos:qos/oc-qos:scheduler-policies/oc-qos:scheduler-policy/oc-qos:schedulers/oc-qos:scheduler/oc-qos:two-rate-three-color/oc-qos:violate-action" {
      description
          "Not supported in this release";
      deviate not-supported;
  }
  deviation "/oc-qos:qos/oc-qos:scheduler-policies/oc-qos:scheduler-policy/oc-qos:schedulers/oc-qos:scheduler/oc-qos:one-rate-two-color/oc-qos:config/oc-qos:bc" {
      description
          "Not supported in this release";
      deviate not-supported;
  }
  deviation "/oc-qos:qos/oc-qos:scheduler-policies/oc-qos:scheduler-policy/oc-qos:schedulers/oc-qos:scheduler/oc-qos:one-rate-two-color/oc-qos:config/oc-qos:max-queue-depth-bytes" {
      description
          "Not supported in this release";
      deviate not-supported;
  }
  deviation "/oc-qos:qos/oc-qos:scheduler-policies/oc-qos:scheduler-policy/oc-qos:schedulers/oc-qos:scheduler/oc-qos:one-rate-two-color/oc-qos:config/oc-qos:max-queue-depth-packets" {
      description
          "Not supported in this release";
      deviate not-supported;
  }
  deviation "/oc-qos:qos/oc-qos:scheduler-policies/oc-qos:scheduler-policy/oc-qos:schedulers/oc-qos:scheduler/oc-qos:one-rate-two-color/oc-qos:state/oc-qos:bc" {
      description
          "Not supported in this release";
      deviate not-supported;
  }
  deviation "/oc-qos:qos/oc-qos:scheduler-policies/oc-qos:scheduler-policy/oc-qos:schedulers/oc-qos:scheduler/oc-qos:one-rate-two-color/oc-qos:state/oc-qos:max-queue-depth-bytes" {
      description
          "Not supported in this release";
      deviate not-supported;
  }
  deviation "/oc-qos:qos/oc-qos:scheduler-policies/oc-qos:scheduler-policy/oc-qos:schedulers/oc-qos:scheduler/oc-qos:one-rate-two-color/oc-qos:state/oc-qos:max-queue-depth-packets" {
      description
          "Not supported in this release";
      deviate not-supported;
  }
  deviation "/oc-qos:qos/oc-qos:scheduler-policies/oc-qos:scheduler-policy/oc-qos:schedulers/oc-qos:scheduler/oc-qos:one-rate-two-color/oc-qos:conform-action" {
      description
          "Not supported in this release";
      deviate not-supported;
  }
  deviation "/oc-qos:qos/oc-qos:scheduler-policies/oc-qos:scheduler-policy/oc-qos:schedulers/oc-qos:scheduler/oc-qos:one-rate-two-color/oc-qos:exceed-action" {
      description
          "Not supported in this release";
      deviate not-supported;
  }
  deviation "/oc-qos:qos/oc-qos:interfaces/oc-qos:interface/oc-qos:input/oc-qos:config"{
      description
          "Not supported in this release";
      deviate not-supported;
  }
  deviation "/oc-qos:qos/oc-qos:interfaces/oc-qos:interface/oc-qos:input/oc-qos:state"{
      description
          "Not supported in this release";
      deviate not-supported;
  }
  deviation "/oc-qos:qos/oc-qos:interfaces/oc-qos:interface/oc-qos:input/oc-qos:classifiers/oc-qos:classifier/oc-qos:terms"{
      description
          "Not supported in this release";
      deviate not-supported;
  }
  deviation "/oc-qos:qos/oc-qos:interfaces/oc-qos:interface/oc-qos:input/oc-qos:queues/oc-qos:queue/oc-qos:config"{
      description
          "Not supported in this release";
      deviate not-supported;
  }
  deviation "/oc-qos:qos/oc-qos:interfaces/oc-qos:interface/oc-qos:input/oc-qos:queues/oc-qos:queue/oc-qos:state/oc-qos:queue-management-profile"{
      description
          "Not supported in this release";
      deviate not-supported;
  }
  deviation "/oc-qos:qos/oc-qos:interfaces/oc-qos:interface/oc-qos:input/oc-qos:scheduler-policy"{
      description
          "Not supported in this release";
      deviate not-supported;
  }
  deviation "/oc-qos:qos/oc-qos:interfaces/" +
        "oc-qos:interface/oc-qos:input/oc-qos:virtual-output-queues/" +
        "oc-qos:voq-interface/oc-qos:config" {
       description
            "Not supported in this release";
       deviate not-supported;
  }
  deviation "/oc-qos:qos/oc-qos:interfaces/" +
        "oc-qos:interface/oc-qos:input/oc-qos:virtual-output-queues/" +
        "oc-qos:voq-interface/oc-qos:state" {
       description
            "Not supported in this release";
       deviate not-supported;
  }
  deviation "/oc-qos:qos/oc-qos:interfaces/" +
        "oc-qos:interface/oc-qos:input/oc-qos:virtual-output-queues/" +
        "oc-qos:voq-interface/oc-qos:queues/oc-qos:queue/oc-qos:config" {
       description
            "Not supported in this release";
       deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:name" {
       description
            "transmit packets on voq ingress not supoorted";
       deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:transmit-pkts" {
       description
            "transmit packets on voq ingress not supoorted";
       deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:transmit-octets" {
       description "transmit octets on ingress voq not supported";
       deviate not-supported;
  }
  deviation "/oc-qos:qos/oc-qos:interfaces/" +
        "oc-qos:interface/oc-qos:input/oc-qos:virtual-output-queues/" +
        "oc-qos:voq-interface/oc-qos:queues/oc-qos:queue/oc-qos:state/" +
        "oc-qos:dropped-octets" {
       description "dropped octets on ingress voq not supported";
       deviate not-supported;
  }
  deviation "/oc-qos:qos/oc-qos:interfaces/oc-qos:interface/oc-qos:output/oc-qos:config" {
      description
          "Not supported in this release";
      deviate not-supported;
  }
  deviation "/oc-qos:qos/oc-qos:interfaces/oc-qos:interface/oc-qos:output/oc-qos:state" {
      description
          "Not supported in this release";
      deviate not-supported;
  }
  deviation "/oc-qos:qos/oc-qos:interfaces/oc-qos:interface/oc-qos:output/oc-qos:classifiers/oc-qos:classifier/oc-qos:terms"{
      description
          "Not supported in this release";
      deviate not-supported;
  }
  deviation "/oc-qos:qos/oc-qos:interfaces/oc-qos:interface/oc-qos:output/oc-qos:scheduler-policy/oc-qos:schedulers"{
      description
          "Not supported in this release";
      deviate not-supported;
  }
  deviation "/oc-qos:qos/oc-qos:buffer-allocation-profiles"{
      description
          "buffer allocation profiles are not supported";
      deviate not-supported;
  }
  deviation "/oc-qos:qos/oc-qos:queue-management-profiles/" +
        "oc-qos:queue-management-profile/oc-qos:red" {
      description
            "red profile is not supported";
      deviate not-supported;
  }

  // IGMP Deviations
  deviation "/oc-ni:network-instances/oc-ni:network-instance/oc-ni:protocols/oc-ni:protocol/oc-ni:igmp/oc-ni:global" {
       deviate not-supported;
  }
  deviation "/oc-ni:network-instances/oc-ni:network-instance/oc-ni:protocols/oc-ni:protocol/oc-ni:igmp/" +
         "oc-ni:interfaces/oc-ni:interface/oc-ni:config/oc-ni:query-interval" {
       deviate not-supported;
  }
  deviation "/oc-ni:network-instances/oc-ni:network-instance/oc-ni:protocols/oc-ni:protocol/oc-ni:igmp/" +
         "oc-ni:interfaces/oc-ni:interface/oc-ni:interface-ref" {
       deviate not-supported;
  }

  // Pim Deviations
  deviation "/oc-ni:network-instances/oc-ni:network-instance/oc-ni:protocols/oc-ni:protocol/oc-ni:pim/" +
         "oc-ni:global/oc-ni:sources-joined" {
        deviate not-supported;
  }
  deviation "/oc-ni:network-instances/oc-ni:network-instance/oc-ni:protocols/oc-ni:protocol/oc-ni:pim/" +
         "oc-ni:interfaces/oc-ni:interface/oc-ni:config/oc-ni:join-prune-interval" {
        deviate not-supported;
  }
  deviation "/oc-ni:network-instances/oc-ni:network-instance/oc-ni:protocols/oc-ni:protocol/oc-ni:pim/" +
         "oc-ni:interfaces/oc-ni:interface/oc-ni:config/oc-ni:dead-timer" {
        deviate not-supported;
  }
  deviation "/oc-ni:network-instances/oc-ni:network-instance/oc-ni:protocols/oc-ni:protocol/oc-ni:pim/" +
         "oc-ni:interfaces/oc-ni:interface/oc-ni:state/oc-ni:dead-timer" {
        deviate not-supported;
  }
  deviation "/oc-ni:network-instances/oc-ni:network-instance/oc-ni:protocols/oc-ni:protocol/oc-ni:pim/" +
         "oc-ni:interfaces/oc-ni:interface/oc-ni:config/oc-ni:maximum-groups" {
        deviate not-supported;
  }
  deviation "/oc-ni:network-instances/oc-ni:network-instance/oc-ni:protocols/oc-ni:protocol/oc-ni:pim/" +
         "oc-ni:interfaces/oc-ni:interface/oc-ni:state/oc-ni:maximum-groups" {
        deviate not-supported;
  }
  deviation "/oc-ni:network-instances/oc-ni:network-instance/oc-ni:protocols/oc-ni:protocol/oc-ni:pim/" +
         "oc-ni:interfaces/oc-ni:interface/oc-ni:interface-ref" {
        deviate not-supported;
  }

  // PCEP Deviations
  deviation "/oc-ni:network-instances/oc-ni:network-instance/oc-ni:protocols/oc-ni:protocol/oc-ni:pcep" {
      deviate not-supported;
  }

  deviation "/oc-ni:network-instances/oc-ni:network-instance/oc-ni:afts/oc-ni:policy-forwarding" {
      description
           "Not supported in this release";
      deviate not-supported;
  }

  deviation "/oc-ni:network-instances/oc-ni:network-instance/oc-ni:afts/oc-ni:mpls/oc-ni:label-entry" +
            "/oc-ni:state/oc-ni:counters" {
      description
            "Not supported in this release";
      deviate not-supported;
  }

  deviation "/oc-ni:network-instances/oc-ni:network-instance/oc-ni:afts/oc-ni:mpls/oc-ni:label-entry" +
            "/oc-ni:state/oc-ni:entry-metadata" {
      description
            "Not supported in this release";
      deviate not-supported;
  }

  deviation "/oc-ni:network-instances/oc-ni:network-instance/oc-ni:afts/oc-ni:ethernet" {
      description
           "Not supported in this release";
      deviate not-supported;
  }

  deviation "/oc-ni:network-instances/oc-ni:network-instance/oc-ni:afts/oc-ni:next-hops" +
             "/oc-ni:next-hop/oc-ni:state/oc-ni:counters" {
      description
           "Not supported in this release";
      deviate not-supported;
  }

  deviation "/oc-ni:network-instances/oc-ni:network-instance/oc-ni:afts/oc-ni:next-hops" +
             "/oc-ni:next-hop/oc-ni:state/oc-aftni:network-instance" {
      description
           "Not supported in this release";
      deviate not-supported;
  }

  deviation "/oc-ni:network-instances/oc-ni:network-instance/oc-ni:afts/oc-ni:next-hop-groups" +
             "/oc-ni:next-hop-group/oc-ni:state/oc-ni:backup-next-hop-group" {
      description
           "Not supported in this release";
      deviate not-supported;
  }

  deviation "/oc-ni:network-instances/oc-ni:network-instance/oc-ni:afts/oc-ni:next-hop-groups" +
             "/oc-ni:next-hop-group/oc-ni:state/oc-ni:color" {
      description
           "Not supported in this release";
      deviate not-supported;
  }

  deviation "/oc-ni:network-instances/oc-ni:network-instance/oc-ni:afts/oc-ni:ipv4-unicast" +
             "/oc-ni:ipv4-entry/oc-ni:state/oc-ni:entry-metadata" {
      description
           "Not supported in this release";
      deviate not-supported;
  }

  deviation "/oc-ni:network-instances/oc-ni:network-instance/oc-ni:afts/oc-ni:ipv6-unicast" +
             "/oc-ni:ipv6-entry/oc-ni:state/oc-ni:entry-metadata" {
      description
           "Not supported in this release";
      deviate not-supported;
  }

  deviation "/oc-ni:network-instances/oc-ni:network-instance/oc-ni:afts/oc-ni:ipv6-unicast" +
             "/oc-ni:ipv6-entry/oc-ni:state/oc-ni:counters/oc-ni:packets-forwarded-backup" {
      deviate not-supported;
  }

  deviation "/oc-ni:network-instances/oc-ni:network-instance/oc-ni:afts/oc-ni:ipv6-unicast" +
             "/oc-ni:ipv6-entry/oc-ni:state/oc-ni:counters/oc-ni:octets-forwarded-backup" {
      deviate not-supported;
  }

  deviation "/oc-ni:network-instances/oc-ni:network-instance/oc-ni:afts/oc-ni:ipv4-unicast" +
             "/oc-ni:ipv4-entry/oc-ni:state/oc-ni:counters/oc-ni:packets-forwarded-backup" {
      deviate not-supported;
  }

  deviation "/oc-ni:network-instances/oc-ni:network-instance/oc-ni:afts/oc-ni:ipv4-unicast" +
             "/oc-ni:ipv4-entry/oc-ni:state/oc-ni:counters/oc-ni:octets-forwarded-backup" {
      deviate not-supported;
  }

  deviation /oc-system:system/oc-system:license/oc-system:licenses/oc-system:license/oc-system:config {
      deviate not-supported;
  }

  deviation /oc-system:system/oc-system:license/oc-system:licenses/oc-system:license/oc-system:state/oc-system:issue-date {
      deviate not-supported;
  }

  deviation /oc-system:system/oc-system:messages {
      description
          "Syslog message is not supported";
      deviate not-supported;
  }

  deviation "/oc-telemetry:telemetry-system/oc-telemetry:subscriptions/oc-telemetry:dynamic-subscriptions" +
            "/oc-telemetry:dynamic-subscription/oc-telemetry:state/oc-telemetry:sample-interval" {
      deviate not-supported;
  }

  deviation "/oc-telemetry:telemetry-system/oc-telemetry:subscriptions/oc-telemetry:dynamic-subscriptions" +
            "/oc-telemetry:dynamic-subscription/oc-telemetry:state/oc-telemetry:heartbeat-interval" {
      deviate not-supported;
  }

  deviation "/oc-telemetry:telemetry-system/oc-telemetry:subscriptions/oc-telemetry:dynamic-subscriptions" +
            "/oc-telemetry:dynamic-subscription/oc-telemetry:state/oc-telemetry:suppress-redundant" {
      deviate not-supported;
  }

  deviation "/oc-telemetry:telemetry-system/oc-telemetry:subscriptions/oc-telemetry:dynamic-subscriptions" +
            "/oc-telemetry:dynamic-subscription/oc-telemetry:state/oc-telemetry:originated-qos-marking" {
      deviate not-supported;
  }

  deviation "/oc-telemetry:telemetry-system/oc-telemetry:subscriptions/oc-telemetry:dynamic-subscriptions" +
            "/oc-telemetry:dynamic-subscription/oc-telemetry:sensor-paths/oc-telemetry:sensor-path" +
            "/oc-telemetry:state/oc-telemetry:exclude-filter" {
      deviate not-supported;
  }
  deviation "/oc-telemetry:telemetry-system/oc-telemetry:subscriptions/oc-telemetry:persistent-subscriptions" +
            "/oc-telemetry:persistent-subscription/oc-telemetry:config/oc-telemetry:originated-qos-marking" {
      deviate not-supported;
  }
  deviation "/oc-telemetry:telemetry-system/oc-telemetry:subscriptions/oc-telemetry:persistent-subscriptions" +
            "/oc-telemetry:persistent-subscription/oc-telemetry:destination-groups/oc-telemetry:destination-group/oc-telemetry:state" {
      deviate not-supported;
  }

  deviation "/oc-telemetry:telemetry-system/oc-telemetry:subscriptions/oc-telemetry:persistent-subscriptions" +
            "/oc-telemetry:persistent-subscription/oc-telemetry:state" {
      deviate not-supported;
  }

  deviation "/oc-telemetry:telemetry-system/oc-telemetry:subscriptions/oc-telemetry:persistent-subscriptions" +
            "/oc-telemetry:persistent-subscription/oc-telemetry:sensor-profiles/oc-telemetry:sensor-profile/" +
	    "oc-telemetry:state" {
       deviate not-supported;
  }

  deviation "/oc-telemetry:telemetry-system/oc-telemetry:subscriptions/oc-telemetry:persistent-subscriptions" +
	    "/oc-telemetry:persistent-subscription/oc-telemetry:sensor-profiles/oc-telemetry:sensor-profile/" +
	    "oc-telemetry:config/oc-telemetry:heartbeat-interval" {
      deviate not-supported;
  }

  deviation "/oc-telemetry:telemetry-system/oc-telemetry:subscriptions/oc-telemetry:persistent-subscriptions" +
            "/oc-telemetry:persistent-subscription/oc-telemetry:sensor-profiles/oc-telemetry:sensor-profile/" +
            "oc-telemetry:config/oc-telemetry:suppress-redundant" {
      deviate not-supported;
  }

  deviation "/oc-telemetry:telemetry-system/oc-telemetry:sensor-groups/oc-telemetry:sensor-group/oc-telemetry:state" {
      deviate not-supported;
  }

  deviation "/oc-telemetry:telemetry-system/oc-telemetry:sensor-groups/oc-telemetry:sensor-group/oc-telemetry:sensor-paths" +
            "/oc-telemetry:sensor-path/oc-telemetry:config/oc-telemetry:exclude-filter" {
      deviate not-supported;
  }

  deviation "/oc-telemetry:telemetry-system/oc-telemetry:sensor-groups/oc-telemetry:sensor-group/oc-telemetry:sensor-paths" +
            "/oc-telemetry:sensor-path/oc-telemetry:state" {
      deviate not-supported;
  }

  deviation "/oc-telemetry:telemetry-system/oc-telemetry:destination-groups/oc-telemetry:destination-group/oc-telemetry:state" {
      deviate not-supported;
  }

  deviation "/oc-telemetry:telemetry-system/oc-telemetry:destination-groups/oc-telemetry:destination-group/oc-telemetry:destinations" +
            "/oc-telemetry:destination/oc-telemetry:state" {
      deviate not-supported;
  }
  
  deviation /oc-system:system/oc-sys-grpc:grpc-servers/oc-sys-grpc:grpc-server/oc-sys-grpc:state/oc-sys-grpc:network-instance {
      deviate not-supported;
  }

  /* OC MACsec deviations */
  deviation "/oc-msec:macsec/oc-msec:mka/oc-msec:policies/oc-msec:policy/oc-msec:config/oc-msec:sak-rekey-on-live-peer-loss"{
    deviate not-supported;
  }

  deviation "/oc-msec:macsec/oc-msec:mka/oc-msec:policies/oc-msec:policy/oc-msec:config/oc-msec:use-updated-eth-header"{
    deviate not-supported;
  }

  deviation "/oc-msec:macsec/oc-msec:mka/oc-msec:policies/oc-msec:policy/oc-msec:config/oc-msec:sak-rekey-interval"{
    deviate replace {
      type uint32 {
        range 0..86400;
      }
    }
  }

  deviation "/oc-msec:macsec/oc-msec:mka/oc-msec:key-chains/oc-msec:key-chain/oc-msec:mka-keys/oc-msec:mka-key/oc-msec:id"{
    deviate replace {
      type string {
        length 4..66;
        pattern '([0-5][0-9]|6[0-3])[0-9a-fA-F]*';
      }
    }
  }

  deviation "/oc-msec:macsec/oc-msec:mka/oc-msec:key-chains/oc-msec:key-chain/oc-msec:mka-keys/oc-msec:mka-key/oc-msec:config/oc-msec:id"{
    deviate replace {
      type string {
        length 4..66;
        pattern '([0-5][0-9]|6[0-3])[0-9a-fA-F]*';
      }
    }
  }

  deviation "/oc-msec:macsec/oc-msec:mka/oc-msec:key-chains/oc-msec:key-chain/oc-msec:mka-keys/oc-msec:mka-key/oc-msec:config/oc-msec:key-clear-text"{
    deviate replace {
      type string {
        length 1..126;
      }
    }
  }

  deviation "/oc-msec:macsec/oc-msec:mka/oc-msec:key-chains/oc-msec:key-chain/oc-msec:mka-keys/oc-msec:mka-key/oc-msec:config/oc-msec:cryptographic-algorithm"{
    deviate not-supported;
  }

  deviation "/oc-msec:macsec/oc-msec:mka/oc-msec:key-chains/oc-msec:key-chain/oc-msec:mka-keys/oc-msec:mka-key/oc-msec:config/oc-msec:expiration-date-time"{
    deviate not-supported;
  }

  deviation "/oc-msec:macsec/oc-msec:mka/oc-msec:policies/oc-msec:policy/oc-msec:state/oc-msec:sak-rekey-on-live-peer-loss"{
    deviate not-supported;
  }

  deviation "/oc-msec:macsec/oc-msec:mka/oc-msec:key-chains/oc-msec:key-chain/oc-msec:state"{
    deviate not-supported;
  }

  deviation "/oc-msec:macsec/oc-msec:mka/oc-msec:key-chains/oc-msec:key-chain/oc-msec:mka-keys/oc-msec:mka-key/oc-msec:state"{
    deviate not-supported;
  }

  deviation "/oc-msec:macsec/oc-msec:mka/oc-msec:state"{
    deviate not-supported;
  }

  deviation "/oc-msec:macsec/oc-msec:interfaces/oc-msec:interface/oc-msec:mka/oc-msec:state/oc-msec:mka-policy"{
    deviate not-supported;
  }

  deviation "/oc-msec:macsec/oc-msec:interfaces/oc-msec:interface/oc-msec:mka/oc-msec:state/oc-msec:key-chain"{
    deviate not-supported;
  }

  deviation "/oc-msec:macsec/oc-msec:interfaces/oc-msec:interface/oc-msec:mka/oc-msec:state/oc-msec:counters/oc-msec:in-sak-mkpdu"{
    deviate not-supported;
  }

  deviation "/oc-msec:macsec/oc-msec:interfaces/oc-msec:interface/oc-msec:mka/oc-msec:state/oc-msec:counters/oc-msec:in-cak-mkpdu"{
    deviate not-supported;
  }

  deviation "/oc-msec:macsec/oc-msec:interfaces/oc-msec:interface/oc-msec:mka/oc-msec:state/oc-msec:counters/oc-msec:out-sak-mkpdu"{
    deviate not-supported;
  }

  deviation "/oc-msec:macsec/oc-msec:interfaces/oc-msec:interface/oc-msec:mka/oc-msec:state/oc-msec:counters/oc-msec:out-cak-mkpdu"{
    deviate not-supported;
  }

  deviation "/oc-probes:probes/oc-probes:probe/oc-probes:config/oc-probes:name"{
      deviate not-supported;
  }
  deviation "/oc-probes:probes/oc-probes:probe/oc-probes:config/oc-probes:enabled"{
      deviate not-supported;
  }
  deviation "/oc-probes:probes/oc-probes:probe/oc-probes:tests/oc-probes:test/oc-probes:config/oc-probes:name"{
      deviate not-supported;
  }
  deviation "/oc-probes:probes/oc-probes:probe/oc-probes:tests/oc-probes:test/oc-probes:config/oc-probes:enabled"{
      deviate not-supported;
  }
  deviation "/oc-probes:probes/oc-probes:probe/oc-probes:tests/oc-probes:test/oc-probes:config/oc-probes:test-type"{
      deviate not-supported;
  }
  deviation "/oc-probes:probes/oc-probes:probe/oc-probes:tests/oc-probes:test/oc-probes:config/oc-probes:count"{
      deviate not-supported;
  }
  deviation "/oc-probes:probes/oc-probes:probe/oc-probes:tests/oc-probes:test/oc-probes:config/oc-probes:interval"{
      deviate not-supported;
  }
  deviation "/oc-probes:probes/oc-probes:probe/oc-probes:tests/oc-probes:test/oc-probes:config/oc-probes:source"{
      deviate not-supported;
  }
  deviation "/oc-probes:probes/oc-probes:probe/oc-probes:tests/oc-probes:test/oc-probes:config/oc-probes:history-size"{
      deviate not-supported;
  }
  deviation "/oc-probes:probes/oc-probes:probe/oc-probes:tests/oc-probes:test/oc-probes:config/oc-probes:source-port"{
      deviate not-supported;
  }
  deviation "/oc-probes:probes/oc-probes:probe/oc-probes:tests/oc-probes:test/oc-probes:config/oc-probes:dscp"{
      deviate not-supported;
  }
  deviation "/oc-probes:probes/oc-probes:probe/oc-probes:tests/oc-probes:test/oc-probes:target/oc-probes:config/oc-probes:address"{
      deviate not-supported;
  }
  deviation "/oc-probes:probes/oc-probes:probe/oc-probes:tests/oc-probes:test/oc-probes:target/oc-probes:config/oc-probes:port"{
      deviate not-supported;
  }
  deviation "/oc-probes:probes/oc-probes:probe/oc-probes:tests/oc-probes:test/oc-probes:target/oc-probes:config/oc-probes:url"{
      deviate not-supported;
  }

  // openconfig-spanning-tree deviations
  deviation "/oc-stp:stp/oc-stp:global/oc-stp:config/oc-stp:etherchannel-misconfig-guard" {
      deviate not-supported;
  }
  deviation "/oc-stp:stp/oc-stp:global/oc-stp:state/oc-stp:etherchannel-misconfig-guard" {
      deviate not-supported;
  }
  deviation "/oc-stp:stp/oc-stp:global/oc-stp:config/oc-stp:bridge-assurance" {
      deviate not-supported;
  }
  deviation "/oc-stp:stp/oc-stp:global/oc-stp:state/oc-stp:bridge-assurance" {
      deviate not-supported;
  }
  deviation "/oc-stp:stp/oc-stp:global/oc-stp:config/oc-stp:bpdu-filter" {
      deviate not-supported;
  }
  deviation "/oc-stp:stp/oc-stp:global/oc-stp:state/oc-stp:bpdu-filter" {
      deviate not-supported;
  }
  deviation "/oc-stp:stp/oc-stp:rstp/oc-stp:config/oc-stp:hold-count" {
      deviate not-supported;
  }
  deviation "/oc-stp:stp/oc-stp:rstp/oc-stp:interfaces/oc-stp:interface/oc-stp:state/oc-stp:counters" {
      deviate not-supported;
  }
  deviation "/oc-stp:stp/oc-stp:mstp/oc-stp:config/oc-stp:hold-count" {
      deviate not-supported;
  }
  deviation "/oc-stp:stp/oc-stp:mstp/oc-stp:mst-instances/oc-stp:mst-instance/oc-stp:interfaces/oc-stp:interface/oc-stp:state/oc-stp:counters" {
      deviate not-supported;
  }
  deviation "/oc-stp:stp/oc-stp:rapid-pvst/oc-stp:vlan/oc-stp:config/oc-stp:hold-count" {
      deviate not-supported;
  }
  deviation "/oc-stp:stp/oc-stp:rapid-pvst/oc-stp:vlan/oc-stp:interfaces/oc-stp:interface/oc-stp:state/oc-stp:counters" {
      deviate not-supported;
  }
  deviation "/oc-stp:stp/oc-stp:interfaces/oc-stp:interface/oc-stp:config/oc-stp:bpdu-filter" {
      deviate not-supported;
  }
  deviation "/oc-stp:stp/oc-stp:interfaces/oc-stp:interface/oc-stp:state/oc-stp:bpdu-filter" {
      deviate not-supported;
  }

  // openconfig-system state deviations
  deviation /oc-system:system/oc-system:ntp/oc-system:state/oc-system:auth-mismatch {
      deviate not-supported;
  }
  deviation /oc-system:system/oc-system:ntp/oc-system:servers/oc-system:server/oc-system:state/oc-system:source-address {
      deviate not-supported;
  }
  deviation /oc-system:system/oc-system:ntp/oc-system:servers/oc-system:server/oc-system:state/oc-system:stratum {
      deviate not-supported;
  }
  deviation /oc-system:system/oc-system:ntp/oc-system:servers/oc-system:server/oc-system:state/oc-system:root-delay {
      deviate not-supported;
  }
  deviation /oc-system:system/oc-system:ntp/oc-system:servers/oc-system:server/oc-system:state/oc-system:root-dispersion {
      deviate not-supported;
  }
  deviation /oc-system:system/oc-system:ntp/oc-system:servers/oc-system:server/oc-system:state/oc-system:offset {
      deviate not-supported;
  }
  deviation /oc-system:system/oc-system:ntp/oc-system:servers/oc-system:server/oc-system:state/oc-system:poll-interval {
      deviate not-supported;
  }
  deviation /oc-system:system/oc-system:telnet-server/oc-system:state/oc-system:timeout {
      deviate not-supported;
  }
  deviation /oc-system:system/oc-system:aaa/oc-system:state {
      deviate not-supported;
  }
  deviation /oc-system:system/oc-system:aaa/oc-system:authentication/oc-system:admin-user/oc-system:state/oc-system:admin-password {
      deviate not-supported;
  }
  deviation /oc-system:system/oc-system:aaa/oc-system:authentication/oc-system:users/oc-system:user/oc-system:state/oc-system:password {
      deviate not-supported;
  }
  deviation /oc-system:system/oc-system:aaa/oc-system:authentication/oc-system:users/oc-system:user/oc-system:state/oc-system:ssh-key {
      deviate not-supported;
  }
  deviation /oc-system:system/oc-system:aaa/oc-system:authorization/oc-system:state {
      deviate not-supported;
  }
  deviation /oc-system:system/oc-system:aaa/oc-system:accounting/oc-system:state {
      deviate not-supported;
  }
  deviation /oc-system:system/oc-system:aaa/oc-system:accounting/oc-system:events/oc-system:event/oc-system:state/oc-system:record {
      deviate not-supported;
  }
  deviation /oc-system:system/oc-system:aaa/oc-system:server-groups/oc-system:server-group/oc-system:servers/oc-system:server/oc-system:state/oc-system:connection-opens {
      deviate not-supported;
  }
  deviation /oc-system:system/oc-system:aaa/oc-system:server-groups/oc-system:server-group/oc-system:servers/oc-system:server/oc-system:state/oc-system:connection-closes {
      deviate not-supported;
  }
  deviation /oc-system:system/oc-system:aaa/oc-system:server-groups/oc-system:server-group/oc-system:servers/oc-system:server/oc-system:state/oc-system:connection-aborts {
      deviate not-supported;
  }
  deviation /oc-system:system/oc-system:aaa/oc-system:server-groups/oc-system:server-group/oc-system:servers/oc-system:server/oc-system:state/oc-system:connection-failures {
      deviate not-supported;
  }
  deviation /oc-system:system/oc-system:aaa/oc-system:server-groups/oc-system:server-group/oc-system:servers/oc-system:server/oc-system:state/oc-system:connection-timeouts {
      deviate not-supported;
  }
  deviation /oc-system:system/oc-system:aaa/oc-system:server-groups/oc-system:server-group/oc-system:servers/oc-system:server/oc-system:state/oc-system:messages-sent {
      deviate not-supported;
  }
  deviation /oc-system:system/oc-system:aaa/oc-system:server-groups/oc-system:server-group/oc-system:servers/oc-system:server/oc-system:state/oc-system:messages-received {
      deviate not-supported;
  }
  deviation /oc-system:system/oc-system:aaa/oc-system:server-groups/oc-system:server-group/oc-system:servers/oc-system:server/oc-system:state/oc-system:errors-received {
      deviate not-supported;
  }
  deviation /oc-system:system/oc-system:aaa/oc-system:server-groups/oc-system:server-group/oc-system:servers/oc-system:server/oc-system:tacacs/oc-system:state/oc-system:secret-key-hashed {
      deviate not-supported;
  }
  deviation /oc-system:system/oc-system:aaa/oc-system:server-groups/oc-system:server-group/oc-system:servers/oc-system:server/oc-system:radius/oc-system:state/oc-system:secret-key-hashed {
      deviate not-supported;
  }
  deviation /oc-system:system/oc-system:aaa/oc-system:server-groups/oc-system:server-group/oc-system:servers/oc-system:server/oc-system:radius/oc-system:state/oc-system:counters {
      deviate not-supported;
  }
  deviation /oc-messages:messages {
      description
          "Not supported in this release";
      deviate not-supported;
  }
  deviation /oc-platform:components/oc-platform:component/oc-platform:port/oc-port:breakout-mode/oc-port:groups/oc-port:group/oc-port:config/oc-port:index {
      description
          "Not supported in this version";
      deviate not-supported;
  }
  deviation /oc-platform:components/oc-platform:component/oc-platform:port/oc-port:breakout-mode/oc-port:groups/oc-port:group/oc-port:config/oc-port:num-physical-channels {
      description
          "Not supported in this version";
      deviate not-supported;
  }
  deviation /oc-platform:components/oc-platform:component/oc-platform:power-supply/oc-platform:config/oc-platform-psu:enabled {
      description
          "Not supported in this version";
      deviate not-supported;
  }

  deviation "/oc-acl:acl/oc-acl:state"{
        deviate not-supported;
  }

  deviation "/oc-acl:acl/oc-acl:acl-sets/oc-acl:acl-set/oc-acl:acl-entries/oc-acl:acl-entry/oc-acl:input-interface/oc-acl:state"{
        deviate not-supported;
  }

   deviation "/oc-acl:acl/oc-acl:acl-sets/oc-acl:acl-set/oc-acl:acl-entries/oc-acl:acl-entry/oc-acl:mpls/oc-acl:config/oc-acl:ttl-value"{
         deviate not-supported;
   }

   deviation "/oc-acl:acl/oc-acl:acl-sets/oc-acl:acl-set/oc-acl:acl-entries/oc-acl:acl-entry/oc-acl:mpls/oc-acl:state/oc-acl:ttl-value"{
         deviate not-supported;
   }

    /* OC Dot1x deviations  */
    deviation /oc-if:interfaces/oc-if:interface/oc-eth:ethernet/oc-1x:dot1x/oc-1x:config/oc-1x:reauthenticate-interval {
        deviate replace {
            type uint16 {
                range 1..65535;
            }
        }
    }
    deviation /oc-if:interfaces/oc-if:interface/oc-eth:ethernet/oc-1x:dot1x/oc-1x:config/oc-1x:retransmit-interval {
        deviate replace {
            type uint16 {
                range 1..65535;
            }
        }
    }
    deviation /oc-if:interfaces/oc-if:interface/oc-eth:ethernet/oc-1x:dot1x/oc-1x:config/oc-1x:supplicant-timeout {
        deviate replace {
            type uint16 {
                range 1..60;
            }
        }
    }
    deviation /oc-if:interfaces/oc-if:interface/oc-eth:ethernet/oc-1x:dot1x/oc-1x:config/oc-1x:max-requests {
        deviate replace {
            type uint16 {
                range 1..10;
            }
        }
    }
    deviation /oc-if:interfaces/oc-if:interface/oc-eth:ethernet/oc-vlan:switched-vlan/oc-1x:dot1x-vlan-map/oc-1x:vlan-name/oc-1x:config {
        deviate not-supported;
    }

    deviation /oc-if:interfaces/oc-if:interface/oc-eth:ethernet/oc-eth:config/oc-eth:standalone-link-training {
        description
          "Not supported in this release";
        deviate not-supported;
    }
    deviation /oc-if:interfaces/oc-if:interface/oc-eth:ethernet/oc-eth:config/oc-eth:fec-mode {
        description
          "Not supported in this release";
        deviate not-supported;
    }
    deviation "/oc-if:interfaces/oc-if:interface/oc-if:subinterfaces/oc-if:subinterface/oc-vlan:vlan/" +
              "oc-vlan:egress-mapping/oc-vlan:config/oc-vlan:vlan-id" {
        description
          "Junos support is not yet added";
        deviate not-supported;
    }
    deviation "/oc-if:interfaces/oc-if:interface/oc-if:subinterfaces/oc-if:subinterface/oc-vlan:vlan/" +
              "oc-vlan:egress-mapping/oc-vlan:state/oc-vlan:vlan-id" {
        description
          "Junos support is not yet added";
        deviate not-supported;
    }
    deviation "/oc-if:interfaces/oc-if:interface/oc-if:subinterfaces/oc-if:subinterface/oc-ip:ipv4/oc-ip:addresses/" +
	      "oc-ip:address/oc-ip:config/oc-ip:type" {
	description
	    "Junos support is not yet added";
	    deviate not-supported;
    }
}
