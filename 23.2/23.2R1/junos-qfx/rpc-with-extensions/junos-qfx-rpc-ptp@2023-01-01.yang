/*
 * Copyright (c) 2023 Juniper Networks, Inc.
 * All rights reserved.
 */
 module junos-qfx-rpc-ptp {
   namespace "http://yang.juniper.net/junos-qfx/rpc/ptp";

   prefix ptp;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for ptp command(s)";

   revision 2023-01-01 {
     description "Junos: 23.2R1.14";
   }

   rpc get-ptp-global-information {
     description "Show PTP related global information";
     junos:command "show ptp global-information";
     output {
       container ptp-global-information {
         uses ptp-global-information-block;
       }
     }
   }
   rpc get-ptp-slave {
     description "Show interfaces that receive clock from upstream";
     junos:command "show ptp slave";
     input {
       leaf interface {
         description "Name of physical interface";
         type string;
       }
       leaf verbosity {
         junos:cli-feature "nokeyword";
         default "brief";
         type enumeration {
           enum "brief" {
             description "Display brief output";
           }
           enum "detail" {
             description "Display detail output";
           }
         }
       }
     }
     output {
       container ptp-slave-information {
         uses ptp-slave-information-block;
       }
     }
   }
   rpc get-ptp-master-information {
     description "Show interfaces that drive clock to downstream slaves";
     junos:command "show ptp master";
     input {
       leaf interface {
         description "Name of physical interface";
         type string;
       }
       leaf verbosity {
         junos:cli-feature "nokeyword";
         default "brief";
         type enumeration {
           enum "brief" {
             description "Display brief output";
           }
           enum "detail" {
             description "Display detail output";
           }
         }
       }
     }
     output {
       container ptp-master-information {
         uses ptp-master-information-block;
       }
     }
   }
   rpc get-ptp-delay-metrics-short-term-information {
     description "Display short term data";
     junos:command "show ptp performance-monitor short-term";
     input {
       leaf entries {
         description "No of entries to display";
         type union {
           type string {
             pattern "<.*>|$.*";
           }
           type uint32 {
             range "1 .. 96";
           }
         }
       }
     }
     output {
       container ptp-delay-metrics-short-term-information {
         uses ptp-delay-metrics-short-term-information-block;
       }
     }
   }
   rpc get-ptp-delay-metrics-long-term-information {
     description "Display long term data";
     junos:command "show ptp performance-monitor long-term";
     input {
       leaf entry {
         description "Nth last entry to display";
         type union {
           type string {
             pattern "<.*>|$.*";
           }
           type uint32 {
             range "1 .. 30";
           }
         }
       }
     }
   }
   rpc get-ptp-port {
     description "Show port stream details";
     junos:command "show ptp port";
     input {
       leaf remote-ip {
         description "IP address of remote peer";
         type jt:ipaddr;
       }
       leaf ifl {
         description "IFL name of remote peer";
         type string;
       }
       leaf verbosity {
         junos:cli-feature "nokeyword";
         default "brief";
         type enumeration {
           enum "brief" {
             description "Display brief output";
           }
           enum "detail" {
             description "Display detail output";
           }
         }
       }
     }
     output {
       container ptp-port {
         uses ptp-port-block;
       }
     }
   }
   rpc get-ptp-clock {
     description "Show clock details";
     junos:command "show ptp clock";
     input {
       leaf verbosity {
         junos:cli-feature "nokeyword";
         default "detail";
         type enumeration {
           enum "brief" {
             description "Display brief output";
           }
           enum "detail" {
             description "Display detail output";
           }
         }
       }
     }
     output {
       container ptp-clock {
         uses ptp-clock-block;
       }
     }
   }
   rpc get-ptp-masters-debug {
     description "Show All Upstream Masters";
     junos:command "show ptp all-master-clock";
     input {
       leaf verbosity {
         junos:cli-feature "nokeyword";
         default "detail";
         type enumeration {
           enum "brief" {
             description "Display brief output";
           }
           enum "detail" {
             description "Display detail output";
           }
         }
       }
     }
     output {
       container ptp-masters-debug {
         uses ptp-masters-debug-block;
       }
     }
   }
   rpc get-ptp-path-trace {
     description "Show path trace details";
     junos:command "show ptp path-trace";
     input {
       leaf verbosity {
         junos:cli-feature "nokeyword";
         default "brief";
         type enumeration {
           enum "brief" {
             description "Display brief output";
           }
           enum "detail" {
             description "Display detail output";
           }
         }
       }
     }
     output {
       container ptp-path-trace {
         uses ptp-path-trace-block;
       }
     }
   }
   rpc get-ptp-lock-status {
     description "Show PTP slave clock locking status";
     junos:command "show ptp lock-status";
     input {
       leaf verbosity {
         junos:cli-feature "nokeyword";
         default "brief";
         type enumeration {
           enum "brief" {
             description "Display brief output";
           }
           enum "detail" {
             description "Display detail output";
           }
         }
       }
     }
     output {
       container ptp-lock-status {
         uses ptp-lock-status-block;
       }
     }
   }
   rpc get-ptp-statistics-information {
     description "Show PTP statistics";
     junos:command "show ptp statistics";
     input {
       leaf verbosity {
         junos:cli-feature "nokeyword";
         default "brief";
         type enumeration {
           enum "brief" {
             description "Display brief output";
           }
           enum "detail" {
             description "Display detail output";
           }
         }
       }
     }
     output {
       container ptp-statistics-information {
         uses ptp-statistics-information-block;
       }
     }
   }
   rpc get-ae-interfaces {
     description "Show AE interfaces";
     junos:command "show ptp aggregated-ethernet-interfaces";
     input {
       leaf verbosity {
         junos:cli-feature "nokeyword";
         default "brief";
         type enumeration {
           enum "brief" {
             description "Display brief output";
           }
           enum "detail" {
             description "Display detail output";
           }
         }
       }
     }
   }
   rpc get-ptp-quality-level-mapping {
     description "Show PTP clock class to ESMC quality level mapping";
     junos:command "show ptp quality-level-mapping";
     input {
       leaf verbosity {
         junos:cli-feature "nokeyword";
         default "detail";
         type enumeration {
           enum "brief" {
             description "Display brief output";
           }
           enum "detail" {
             description "Display detail output";
           }
         }
       }
     }
     output {
       container ptp-quality-level-mapping {
         uses ptp-quality-level-mapping-block;
       }
     }
   }
   rpc get-ptp-hybrid-status {
     description "Show hybrid mode operational status";
     junos:command "show ptp hybrid status";
     input {
       leaf verbosity {
         junos:cli-feature "nokeyword";
         default "detail";
         type enumeration {
           enum "brief" {
             description "Display brief output";
           }
           enum "detail" {
             description "Display detail output";
           }
         }
       }
     }
     output {
       container ptp-hybrid-status {
         uses ptp-hybrid-status-block;
       }
     }
   }
   rpc get-phy-timestamp-enabled-intfs {
     description "Show interfaces on which PTP PHY time-stamping feature is enabled";
     junos:command "show ptp phy-timestamping-interfaces";
     input {
       leaf verbosity {
         junos:cli-feature "nokeyword";
         default "brief";
         type enumeration {
           enum "brief" {
             description "Display brief output";
           }
           enum "detail" {
             description "Display detail output";
           }
         }
       }
     }
     output {
       container phy-timestamp-enabled-intfs {
         uses phy-timestamp-enabled-intfs-block;
       }
     }
   }
   rpc get-ptp-virtual-port {
     description "Show ptp virtual port details";
     junos:command "show ptp virtual-port";
     input {
       leaf verbosity {
         junos:cli-feature "nokeyword";
         default "detail";
         type enumeration {
           enum "brief" {
             description "Display brief output";
           }
           enum "detail" {
             description "Display detail output";
           }
         }
       }
     }
     output {
       container ptp-virtual-port {
         uses ptp-virtual-port-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ptp-global-information-block {
     leaf ptp-clock-mode {
       type string;
       description "PTP clock mode - Boundary or Ordinary";
     }
     leaf ptp-profile-type {
       type string;
       description "PTP profile type";
     }
     leaf ptp-domain {
       type uint32;
       description "PTP domain number (0...127)";
     }
     leaf ptp-priority1 {
       type uint32;
       description "Priority level1";
     }
     leaf ptp-priority2 {
       type uint32;
       description "Priority level2";
     }
     leaf ptp-local-priority {
       type string;
       description "Local priority";
     }
     leaf ptp-path-trace-enabled {
       type string;
       description "Path tracing enabled or not";
     }
     leaf ptp-uni-neg {
       type string;
       description "Unicast negotiation enabled or not";
     }
     leaf ptp-convert-clock-class {
       type string;
       description "Enable conversion of clock class to ESMC QL or not";
     }
     leaf ptp-converted-esmc-quality-level {
       type string;
       description "String displaying clock class and corresponding ESMC QL";
     }
     leaf ptp-snmp-trap-status {
       type string;
       description "SNMP trap status";
     }
     leaf ptp-phy-time-stamping {
       type string;
       description "PTP PHY time stamping status";
     }
     leaf ptp-utc-leap-secs {
       type uint32;
       description "UTC leap seconds";
     }
     leaf ptp-transparent-clock-config {
       type string;
       description "Transparent clock config enabled or not";
     }
     leaf ptp-transparent-clock-status {
       type string;
       description "Transparent clock status";
     }
     leaf ptp-acquiring-state-announce {
       type string;
       description "PTP Acquiring state announce message contents";
     }
     leaf ptp-holdover-budget {
       type uint32;
       description "PTP Holdover in specification time error budget in nanoseconds";
     }
     leaf ptp-slave-synchronization-interval-string {
       type string;
       description "PTP slave synchronization interval (String Format)";
     }
     leaf ptp-slave-delay-request-string {
       type string;
       description "PTP slave delay request time (String Format)";
     }
     leaf ptp-slave-announce-interval-string {
       type string;
       description "PTP slave announce interval (String Format)";
     }
     leaf ptp-announce-timeout {
       type int32;
       description "PTP announce timeout";
     }
     leaf ptp-grant-duration-string {
       type string;
       description "PTP grant duration";
     }
     leaf ptp-master-synchronization-interval-string {
       type string;
       description "PTP master synchronization interval (String Format)";
     }
     leaf ptp-master-delay-request-string {
       type string;
       description "PTP master delay request time (String Format)";
     }
     leaf ptp-master-announce-interval-string {
       type string;
       description "PTP master announce interval (String Format)";
     }
     leaf ptp-master-min-ann-interval-string {
       type string;
       description "Minimum announce interval that can be negotiated";
     }
     leaf ptp-master-max-ann-interval-string {
       type string;
       description "Maximum announce interval that can be negotiated";
     }
     leaf ptp-master-min-sync-interval-string {
       type string;
       description "Minimum synchronization interval that can be negotiated";
     }
     leaf ptp-master-max-sync-interval-string {
       type string;
       description "Maximum synchronization interval that can be negotiated";
     }
     leaf ptp-master-min-delay-interval-string {
       type string;
       description "Minimum delay-response interval that can be negotiated";
     }
     leaf ptp-master-max-delay-interval-string {
       type string;
       description "Maximum delay-response interval that can be negotiated";
     }
     leaf ptp-master-delay-req-timeout {
       type string;
       description "Delay request timeout(secs) above which clients will be deleted";
     }
     leaf ptp-clock-stepping {
       type string;
       description "Type of clock step";
     }
     leaf ptp-master-arbitrary-mode {
       type string;
       description "Is arbitrary mode configured";
     }
     leaf ptp-slave-count {
       type uint32;
       description "Total number of PTP slaves configured";
     }
     leaf ptp-master-count {
       type uint32;
       description "Total number of PTP masters configured";
     }
     leaf ptp-stateful-count {
       type uint32;
       description "Total number of PTP stateful configured";
     }
     leaf ptp-hypermode-warning-msg {
       type string;
       description "PTP hypermode dependency Warning";
     }
     leaf master {
       type string;
       description "PTP master parameters";
     }
     leaf ptp-slave-uni-neg {
       type string;
       description "Slave unicast negotiation enabled or not";
     }
     leaf ptp-master-uni-neg {
       type string;
       description "Master unicast negotiation enabled or not";
     }
     leaf ptp-total-ports {
       type uint32;
       description "Total number of PTP ports";
     }
   }
   grouping ptp-slave-information-block {
     list ptp-slave {
       description "PTP slave interface details";
       leaf ptp-slave-interface-name {
         type string;
         description "PTP slave interface name";
       }
       leaf ptp-slave-interface-status {
         type string;
         description "Status flags for PTP slave interface";
       }
       leaf ptp-slave-local-addr {
         type string;
         description "Address of local interface that uses this source as master";
       }
       leaf ptp-slave-local-status {
         type string;
         description "Status flags for local PTP slave interface";
       }
       leaf ptp-slave-l2-ifl {
         type string;
         description "L2 IFL used with this local clock";
       }
       leaf ptp-slave-total-masters {
         type uint32;
         description "Total remote masters active for this slave";
       }
       leaf ptp-slave-clock-source-addr {
         type string;
         description "Address of the remote clock source";
       }
       leaf ptp-slave-clock-source-flags {
         type string;
         description "Status flags for the remote clock source";
       }
     }
   }
   grouping ptp-master-information-block {
     list ptp-master {
       description "PTP master interface details";
       leaf ptp-master-interface-name {
         type string;
         description "PTP master interface name";
       }
       leaf ptp-master-interface-status {
         type string;
         description "Status flags for PTP master interface";
       }
       leaf ptp-master-local-addr {
         type string;
         description "Address of local interface which is PTP master";
       }
       leaf ptp-master-local-status {
         type string;
         description "Status flags for PTP master interface";
       }
       leaf ptp-master-l2-ifl {
         type string;
         description "L2 IFL used with this local clock";
       }
       leaf ptp-master-total-slaves {
         type uint32;
         description "Total remove slaves active for this master";
       }
       leaf ptp-master-remote-addr {
         type string;
         description "Address of the remote PTP client";
       }
       leaf ptp-master-remote-status {
         type string;
         description "Status flags for the remote PTP client";
       }
     }
   }
   grouping ptp-delay-metrics-short-term-information-block {
     leaf ptp-delay-metrics-short-term-entries {
       type uint32;
       description "Interval ID";
     }
     leaf ptp-delay-metrics-short-term-valid {
       type string;
       description "Is entry Valid";
     }
     leaf ptp-delay-metrics-short-term-master-id {
       type string;
       description "Master ID";
     }
     leaf ptp-delay-metrics-short-term-slave-id {
       type string;
       description "Slave ID";
     }
     leaf ptp-delay-metrics-short-term-outbound-delay-min {
       type int32;
       description "Outbound min delay";
     }
     leaf ptp-delay-metrics-short-term-outbound-delay-max {
       type int32;
       description "Outbound max delay";
     }
     leaf ptp-delay-metrics-short-term-outbound-delay-avg {
       type int32;
       description "Outbound mean delay";
     }
     leaf ptp-delay-metrics-short-term-inbound-delay-min {
       type int32;
       description "Inbound min";
     }
     leaf ptp-delay-metrics-short-term-inbound-delay-max {
       type int32;
       description "Inbound max";
     }
     leaf ptp-delay-metrics-short-term-inbound-delay-avg {
       type int32;
       description "Inbound mean";
     }
     leaf ptp-delay-metrics-short-term-outbound-jitter-neg {
       type int32;
       description "Outbound negative jitter ";
     }
     leaf ptp-delay-metrics-short-term-outbound-jitter-pos {
       type uint32;
       description "Outbound positive jitter";
     }
     leaf ptp-delay-metrics-short-term-inbound-jitter-neg {
       type int32;
       description "Inbound negative jitter";
     }
     leaf ptp-delay-metrics-short-term-inbound-jitter-pos {
       type uint32;
       description "Inbound positive jitter";
     }
     leaf ptp-delay-metrics-short-term-timestamp {
       type uint32;
       description "Entry Timestamp (seconds)";
     }
     leaf ptp-delay-metrics-short-term-date-time {
       type string;
       description "Entry Timestamp (MM-DD-YYYY)";
     }
     leaf ptp-delay-metrics-short-term-slave-state {
       type string;
       description "PTP Slave state";
     }
   }
   grouping ptp-port-block {
     list ptp-port-information {
       description "Show details of each PTP stream";
       leaf ptp-port-local-interface-name {
         type string;
         description "Local Interface Name";
       }
       leaf ptp-port-l2-ifl {
         type string;
         description "L2 IFL used with this local clock";
       }
       leaf ptp-port-local-addr {
         type string;
         description "Local Address";
       }
       leaf ptp-port-remote-addr {
         type string;
         description "Remote Address";
       }
       leaf ptp-clock-stream-handle {
         type uint32;
         description "PTP Clock Stream Handle";
       }
       leaf ptp-clock-id {
         type string;
         description "Clock stream identity";
       }
       leaf ptp-state-changes {
         type uint32;
         description "Number of state changes for this port";
       }
       leaf ptp-port-state {
         type string;
         description "Clock port state";
       }
       leaf ptp-delay-request {
         type int32;
         description "PTP delay request time";
       }
       leaf ptp-mean-path-delay-high {
         type uint32;
         description "Mean path delay High";
       }
       leaf ptp-mean-path-delay-low {
         type uint32;
         description "Mean path delay Low";
       }
       leaf ptp-announce-interval {
         type int32;
         description "PTP announce interval";
       }
       leaf ptp-announce-timeout {
         type int32;
         description "PTP announce timeout";
       }
       leaf ptp-synchronization-interval {
         type int32;
         description "PTP synchronization interval";
       }
       leaf ptp-delay-mechanism {
         type string;
         description "Delay mechanism";
       }
       leaf ptp-port-number {
         type uint32;
         description "Port Number";
       }
       leaf ptp-op-mode {
         type string;
         description "Operating Mode for stream";
       }
       leaf ptp-local-priority {
         type string;
         description "Local priority";
       }
       leaf ptp-asymmetry {
         type int32;
         description "Asymmetry value configured on this port";
       }
       leaf ptp-dscp {
         type uint32;
         description "DSCP for this port";
       }
       leaf ptp-grant-duration {
         type uint32;
         description "Grant duration for this port";
       }
       leaf ptp-port-vlan-id {
         type string;
         description "Vlan ID for this port";
       }
       leaf ptp-port-priority {
         type string;
         description "PTP port priority bits";
       }
       leaf ptp-erbest-status {
         type string;
         description "Erbest status for virtual port";
       }
       leaf ptp-ptsf {
         type uint32;
         description "PTSF state of the signal";
       }
       leaf ptp-prtc-connected {
         type string;
         description "Is GM connected to Primary reference time clock";
       }
       leaf ptp-virtualport-timesource {
         type uint32;
         description "Time source of the virtual port";
       }
       container ptp-state-time {
         leaf time-length {
           type string;
         }
       }
       leaf ptp-foreign-master-title-string {
         type string;
         description "Title string displyed before foreign master details";
       }
       leaf ptp-foreign-master-clock-id {
         type string;
         description "Foreign master clock id";
       }
       leaf ptp-foreign-master-messages {
         type uint32;
         description "Announce messages in previous time window";
       }
       leaf ptp-foreign-master-current-messages {
         type uint32;
         description "Announce messages in current time window";
       }
     }
   }
   grouping ptp-clock-block {
     leaf ptp-slot-number-string {
       type string;
       description "Title string displyed before foreign master details";
     }
     leaf ptp-two-step-clk {
       type string;
       description "Two step clock";
     }
     leaf ptp-clock-id-default {
       type string;
       description "Clock stream identity (Default Dataset)";
     }
     leaf ptp-number-of-ports {
       type uint32;
       description "Number of ports on device";
     }
     leaf ptp-clock-class {
       type uint32;
       description "Clock quality - class";
     }
     leaf ptp-clock-accuracy {
       type uint32;
       description "PTP clock accuracy";
     }
     leaf ptp-clock-variance {
       type uint32;
       description "Clock quality - Log variance";
     }
     leaf ptp-clock-priority1 {
       type uint32;
       description "Priority1";
     }
     leaf ptp-clock-priority2 {
       type uint32;
       description "Priority2";
     }
     leaf ptp-clock-default-utc-offset {
       type int32;
       description "Default - UTC Offset";
     }
     leaf ptp-clock-default-leap-59 {
       type string;
       description "Default - Leap 59 or not";
     }
     leaf ptp-clock-default-leap-61 {
       type string;
       description "Default - Leap 61 or not";
     }
     leaf ptp-clock-default-time-tracable {
       type string;
       description "Default - Time traceable or not ";
     }
     leaf ptp-clock-default-freq-tracable {
       type string;
       description "Default - Frequency traceable or not";
     }
     leaf ptp-clock-default-time-source {
       type uint32;
       description "Default - time source";
     }
     leaf ptp-clock-delay-request-send-time {
       type int32;
       description "Delay request sending time";
     }
     leaf ptp-clock-steps-removed {
       type uint32;
       description "Steps removed";
     }
     leaf ptp-clock-slave-only {
       type string;
       description "Slave only or master also";
     }
     leaf ptp-local-priority {
       type string;
       description "Local priority";
     }
     leaf ptp-acquiring-state-announce {
       type string;
       description "PTP Acquiring state announce message contents";
     }
     leaf ptp-clock-parent-id {
       type string;
       description "Parent port identity";
     }
     leaf ptp-gmc-id {
       type string;
       description "Gramd Master Identity";
     }
     leaf ptp-gmc-class-str {
       type string;
       description "Grand Master (GM) Clock quality - class";
     }
     leaf ptp-gmc-accuracy-str {
       type string;
       description "GM Clock quality - accuracy";
     }
     leaf ptp-gmc-variance-str {
       type string;
       description "GM Clock quality - Log variance";
     }
     leaf ptp-gmc-priority1 {
       type uint32;
       description "GM Priority1";
     }
     leaf ptp-gmc-priority2-str {
       type string;
       description "GM Priority2";
     }
     leaf ptp-clock-global-utc-offset {
       type int32;
       description "Global - UTC Offset";
     }
     leaf ptp-clock-global-leap-59 {
       type string;
       description "Global - Leap 59 or not";
     }
     leaf ptp-clock-global-leap-61 {
       type string;
       description "Global - Leap 61 or not";
     }
     leaf ptp-clock-global-time-tracable {
       type string;
       description "Global - Time traceable or not ";
     }
     leaf ptp-clock-global-freq-tracable {
       type string;
       description "Global - Frequency traceable or not";
     }
     leaf ptp-clock-global-time-scale {
       type string;
       description "Global - Frequency traceable or not";
     }
     leaf ptp-clock-global-time-source {
       type uint32;
       description "Global - time source";
     }
     leaf ptp-path-trace-member-count {
       type uint32;
       description "Path trace member count";
     }
     leaf ptp-gmc-class {
       type uint32;
       description "Grand Master (GM) Clock quality - class";
     }
     leaf ptp-gmc-accuracy {
       type uint32;
       description "GM Clock quality - accuracy";
     }
     leaf ptp-gmc-variance {
       type uint32;
       description "GM Clock quality - Log variance";
     }
     leaf ptp-gmc-priority2 {
       type uint32;
       description "GM Priority2";
     }
   }
   grouping ptp-masters-debug-block {
     container ptp-master-debug {
       description "Show Debug Master details";
       leaf ptp-slot-number {
         type uint32;
         description "Slot number for each foreign master";
       }
       leaf ptp-clock-parent-id {
         type string;
         description "Parent port identity";
       }
       leaf ptp-gmc-id {
         type string;
         description "Gramd Master Identity";
       }
       leaf ptp-gmc-class-info {
         type uint32;
         description "Grand Master (GM) Clock class";
       }
       leaf ptp-gmc-accuracy-info {
         type uint32;
         description "GM Clock accuracy";
       }
       leaf ptp-gmc-variance-info {
         type int32;
         description "GM Clock Log variance";
       }
       leaf ptp-gmc-priority1-info {
         type uint32;
         description "Foreign Master GM Priority1";
       }
       leaf ptp-gmc-priority2-info {
         type uint32;
         description "Foreign Master GM Priority2";
       }
       leaf ptp-clock-utc-offset-info {
         type int32;
         description "UTC Offset";
       }
       leaf ptp-clock-leap-59-info {
         type string;
         description "Leap 59 or not";
       }
       leaf ptp-clock-leap-61-info {
         type string;
         description "Leap 61 or not";
       }
       leaf ptp-clock-time-tracable-info {
         type string;
         description "Time traceable or not ";
       }
       leaf ptp-clock-freq-tracable-info {
         type string;
         description "Frequency traceable or not";
       }
       leaf ptp-clock-time-scale-info {
         type string;
         description "Frequency traceable or not";
       }
       leaf ptp-clock-time-source-info {
         type uint32;
         description "Time source";
       }
       leaf ptp-clock-unicast-info {
         type string;
         description "Unicast or not";
       }
       leaf ptp-clock-utc-valid-info {
         type string;
         description "UTC Reasonable or not";
       }
       leaf ptp-clock-two-step-info {
         type string;
         description "Two step clock or not";
       }
       leaf ptp-clock-alternate-master-info {
         type string;
         description "Alternate master or not";
       }
       leaf ptp-clock-steps-removed-info {
         type uint32;
         description "Steps removed count";
       }
       leaf ptp-clock-parent-port-id-info {
         type uint32;
         description "Parent Port ID";
       }
       leaf ptp-clock-log-msg-interval-info {
         type int32;
         description "Announcement Interval";
       }
     }
   }
   grouping ptp-path-trace-block {
     leaf path-trace-member-index {
       type uint32;
       description "Path trace member hop count";
     }
     leaf path-trace-member-id {
       type string;
       description "Path trace member's clock identity";
     }
   }
   grouping ptp-lock-status-block {
     leaf ptp-spll-lock-state {
       type uint32;
       description "SPLL Lock State";
     }
     leaf ptp-spll-lock-state-string {
       type string;
       description "SPLL Lock State String";
     }
     leaf ptp-spll-phase-offset {
       type string;
       description "SPLL phase offset";
     }
     leaf ptp-holdover-time-error {
       type string;
       description "Holdover time interval error";
     }
     leaf ptp-lock-source {
       type string;
       description "Lock source of PTP";
     }
     leaf ptp-fsm-header-string {
       type string;
       description "Header string for FSM Status Details";
     }
     leaf ptp-master-address {
       type string;
       description "Address of the upstream master";
     }
     leaf ptp-slave-interface {
       type string;
       description "Interface corresponding to the locked slave";
     }
     leaf ptp-slave-interface-l2-ifl {
       type string;
       description "L2-ifl Interface corresponding to the locked slave";
     }
     leaf ptp-clock-parent-id {
       type string;
       description "Parent port identity";
     }
     leaf ptp-gmc-id {
       type string;
       description "Gramd Master Identity";
     }
     leaf ptp-primary-reference-state {
       type string;
       description "Primary reference(clock) FSM state of locked slave";
     }
     leaf ptp-secondary-reference-state {
       type string;
       description "Secondary reference(1pps) FSM state of locked state";
     }
     leaf ptp-holdover-reason {
       type string;
       description "Holdover state: Sync or DResp or both not recieved while Announce pkts still received";
     }
     container ptp-spll-change-time {
       leaf date-time {
         type string;
       }
       leaf time-length {
         type string;
       }
     }
     leaf ptp-spll-error-flag {
       type string;
       description "SPLL Error String";
     }
   }
   grouping ptp-statistics-information-block {
     list ptp-statistics {
       description "Show clock stream statistics";
       leaf ptp-local-clk {
         type string;
         description "Local Clock";
       }
       leaf ptp-remote-clk {
         type string;
         description "Remote clock";
       }
       leaf ptp-statistics-stream-role {
         type string;
       }
       leaf ptp-clock-stream-handle {
         type uint32;
         description "PTP Clock Stream Handle";
       }
       leaf ptp-clock-statistics-in-unicast-packets {
         type uint64;
         description "In-unicast packets";
       }
       leaf ptp-clock-statistics-out-unicast-packets {
         type uint64;
         description "Out-unicast packets";
       }
       leaf ptp-ae-active-ifd {
         type string;
       }
       leaf ptp-clock-statistics-in-errors {
         type uint32;
         description "In-errors";
       }
       leaf ptp-clock-statistics-out-errors {
         type uint32;
         description "Out-errors";
       }
       container ptp-statistics-detail {
         leaf ptp-statistics-sig-in {
           type uint32;
           description "Signalling packets received";
         }
         leaf ptp-statistics-ann-in {
           type uint32;
           description "Announce packets received";
         }
         leaf ptp-statistics-sync-in {
           type uint32;
           description "Sync packets received";
         }
         leaf ptp-statistics-delay-in {
           type uint32;
           description "Delay-request or delay-response packets received";
         }
         leaf ptp-statistics-error-in {
           type uint32;
           description "Error packets received";
         }
         leaf ptp-statistics-sig-out {
           type uint32;
           description "Signalling packets transmitted";
         }
         leaf ptp-statistics-ann-out {
           type uint32;
           description "Announce packets transmitted";
         }
         leaf ptp-statistics-sync-out {
           type uint32;
           description "Sync packets transmitted";
         }
         leaf ptp-statistics-delay-out {
           type uint32;
           description "Delay-request or delay-response packets transmitted";
         }
         leaf ptp-statistics-error-out {
           type uint32;
           description "Error packets transmitted";
         }
       }
     }
   }
   grouping ptp-quality-level-mapping-block {
     leaf synchronous-ethernet-quality-level {
       type string;
       description "Synchronous Ethernet quality level";
     }
     leaf ptp-clock-class-value {
       type int32;
       description "Ptp clock class mapped to this quality level";
     }
   }
   grouping ptp-hybrid-status-block {
     leaf hybrid-configured-mode {
       type string;
       description "Configuration mode";
     }
     leaf hybrid-operating-mode {
       type string;
       description "Operational mode";
     }
     leaf hybrid-ptp-reference {
       type string;
       description "PTP reference stream";
     }
     leaf hybrid-synchronous-ethernet-reference {
       type string;
       description "Synchronous Ethernet source interface name";
     }
     leaf hybrid-frequency-reference {
       type string;
       description "Hybrid Frequency interface name";
     }
     leaf hybrid-phase-source {
       type string;
       description "Hybrid Phase source";
     }
     leaf hybrid-phase-interface {
       type string;
       description "Hybrid Phase Interface";
     }
     leaf hybrid-frequency-source {
       type string;
       description "Hybrid Frequency source";
     }
     leaf hybrid-frequency-interface {
       type string;
       description "Hybrid Frequency Interface";
     }
     leaf hybrid-lock-state {
       type string;
       description "Hybrid mode lock state";
     }
     leaf hybrid-lock-state-description {
       type string;
       description "Hybrid mode lock state description";
     }
     leaf hybrid-phase-plane-lock-state {
       type string;
       description "Hybrid Phase Plane Lock State";
     }
     leaf hybrid-frequency-plane-lock-state {
       type string;
       description "Hybrid Frequency Plane Lock State";
     }
   }
   grouping phy-timestamp-enabled-intfs-block {
     leaf phy-timestamp-intf-name {
       type string;
       description "Interfaces on which PHY time-stamping feature is enabled";
     }
     leaf phy-timestamp-intf-status {
       type string;
       description "PHY time-stamping feature status";
     }
   }
   grouping ptp-virtual-port-block {
     leaf ptp-port-number {
       type uint32;
       description "Port Number";
     }
     leaf ptp-clock-id {
       type string;
       description "Clock stream identity";
     }
     leaf ptp-local-priority {
       type string;
       description "Local priority";
     }
     leaf ptp-priority1 {
       type uint32;
       description "Priority level1";
     }
     leaf ptp-priority2 {
       type uint32;
       description "Priority level2";
     }
     leaf ptp-op-mode {
       type string;
       description "Operating Mode for stream";
     }
     leaf ptp-erbest-status {
       type string;
       description "Erbest status for virtual port";
     }
     leaf ptp-prtc-connected {
       type string;
       description "Is GM connected to Primary reference time clock";
     }
     leaf ptp-virtualport-timesource {
       type uint32;
       description "Time source of the virtual port";
     }
   }
 }
