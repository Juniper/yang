/*
 * Copyright (c) 2023 Juniper Networks, Inc.
 * All rights reserved.
 */
 module junos-nfx-rpc-fip {
   namespace "http://yang.juniper.net/junos-nfx/rpc/fip";

   prefix fip;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for fip command(s)";

   revision 2023-01-01 {
     description "Junos: 23.2R1.14";
   }

   rpc get-fip-snooping {
     description "Show FIP snooping information";
     junos:command "show fip snooping";
     input {
       leaf verbosity_level {
         junos:cli-feature "nokeyword";
         default "brief";
         type enumeration {
           enum "brief" {
             description "Display brief output (default)";
           }
           enum "detail" {
             description "Display detailed output";
           }
         }
       }
     }
     output {
       container fip-snooping-information {
         uses fip-snooping-information-block;
       }
     }
   }
   rpc get-fip-snooping-scpd-information {
     description "Show FIP snooping information";
     junos:command "show fip snooping satellite";
     input {
       leaf verbosity_level {
         junos:cli-feature "nokeyword";
         default "brief";
         type enumeration {
           enum "brief" {
             description "Display brief output (default)";
           }
           enum "detail" {
             description "Display detailed output";
           }
         }
       }
     }
     output {
       container fip-snooping-information {
         uses fip-snooping-information-block;
       }
     }
   }
   rpc get-fip-snooping-vlan-information {
     description "Show per VLAN information";
     junos:command "show fip snooping satellite vlan";
     input {
       leaf verbosity_level {
         junos:cli-feature "nokeyword";
         default "brief";
         type enumeration {
           enum "brief" {
             description "Display brief output (default)";
           }
           enum "detail" {
             description "Display detailed output";
           }
         }
       }
       leaf vlan-name {
         description "Name of VLAN";
         junos:cli-feature "nokeyword";
         type string;
         mandatory true;
       }
     }
     output {
       container fip-snooping-information {
         uses fip-snooping-information-block;
       }
     }
   }
   rpc get-fip-snooping-fcf-information {
     description "Show fibre-channel forwarder information";
     junos:command "show fip snooping satellite fcf";
     input {
       leaf verbosity_level {
         junos:cli-feature "nokeyword";
         default "brief";
         type enumeration {
           enum "brief" {
             description "Display brief output (default)";
           }
           enum "detail" {
             description "Display detailed output";
           }
         }
       }
       leaf mac {
         description "MAC address of FCF";
         junos:cli-feature "nokeyword";
         type jt:mac-addr;
         mandatory true;
       }
       leaf vlan-name {
         description "Name of VLAN";
         type string;
       }
     }
     output {
       container fip-snooping-fcf-information {
         uses fip-snooping-fcf-information-block;
       }
     }
   }
   rpc get-fip-snooping-enode-information {
     description "Show per enode information";
     junos:command "show fip snooping satellite enode";
     input {
       leaf verbosity_level {
         junos:cli-feature "nokeyword";
         default "brief";
         type enumeration {
           enum "brief" {
             description "Display brief output (default)";
           }
           enum "detail" {
             description "Display detailed output";
           }
         }
       }
       leaf mac {
         description "MAC address of Enode";
         junos:cli-feature "nokeyword";
         type jt:mac-addr;
         mandatory true;
       }
       leaf vlan-name {
         description "Name of VLAN";
         type string;
       }
     }
     output {
       container fip-snooping-enode-information {
         uses fip-snooping-enode-information-block;
       }
     }
   }
   rpc get-fip-snooping-statistics-information {
     description "Show fip-snooping statistics";
     junos:command "show fip snooping satellite statistics";
     input {
       leaf verbosity_level {
         junos:cli-feature "nokeyword";
         default "brief";
         type enumeration {
           enum "brief" {
             description "Display brief output (default)";
           }
           enum "detail" {
             description "Display detailed output";
           }
         }
       }
       leaf vlan-name {
         description "Name of VLAN";
         type string;
       }
     }
     output {
       container fip-snooping-statistics {
         uses fip-snooping-statistics-block;
       }
     }
   }
   rpc get-fip-snooping-debug {
     description "Show fip-snooping satellite debug";
     junos:command "show fip snooping satellite debug";
     input {
       leaf verbosity_level {
         junos:cli-feature "nokeyword";
         default "brief";
         type enumeration {
           enum "brief" {
             description "Display brief output (default)";
           }
           enum "detail" {
             description "Display detailed output";
           }
         }
       }
       leaf fpc {
         description "FPC slot number";
         type union {
           type string {
             pattern "<.*>|$.*";
           }
           type uint32 {
             range "65 .. 254";
           }
         }
       }
     }
     output {
       container fip-snooping-debug {
         uses fip-snooping-debug-block;
       }
     }
   }
   rpc get-fip-snooping-vlan {
     description "Show per VLAN information";
     junos:command "show fip snooping vlan";
     input {
       leaf verbosity_level {
         junos:cli-feature "nokeyword";
         default "brief";
         type enumeration {
           enum "brief" {
             description "Display brief output (default)";
           }
           enum "detail" {
             description "Display detailed output";
           }
         }
       }
       leaf vlan-name {
         description "Name of VLAN";
         junos:cli-feature "nokeyword";
         type string;
         mandatory true;
       }
     }
     output {
       container fip-snooping-information {
         uses fip-snooping-information-block;
       }
     }
   }
   rpc get-fip-snooping-fcf {
     description "Show fibre-channel forwarder information";
     junos:command "show fip snooping fcf";
     input {
       leaf verbosity_level {
         junos:cli-feature "nokeyword";
         default "brief";
         type enumeration {
           enum "brief" {
             description "Display brief output (default)";
           }
           enum "detail" {
             description "Display detailed output";
           }
         }
       }
       leaf mac {
         description "MAC address of FCF";
         junos:cli-feature "nokeyword";
         type jt:mac-addr;
         mandatory true;
       }
       leaf vlan {
         description "Name of VLAN";
         type string;
       }
     }
     output {
       container fip-snooping-fcf-information {
         uses fip-snooping-fcf-information-block;
       }
     }
   }
   rpc get-fip-snooping-enode {
     description "Show per enode information";
     junos:command "show fip snooping enode";
     input {
       leaf verbosity_level {
         junos:cli-feature "nokeyword";
         default "brief";
         type enumeration {
           enum "brief" {
             description "Display brief output (default)";
           }
           enum "detail" {
             description "Display detailed output";
           }
         }
       }
       leaf mac {
         description "MAC address of Enode";
         junos:cli-feature "nokeyword";
         type jt:mac-addr;
         mandatory true;
       }
       leaf vlan {
         description "Name of VLAN";
         type string;
       }
     }
     output {
       container fip-snooping-enode-information {
         uses fip-snooping-enode-information-block;
       }
     }
   }
   rpc get-fip-snooping-interface-information {
     description "Show per interface information";
     junos:command "show fip snooping interface";
     input {
       leaf verbosity_level {
         junos:cli-feature "nokeyword";
         default "brief";
         type enumeration {
           enum "brief" {
             description "Display brief output (default)";
           }
           enum "detail" {
             description "Display detailed output";
           }
         }
       }
       leaf interface-name {
         description "Name of Interface";
         junos:cli-feature "nokeyword";
         type union {
           type jt:interface-name;
           type string {
             pattern "<.*>|$.*";
           }
         }
         mandatory true;
       }
       leaf vlan {
         description "Name of VLAN";
         type string;
       }
     }
     output {
       container fip-snooping-interface-information {
         uses fip-snooping-interface-information-block;
       }
     }
   }
   rpc get-fip-snooping-statistics {
     description "Show FIP snooping statistics";
     junos:command "show fip snooping statistics";
     input {
       leaf vlan {
         description "Name of VLAN";
         type string;
       }
     }
     output {
       container fip-snooping-statistics {
         uses fip-snooping-statistics-block;
       }
     }
   }
   rpc get-fip-snooping-vlandiscovery-enodes {
     description "Show FIP snooping internal vlan discovery enodes";
     junos:command "show fip vlan-discovery enodes";
     output {
       container fip-snooping-vlandiscovery-enodes {
         uses fip-snooping-vlandiscovery-enodes-block;
       }
     }
   }
   rpc get-fip-snooping-vlandiscovery-statistics {
     description "Show FIP snooping internal vlan discovery statistics";
     junos:command "show fip vlan-discovery statistics";
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping fip-snooping-information-block {
     list fip-snooping-vn2vf-vlan-entry {
       leaf fip-vn2vf-vlan-name {
         type string;
         description "FIP VLAN name";
       }
       leaf fip-vn2vf-vlan-mode {
         type string;
         description "FIP VLAN mode";
       }
       leaf fip-vn2vf-vlan-fc-map {
         type string;
         description "FCoE MAC address prefix";
       }
       list fip-snooping-vlan-fcf-entry {
         leaf vlan-fcf-mac {
           type string;
           description "FCF MAC address";
         }
         leaf vlan-fcf-session {
           type uint32;
           description "FCF active sessions";
         }
         list fip-snooping-fcf-enode-entry {
           leaf fcf-enode-mac {
             type string;
             description "Enode MAC address";
           }
           list fip-snooping-vn2vf-session-entry {
             leaf vn2vf-session-vnport-mac {
               type string;
               description "VN-Port MAC address";
             }
             leaf session-vnport-timer {
               type uint32;
               description "VN-Port keep-alive time in seconds";
             }
           }
           leaf fcf-enode-interface {
             type string;
             description "Enode interface name";
           }
           leaf member-interface {
             type string;
             description "Enode member interface name";
           }
           leaf fcf-enode-configuration-timer {
             type uint32;
             description "Configured Enode keep-alive time in seconds";
           }
           leaf fcf-enode-running-timer {
             type uint32;
             description "Running Enode keep-alive time in seconds";
           }
         }
         leaf vlan-fcf-configuration-timer {
           type uint32;
           description "Configured keep-alive time in seconds";
         }
         leaf vlan-fcf-running-timer {
           type uint32;
           description "Running keep-alive time in seconds";
         }
       }
     }
     list fip-snooping-vn2vn-vlan-entry {
       leaf fip-vn2vn-vlan-name {
         type string;
         description "FIP VLAN name";
       }
       leaf fip-vn2vn-vlan-mode {
         type string;
         description "FIP VLAN mode";
       }
       leaf fip-vn2vn-vlan-fc-map {
         type string;
         description "FCoE MAC address prefix";
       }
       list fip-snooping-vn2vn-enode-entry {
         leaf vn2vn-enode-mac {
           type string;
           description "VN2VN Enode MAC address";
         }
         leaf enode-vnport-count {
           type uint32;
           description "No. of VN_Ports in Enode";
         }
         list fip-snooping-vn2vn-vnport-entry {
           leaf vnport-mac {
             type string;
             description "Enode MAC address";
           }
           leaf vnport-session-count {
             type uint32;
             description "VN2VN Virtual links from this VN_Port";
           }
           leaf vnport-running-beacon-timer {
             type uint32;
             description "Running beacon period time in milliseconds";
           }
           list fip-snooping-vn2vn-session-entry {
             leaf vn2vn-session-vnport-mac {
               type string;
               description "VN2VN VN-Port MAC address";
             }
           }
         }
         leaf vn2vn-enode-interface {
           type string;
           description "Enode interface name";
         }
       }
       leaf fip-vlan-beacon-period {
         type uint32;
         description "VN_Port keep-alive time in miliseconds";
       }
       leaf fip-vlan-vn2vn-mode {
         type string;
         description "VLAN VN2VN mode";
       }
     }
   }
   grouping fip-snooping-fcf-information-block {
     list fip-snooping-fcf-entry {
       leaf fcf-mac {
         type string;
         description "FCF MAC address";
       }
       leaf fcf-vlan {
         type string;
         description "VLAN name";
       }
       leaf fcf-session {
         type uint32;
         description "FCF active sessions";
       }
       list fip-snooping-fcf-enode-entry {
         leaf fcf-enode-mac {
           type string;
           description "Enode MAC address";
         }
         list fip-snooping-vn2vf-session-entry {
           leaf vn2vf-session-vnport-mac {
             type string;
             description "VN-Port MAC address";
           }
           leaf session-vnport-timer {
             type uint32;
             description "VN-Port keep-alive time in seconds";
           }
         }
         leaf fcf-enode-interface {
           type string;
           description "Enode interface name";
         }
         leaf member-interface {
           type string;
           description "Enode member interface name";
         }
         leaf fcf-enode-configuration-timer {
           type uint32;
           description "Configured Enode keep-alive time in seconds";
         }
         leaf fcf-enode-running-timer {
           type uint32;
           description "Running Enode keep-alive time in seconds";
         }
       }
       leaf fcf-configuration-timer {
         type uint32;
         description "Configured keep-alive time in seconds";
       }
       leaf fcf-running-timer {
         type uint32;
         description "Running keep-alive time in seconds";
       }
     }
   }
   grouping fip-snooping-enode-information-block {
     list fip-snooping-vn2vf-enode-entry {
       leaf vn2vf-enode-mac {
         type string;
         description "Enode MAC address";
       }
       leaf vn2vf-enode-vlan {
         type string;
         description "VLAN name";
       }
       leaf vn2vf-enode-interface {
         type string;
         description "Enode interface name";
       }
       leaf member-interface {
         type string;
         description "Enode member interface name";
       }
       list fip-snooping-vn2vf-session-entry {
         leaf vn2vf-session-vnport-mac {
           type string;
           description "VN-Port MAC address";
         }
         leaf session-fcf-mac {
           type string;
           description "FCF MAC address";
         }
         leaf session-vnport-timer {
           type uint32;
           description "VN-Port keep-alive time in seconds";
         }
       }
       leaf enode-configuration-timer {
         type uint32;
         description "Configured Enode keep-alive time in seconds";
       }
       leaf enode-running-timer {
         type uint32;
         description "Running Enode keep-alive time in seconds";
       }
     }
     list fip-snooping-vn2vn-enode-entry {
       leaf vn2vn-enode-mac {
         type string;
         description "VN2VN Enode MAC address";
       }
       leaf vn2vn-enode-vlan {
         type string;
         description "VN2VN VLAN name";
       }
       leaf vn2vn-enode-interface {
         type string;
         description "Enode interface name";
       }
       leaf enode-vlan-mode {
         type string;
         description "VN2VN VLAN mode";
       }
       leaf enode-vnport-count {
         type uint32;
         description "No. of VN_Ports in Enode";
       }
       list fip-snooping-vn2vn-vnport-entry {
         leaf vnport-mac {
           type string;
           description "Enode MAC address";
         }
         leaf vnport-session-count {
           type uint32;
           description "VN2VN Virtual links from this VN_Port";
         }
         leaf vnport-running-beacon-timer {
           type uint32;
           description "Running beacon period time in milliseconds";
         }
         list fip-snooping-vn2vn-session-entry {
           leaf vn2vn-session-vnport-mac {
             type string;
             description "VN2VN VN-Port MAC address";
           }
         }
       }
       leaf enode-vn2vn-vlan-mode {
         type string;
         description "FIP VLAN mode";
       }
       leaf enode-vlan-beacon-period {
         type uint32;
         description "VN_Port keep-alive time in miliseconds";
       }
     }
   }
   grouping fip-snooping-statistics-block {
     list fip-snooping-vn2vf-vlan-entry {
       leaf fip-vn2vf-vlan-name {
         type string;
         description "FIP VLAN name";
       }
       container fip-snooping-vn2vf-vlan-statistics {
         leaf enode-mds-count {
           type uint32;
         }
         leaf enode-uds-count {
           type uint32;
         }
         leaf enode-flogi-count {
           type uint32;
         }
         leaf enode-fdisc-count {
           type uint32;
         }
         leaf enode-logo-count {
           type uint32;
         }
         leaf enode-ka-count {
           type uint32;
         }
         leaf enode-vnport-ka-count {
           type uint32;
         }
         leaf fcf-mda-count {
           type uint32;
         }
         leaf fcf-uda-count {
           type uint32;
         }
         leaf fcf-flogi-acc-count {
           type uint32;
         }
         leaf fcf-flogi-rjt-count {
           type uint32;
         }
         leaf fcf-fdisc-acc-count {
           type uint32;
         }
         leaf fcf-fdisc-rjt-count {
           type uint32;
         }
         leaf fcf-logo-acc-count {
           type uint32;
         }
         leaf fcf-logo-rjt-count {
           type uint32;
         }
         leaf fcf-cvl-count {
           type uint32;
         }
       }
       list fip-snooping-vlan-fcf-entry {
         list fip-snooping-fcf-enode-entry {
         }
       }
     }
     list fip-snooping-vn2vn-vlan-entry {
       leaf fip-vn2vn-vlan-name {
         type string;
         description "FIP VLAN name";
       }
       container fip-snooping-vn2vn-vlan-statistics {
         leaf probe-request-count {
           type uint32;
         }
         leaf claim-notification-count {
           type uint32;
         }
         leaf vn2vn-beacon-count {
           type uint32;
         }
         leaf probe-reply-count {
           type uint32;
         }
         leaf claim-reply-count {
           type uint32;
         }
         leaf vn2vn-fport-login-count {
           type uint32;
         }
         leaf vn2vn-fport-login-accept-count {
           type uint32;
         }
         leaf vn2vn-fport-login-reject-count {
           type uint32;
         }
         leaf vn2vn-fport-discover-count {
           type uint32;
         }
         leaf vn2vn-fport-discover-accept-count {
           type uint32;
         }
         leaf vn2vn-fport-discover-reject-count {
           type uint32;
         }
         leaf vn2vn-logout-count {
           type uint32;
         }
         leaf vn2vn-logout-accept-count {
           type uint32;
         }
         leaf vn2vn-logout-reject-count {
           type uint32;
         }
       }
       list fip-snooping-vn2vn-enode-entry {
         list fip-snooping-vn2vn-vnport-entry {
         }
       }
     }
   }
   grouping fip-snooping-debug-block {
     list fip-snooping-sd-debug {
       leaf fip-snooping-sd-slot-number {
         type uint32;
       }
       leaf fip-snooping-vlan-eod-sent {
         type string;
       }
       leaf fip-snooping-fcf-eod-sent {
         type string;
       }
     }
   }
   grouping fip-snooping-interface-information-block {
     leaf num-sessions {
       type string;
     }
     list fip-snooping-interface-enode-entry {
       leaf interface-enode-mac {
         type string;
         description "Enode MAC address";
       }
       leaf interface-enode-vlan {
         type string;
         description "VLAN name";
       }
       leaf interface-enode-interface {
         type string;
         description "Interface name";
       }
       list fip-snooping-vn2vf-session-entry {
         leaf vn2vf-session-vnport-mac {
           type string;
           description "VN-Port MAC address";
         }
         leaf session-fcf-mac {
           type string;
           description "FCF MAC address";
         }
         leaf session-vnport-timer {
           type uint32;
           description "VN-Port keep-alive time in seconds";
         }
       }
       leaf interface-enode-configuration-timer {
         type uint32;
         description "Configured Enode keep-alive time in seconds";
       }
       leaf interface-enode-running-timer {
         type uint32;
         description "Running Enode keep-alive time in seconds";
       }
     }
     list fip-snooping-vn2vn-interface-enode-entry {
       leaf vn2vn-enode-mac {
         type string;
         description "VN2VN Enode MAC address";
       }
       leaf vn2vn-enode-vlan {
         type string;
         description "VN2VN VLAN name";
       }
       list fip-snooping-vn2vn-vnport-entry {
         leaf vnport-mac {
           type string;
           description "Enode MAC address";
         }
         leaf vnport-session-count {
           type uint32;
           description "VN2VN Virtual links from this VN_Port";
         }
         leaf vnport-running-beacon-timer {
           type uint32;
           description "Running beacon period time in milliseconds";
         }
         list fip-snooping-vn2vn-session-entry {
           leaf vn2vn-session-vnport-mac {
             type string;
             description "VN2VN VN-Port MAC address";
           }
         }
       }
       leaf vn2vn-enode-interface {
         type string;
         description "Enode interface name";
       }
       leaf enode-vnport-count {
         type uint32;
         description "No. of VN_Ports in Enode";
       }
     }
   }
   grouping fip-snooping-vlandiscovery-enodes-block {
     container fip-snooping-vlandiscovery-enode {
       leaf enode-mac {
         type string;
       }
       leaf fip-snooping-vlandiscovery-interface-name {
         type string;
       }
       leaf unsolicited-notification-count {
         type string;
       }
       leaf vlan-list {
         type string;
       }
     }
   }
 }
