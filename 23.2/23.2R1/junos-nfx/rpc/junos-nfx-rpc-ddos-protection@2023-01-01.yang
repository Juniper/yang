/*
 * Copyright (c) 2023 Juniper Networks, Inc.
 * All rights reserved.
 */
 module junos-nfx-rpc-ddos-protection {
   namespace "http://yang.juniper.net/junos-nfx/rpc/ddos-protection";

   prefix ddos-protection;

   import junos-common-types {
     prefix jt;
     revision-date 2023-01-01;
   }

   organization "Juniper Networks, Inc.";

   contact "yang-support@juniper.net";

   description "Junos RPC YANG module for ddos-protection command(s)";

   revision 2023-01-01 {
     description "Junos: 23.2R1.14";
   }

   rpc get-ddos-protocols-information {
     description "Show protocol information";
     output {
       container ddos-protocols-information {
         uses ddos-protocols-information-block;
       }
     }
   }
   rpc get-ddos-protocols-parameters {
     description "Show parameters for all protocols";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-protocols-statistics {
     description "Show statistics and states for all protocols";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-protocols-violations {
     description "Show summary of all protocol violations";
     output {
       container ddos-protocols-information {
         uses ddos-protocols-information-block;
       }
     }
   }
   rpc get-ddos-flow-detection-parameters {
     description "Show flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-protocols-flows {
     description "Show detected culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipv4-uncls-information {
     description "Show unclassified host-bound IPv4 traffic information";
     status deprecated;
     output {
       container ddos-protocols-information {
         uses ddos-protocols-information-block;
       }
     }
   }
   rpc get-ddos-ipv4-uncls-parameters {
     description "Show IPv4-Unclassified protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv4-uncls-statistics {
     description "Show IPv4-Unclassified statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv4-uncls-violations {
     description "Show IPv4-Unclassified traffic violations";
     output {
       container ddos-protocols-information {
         uses ddos-protocols-information-block;
       }
     }
   }
   rpc get-ddos-ipv4-uncls-flow-parameters {
     description "Show IPv4-Unclassified flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv4-uncls-flows {
     description "Show IPv4-Unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipv4-uncls-aggregate {
     description "Show aggregate for all unclassified host-bound IPv4 traffic information";
     output {
       container ddos-protocols-information {
         uses ddos-protocols-information-block;
       }
     }
   }
   rpc get-ddos-ipv4-uncls-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipv6-uncls-information {
     description "Show unclassified host-bound IPv6 traffic information";
     status deprecated;
     output {
       container ddos-protocols-information {
         uses ddos-protocols-information-block;
       }
     }
   }
   rpc get-ddos-ipv6-uncls-parameters {
     description "Show IPv6-Unclassified protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv6-uncls-statistics {
     description "Show IPv6-Unclassified statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv6-uncls-violations {
     description "Show IPv6-Unclassified traffic violations";
     output {
       container ddos-protocols-information {
         uses ddos-protocols-information-block;
       }
     }
   }
   rpc get-ddos-ipv6-uncls-flow-parameters {
     description "Show IPv6-Unclassified flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipv6-uncls-flows {
     description "Show IPv6-Unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipv6-uncls-aggregate {
     description "Show aggregate for all unclassified host-bound IPv6 traffic information";
     output {
       container ddos-protocols-information {
         uses ddos-protocols-information-block;
       }
     }
   }
   rpc get-ddos-ipv6-uncls-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-information {
     description "Show resolve traffic information";
     output {
       container ddos-protocols-information {
         uses ddos-protocols-information-block;
       }
     }
   }
   rpc get-ddos-resolve-parameters {
     description "Show resolve protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-resolve-statistics {
     description "Show resolve statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-resolve-violations {
     description "Show resolve traffic violations";
     output {
       container ddos-protocols-information {
         uses ddos-protocols-information-block;
       }
     }
   }
   rpc get-ddos-resolve-flow-parameters {
     description "Show resolve flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-resolve-flows {
     description "Show resolve culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-aggregate {
     description "Show aggregate for all resolve traffic information";
     output {
       container ddos-protocols-information {
         uses ddos-protocols-information-block;
       }
     }
   }
   rpc get-ddos-resolve-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-other {
     description "Show all other unclassified resolve packets information";
     output {
       container ddos-protocols-information {
         uses ddos-protocols-information-block;
       }
     }
   }
   rpc get-ddos-resolve-other-flows {
     description "Show other culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-ucast-v4 {
     description "Show ipv4 unicast resolve packets information";
     output {
       container ddos-protocols-information {
         uses ddos-protocols-information-block;
       }
     }
   }
   rpc get-ddos-resolve-ucast-v4-flows {
     description "Show ucast-v4 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-mcast-v4 {
     description "Show ipv4 multicast resolve packets information";
     output {
       container ddos-protocols-information {
         uses ddos-protocols-information-block;
       }
     }
   }
   rpc get-ddos-resolve-mcast-v4-flows {
     description "Show mcast-v4 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-ucast-v6 {
     description "Show ipv6 unicast resolve packets information";
     output {
       container ddos-protocols-information {
         uses ddos-protocols-information-block;
       }
     }
   }
   rpc get-ddos-resolve-ucast-v6-flows {
     description "Show ucast-v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-resolve-mcast-v6 {
     description "Show ipv6 multicast resolve packets information";
     output {
       container ddos-protocols-information {
         uses ddos-protocols-information-block;
       }
     }
   }
   rpc get-ddos-resolve-mcast-v6-flows {
     description "Show mcast-v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-filter-act-information {
     description "Show filter action traffic (none-dhcp) information";
     output {
       container ddos-protocols-information {
         uses ddos-protocols-information-block;
       }
     }
   }
   rpc get-ddos-filter-act-parameters {
     description "Show filter-action protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-filter-act-statistics {
     description "Show filter-action statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-filter-act-violations {
     description "Show filter-action traffic violations";
     output {
       container ddos-protocols-information {
         uses ddos-protocols-information-block;
       }
     }
   }
   rpc get-ddos-filter-act-flow-parameters {
     description "Show filter-action flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-filter-act-flows {
     description "Show filter-action culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-filter-act-aggregate {
     description "Show aggregate for all filter action traffic (none-dhcp) information";
     output {
       container ddos-protocols-information {
         uses ddos-protocols-information-block;
       }
     }
   }
   rpc get-ddos-filter-act-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-filter-act-other {
     description "Show non v4/v6 firewall action packets information";
     output {
       container ddos-protocols-information {
         uses ddos-protocols-information-block;
       }
     }
   }
   rpc get-ddos-filter-act-other-flows {
     description "Show other culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-filter-act-filter-v4 {
     description "Show v4 filter action packets information";
     output {
       container ddos-protocols-information {
         uses ddos-protocols-information-block;
       }
     }
   }
   rpc get-ddos-filter-act-filter-v4-flows {
     description "Show filter-v4 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-filter-act-filter-v6 {
     description "Show v6 filter action packets information";
     output {
       container ddos-protocols-information {
         uses ddos-protocols-information-block;
       }
     }
   }
   rpc get-ddos-filter-act-filter-v6-flows {
     description "Show filter-v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dynvlan-information {
     description "Show dynamic vlan exceptions information";
     output {
       container ddos-protocols-information {
         uses ddos-protocols-information-block;
       }
     }
   }
   rpc get-ddos-dynvlan-parameters {
     description "Show Dynamic-Vlan protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dynvlan-statistics {
     description "Show Dynamic-Vlan statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dynvlan-violations {
     description "Show Dynamic-Vlan traffic violations";
     output {
       container ddos-protocols-information {
         uses ddos-protocols-information-block;
       }
     }
   }
   rpc get-ddos-dynvlan-flow-parameters {
     description "Show Dynamic-Vlan flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dynvlan-flows {
     description "Show Dynamic-Vlan culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dynvlan-aggregate {
     description "Show aggregate for all dynamic vlan exceptions information";
     output {
       container ddos-protocols-information {
         uses ddos-protocols-information-block;
       }
     }
   }
   rpc get-ddos-dynvlan-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-information {
     description "Show PPP control traffic information";
     output {
       container ddos-protocols-information {
         uses ddos-protocols-information-block;
       }
     }
   }
   rpc get-ddos-ppp-parameters {
     description "Show PPP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ppp-statistics {
     description "Show PPP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ppp-violations {
     description "Show PPP traffic violations";
     output {
       container ddos-protocols-information {
         uses ddos-protocols-information-block;
       }
     }
   }
   rpc get-ddos-ppp-flow-parameters {
     description "Show PPP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ppp-flows {
     description "Show PPP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-aggregate {
     description "Show aggregate for all PPP control traffic information";
     output {
       container ddos-protocols-information {
         uses ddos-protocols-information-block;
       }
     }
   }
   rpc get-ddos-ppp-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-unclass {
     description "Show unclassified PPP control traffic information";
     output {
       container ddos-protocols-information {
         uses ddos-protocols-information-block;
       }
     }
   }
   rpc get-ddos-ppp-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-lcp {
     description "Show Link Control Protocol information";
     output {
       container ddos-protocols-information {
         uses ddos-protocols-information-block;
       }
     }
   }
   rpc get-ddos-ppp-lcp-flows {
     description "Show lcp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-auth {
     description "Show Authentication Protocol information";
     output {
       container ddos-protocols-information {
         uses ddos-protocols-information-block;
       }
     }
   }
   rpc get-ddos-ppp-auth-flows {
     description "Show authentication culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-ipcp {
     description "Show IP Control Protocol information";
     output {
       container ddos-protocols-information {
         uses ddos-protocols-information-block;
       }
     }
   }
   rpc get-ddos-ppp-ipcp-flows {
     description "Show ipcp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-ipv6cp {
     description "Show IPv6 Control Protocol information";
     output {
       container ddos-protocols-information {
         uses ddos-protocols-information-block;
       }
     }
   }
   rpc get-ddos-ppp-ipv6cp-flows {
     description "Show ipv6cp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-mplscp {
     description "Show MPLS Control Protocol information";
     output {
       container ddos-protocols-information {
         uses ddos-protocols-information-block;
       }
     }
   }
   rpc get-ddos-ppp-mplscp-flows {
     description "Show mplscp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-isis {
     description "Show ISIS Protocol information";
     output {
       container ddos-protocols-information {
         uses ddos-protocols-information-block;
       }
     }
   }
   rpc get-ddos-ppp-isis-flows {
     description "Show isis culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-echo-req {
     description "Show LCP Echo Request information";
     output {
       container ddos-protocols-information {
         uses ddos-protocols-information-block;
       }
     }
   }
   rpc get-ddos-ppp-echo-req-flows {
     description "Show echo-req culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-echo-rep {
     description "Show LCP Echo Reply information";
     output {
       container ddos-protocols-information {
         uses ddos-protocols-information-block;
       }
     }
   }
   rpc get-ddos-ppp-echo-rep-flows {
     description "Show echo-rep culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ppp-mlppp-lcp {
     description "Show MLPPP LCP information";
     output {
       container ddos-protocols-information {
         uses ddos-protocols-information-block;
       }
     }
   }
   rpc get-ddos-ppp-mlppp-lcp-flows {
     description "Show mlppp-lcp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-information {
     description "Show PPPoE control traffic information";
     output {
       container ddos-protocols-information {
         uses ddos-protocols-information-block;
       }
     }
   }
   rpc get-ddos-pppoe-parameters {
     description "Show PPPoE protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pppoe-statistics {
     description "Show PPPoE statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pppoe-violations {
     description "Show PPPoE traffic violations";
     output {
       container ddos-protocols-information {
         uses ddos-protocols-information-block;
       }
     }
   }
   rpc get-ddos-pppoe-flow-parameters {
     description "Show PPPoE flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pppoe-flows {
     description "Show PPPoE culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-aggregate {
     description "Show aggregate for all PPPoE control traffic information";
     output {
       container ddos-protocols-information {
         uses ddos-protocols-information-block;
       }
     }
   }
   rpc get-ddos-pppoe-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padi {
     description "Show PPPoE PADI information";
     output {
       container ddos-protocols-information {
         uses ddos-protocols-information-block;
       }
     }
   }
   rpc get-ddos-pppoe-padi-flows {
     description "Show padi culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-pado {
     description "Show PPPoE PADO information";
     output {
       container ddos-protocols-information {
         uses ddos-protocols-information-block;
       }
     }
   }
   rpc get-ddos-pppoe-pado-flows {
     description "Show pado culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padr {
     description "Show PPPoE PADR information";
     output {
       container ddos-protocols-information {
         uses ddos-protocols-information-block;
       }
     }
   }
   rpc get-ddos-pppoe-padr-flows {
     description "Show padr culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-pads {
     description "Show PPPoE PADS information";
     output {
       container ddos-protocols-information {
         uses ddos-protocols-information-block;
       }
     }
   }
   rpc get-ddos-pppoe-pads-flows {
     description "Show pads culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padt {
     description "Show PPPoE PADT information";
     output {
       container ddos-protocols-information {
         uses ddos-protocols-information-block;
       }
     }
   }
   rpc get-ddos-pppoe-padt-flows {
     description "Show padt culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padm {
     description "Show PPPoE PADM information";
     output {
       container ddos-protocols-information {
         uses ddos-protocols-information-block;
       }
     }
   }
   rpc get-ddos-pppoe-padm-flows {
     description "Show padm culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padn {
     description "Show PPPoE PADN information";
     output {
       container ddos-protocols-information {
         uses ddos-protocols-information-block;
       }
     }
   }
   rpc get-ddos-pppoe-padn-flows {
     description "Show padn culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pppoe-padse {
     description "Show PPPoE SESSION information";
     output {
       container ddos-protocols-information {
         uses ddos-protocols-information-block;
       }
     }
   }
   rpc get-ddos-pppoe-padse-flows {
     description "Show padse culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-information {
     description "Show DHCPv4 traffic information";
     output {
       container ddos-protocols-information {
         uses ddos-protocols-information-block;
       }
     }
   }
   rpc get-ddos-dhcpv4-parameters {
     description "Show DHCPv4 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4-statistics {
     description "Show DHCPv4 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4-violations {
     description "Show DHCPv4 traffic violations";
     output {
       container ddos-protocols-information {
         uses ddos-protocols-information-block;
       }
     }
   }
   rpc get-ddos-dhcpv4-flow-parameters {
     description "Show DHCPv4 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4-flows {
     description "Show DHCPv4 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-aggregate {
     description "Show aggregate for all DHCPv4 traffic information";
     output {
       container ddos-protocols-information {
         uses ddos-protocols-information-block;
       }
     }
   }
   rpc get-ddos-dhcpv4-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-unclass {
     description "Show unclassified DHCPv4 traffic information";
     output {
       container ddos-protocols-information {
         uses ddos-protocols-information-block;
       }
     }
   }
   rpc get-ddos-dhcpv4-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-discover {
     description "Show DHCPv4 DHCPDISCOVER information";
     output {
       container ddos-protocols-information {
         uses ddos-protocols-information-block;
       }
     }
   }
   rpc get-ddos-dhcpv4-discover-flows {
     description "Show discover culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-offer {
     description "Show DHCPv4 DHCPOFFER information";
     output {
       container ddos-protocols-information {
         uses ddos-protocols-information-block;
       }
     }
   }
   rpc get-ddos-dhcpv4-offer-flows {
     description "Show offer culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-request {
     description "Show DHCPv4 DHCPREQUEST information";
     output {
       container ddos-protocols-information {
         uses ddos-protocols-information-block;
       }
     }
   }
   rpc get-ddos-dhcpv4-request-flows {
     description "Show request culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-decline {
     description "Show DHCPv4 DHCPDECLINE information";
     output {
       container ddos-protocols-information {
         uses ddos-protocols-information-block;
       }
     }
   }
   rpc get-ddos-dhcpv4-decline-flows {
     description "Show decline culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-ack {
     description "Show DHCPv4 DHCPACK information";
     output {
       container ddos-protocols-information {
         uses ddos-protocols-information-block;
       }
     }
   }
   rpc get-ddos-dhcpv4-ack-flows {
     description "Show ack culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-nak {
     description "Show DHCPv4 DHCPNAK information";
     output {
       container ddos-protocols-information {
         uses ddos-protocols-information-block;
       }
     }
   }
   rpc get-ddos-dhcpv4-nak-flows {
     description "Show nak culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-release {
     description "Show DHCPv4 DHCPRELEASE information";
     output {
       container ddos-protocols-information {
         uses ddos-protocols-information-block;
       }
     }
   }
   rpc get-ddos-dhcpv4-release-flows {
     description "Show release culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-inform {
     description "Show DHCPv4 DHCPINFORM information";
     output {
       container ddos-protocols-information {
         uses ddos-protocols-information-block;
       }
     }
   }
   rpc get-ddos-dhcpv4-inform-flows {
     description "Show inform culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-renew {
     description "Show DHCPv4 DHCPRENEW information";
     output {
       container ddos-protocols-information {
         uses ddos-protocols-information-block;
       }
     }
   }
   rpc get-ddos-dhcpv4-renew-flows {
     description "Show renew culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-forcerenew {
     description "Show DHCPv4 DHCPFORCERENEW information";
     output {
       container ddos-protocols-information {
         uses ddos-protocols-information-block;
       }
     }
   }
   rpc get-ddos-dhcpv4-forcerenew-flows {
     description "Show force-renew culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-leasequery {
     description "Show DHCPv4 DHCPLEASEQUERY information";
     output {
       container ddos-protocols-information {
         uses ddos-protocols-information-block;
       }
     }
   }
   rpc get-ddos-dhcpv4-leasequery-flows {
     description "Show lease-query culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-leaseuna {
     description "Show DHCPv4 DHCPLEASEUNASSIGNED information";
     output {
       container ddos-protocols-information {
         uses ddos-protocols-information-block;
       }
     }
   }
   rpc get-ddos-dhcpv4-leaseuna-flows {
     description "Show lease-unassigned culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-leaseunk {
     description "Show DHCPv4 DHCPLEASEUNKOWN information";
     output {
       container ddos-protocols-information {
         uses ddos-protocols-information-block;
       }
     }
   }
   rpc get-ddos-dhcpv4-leaseunk-flows {
     description "Show lease-unknown culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-leaseact {
     description "Show DHCPv4 DHCPLEASEACTIVE information";
     output {
       container ddos-protocols-information {
         uses ddos-protocols-information-block;
       }
     }
   }
   rpc get-ddos-dhcpv4-leaseact-flows {
     description "Show lease-active culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-bootp {
     description "Show DHCPv4 DHCPBOOTP information";
     output {
       container ddos-protocols-information {
         uses ddos-protocols-information-block;
       }
     }
   }
   rpc get-ddos-dhcpv4-bootp-flows {
     description "Show bootp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-rebind {
     description "Show DHCPv4 DHCPREBIND information";
     output {
       container ddos-protocols-information {
         uses ddos-protocols-information-block;
       }
     }
   }
   rpc get-ddos-dhcpv4-rebind-flows {
     description "Show rebind culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-no-msgtype {
     description "Show DHCPv4 traffic with missing message type information";
     output {
       container ddos-protocols-information {
         uses ddos-protocols-information-block;
       }
     }
   }
   rpc get-ddos-dhcpv4-no-msgtype-flows {
     description "Show no-message-type culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4-bad-pack {
     description "Show DHCPv4 traffic with bad format information";
     output {
       container ddos-protocols-information {
         uses ddos-protocols-information-block;
       }
     }
   }
   rpc get-ddos-dhcpv4-bad-pack-flows {
     description "Show bad-packets culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-information {
     description "Show DHCPv6 traffic information";
     output {
       container ddos-protocols-information {
         uses ddos-protocols-information-block;
       }
     }
   }
   rpc get-ddos-dhcpv6-parameters {
     description "Show DHCPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv6-statistics {
     description "Show DHCPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv6-violations {
     description "Show DHCPv6 traffic violations";
     output {
       container ddos-protocols-information {
         uses ddos-protocols-information-block;
       }
     }
   }
   rpc get-ddos-dhcpv6-flow-parameters {
     description "Show DHCPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv6-flows {
     description "Show DHCPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-aggregate {
     description "Show aggregate for all DHCPv6 traffic information";
     output {
       container ddos-protocols-information {
         uses ddos-protocols-information-block;
       }
     }
   }
   rpc get-ddos-dhcpv6-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-unclass {
     description "Show unclassified DHCPv6 traffic information";
     output {
       container ddos-protocols-information {
         uses ddos-protocols-information-block;
       }
     }
   }
   rpc get-ddos-dhcpv6-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-solicit {
     description "Show DHCPv6 SOLICIT information";
     output {
       container ddos-protocols-information {
         uses ddos-protocols-information-block;
       }
     }
   }
   rpc get-ddos-dhcpv6-solicit-flows {
     description "Show solicit culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-advertise {
     description "Show DHCPv6 ADVERTISE information";
     output {
       container ddos-protocols-information {
         uses ddos-protocols-information-block;
       }
     }
   }
   rpc get-ddos-dhcpv6-advertise-flows {
     description "Show advertise culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-request {
     description "Show DHCPv6 REQUEST information";
     output {
       container ddos-protocols-information {
         uses ddos-protocols-information-block;
       }
     }
   }
   rpc get-ddos-dhcpv6-request-flows {
     description "Show request culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-confirm {
     description "Show DHCPv6 CONFIRM information";
     output {
       container ddos-protocols-information {
         uses ddos-protocols-information-block;
       }
     }
   }
   rpc get-ddos-dhcpv6-confirm-flows {
     description "Show confirm culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-renew {
     description "Show DHCPv6 RENEW information";
     output {
       container ddos-protocols-information {
         uses ddos-protocols-information-block;
       }
     }
   }
   rpc get-ddos-dhcpv6-renew-flows {
     description "Show renew culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-rebind {
     description "Show DHCPv6 REBIND information";
     output {
       container ddos-protocols-information {
         uses ddos-protocols-information-block;
       }
     }
   }
   rpc get-ddos-dhcpv6-rebind-flows {
     description "Show rebind culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-reply {
     description "Show DHCPv6 REPLY information";
     output {
       container ddos-protocols-information {
         uses ddos-protocols-information-block;
       }
     }
   }
   rpc get-ddos-dhcpv6-reply-flows {
     description "Show reply culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-release {
     description "Show DHCPv6 RELEASE information";
     output {
       container ddos-protocols-information {
         uses ddos-protocols-information-block;
       }
     }
   }
   rpc get-ddos-dhcpv6-release-flows {
     description "Show release culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-decline {
     description "Show DHCPv6 DECLINE information";
     output {
       container ddos-protocols-information {
         uses ddos-protocols-information-block;
       }
     }
   }
   rpc get-ddos-dhcpv6-decline-flows {
     description "Show decline culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-reconfig {
     description "Show DHCPv6 RECONFIGURE information";
     output {
       container ddos-protocols-information {
         uses ddos-protocols-information-block;
       }
     }
   }
   rpc get-ddos-dhcpv6-reconfig-flows {
     description "Show reconfigure culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-info-req {
     description "Show DHCPv6 INFORMATION-REQUEST information";
     output {
       container ddos-protocols-information {
         uses ddos-protocols-information-block;
       }
     }
   }
   rpc get-ddos-dhcpv6-info-req-flows {
     description "Show information-request culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-relay-for {
     description "Show DHCPv6 RELAY-FORW information";
     output {
       container ddos-protocols-information {
         uses ddos-protocols-information-block;
       }
     }
   }
   rpc get-ddos-dhcpv6-relay-for-flows {
     description "Show relay-forward culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-relay-rep {
     description "Show DHCPv6 RELAY-REPL information";
     output {
       container ddos-protocols-information {
         uses ddos-protocols-information-block;
       }
     }
   }
   rpc get-ddos-dhcpv6-relay-rep-flows {
     description "Show relay-reply culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-leasequery {
     description "Show DHCPv6 LEASEQUERY information";
     output {
       container ddos-protocols-information {
         uses ddos-protocols-information-block;
       }
     }
   }
   rpc get-ddos-dhcpv6-leasequery-flows {
     description "Show leasequery culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-leaseq-re {
     description "Show DHCPv6 LEASEQUERY-REPLY information";
     output {
       container ddos-protocols-information {
         uses ddos-protocols-information-block;
       }
     }
   }
   rpc get-ddos-dhcpv6-leaseq-re-flows {
     description "Show leasequery-reply culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-leaseq-do {
     description "Show DHCPv6 LEASEQUERY-DONE information";
     output {
       container ddos-protocols-information {
         uses ddos-protocols-information-block;
       }
     }
   }
   rpc get-ddos-dhcpv6-leaseq-do-flows {
     description "Show leasequery-done culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv6-leaseq-da {
     description "Show DHCPv6 LEASEQUERY-DATA information";
     output {
       container ddos-protocols-information {
         uses ddos-protocols-information-block;
       }
     }
   }
   rpc get-ddos-dhcpv6-leaseq-da-flows {
     description "Show leasequery-data culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-information {
     description "Show virtual chassis traffic information";
     output {
       container ddos-protocols-information {
         uses ddos-protocols-information-block;
       }
     }
   }
   rpc get-ddos-vchassis-parameters {
     description "Show Virtual-Chassis protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vchassis-statistics {
     description "Show Virtual-Chassis statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vchassis-violations {
     description "Show Virtual-Chassis traffic violations";
     output {
       container ddos-protocols-information {
         uses ddos-protocols-information-block;
       }
     }
   }
   rpc get-ddos-vchassis-flow-parameters {
     description "Show Virtual-Chassis flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vchassis-flows {
     description "Show Virtual-Chassis culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-aggregate {
     description "Show aggregate for all virtual chassis traffic information";
     output {
       container ddos-protocols-information {
         uses ddos-protocols-information-block;
       }
     }
   }
   rpc get-ddos-vchassis-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-unclass {
     description "Show unclassified virtual chassis traffic information";
     output {
       container ddos-protocols-information {
         uses ddos-protocols-information-block;
       }
     }
   }
   rpc get-ddos-vchassis-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-control-hi {
     description "Show high priority control traffic information";
     output {
       container ddos-protocols-information {
         uses ddos-protocols-information-block;
       }
     }
   }
   rpc get-ddos-vchassis-control-hi-flows {
     description "Show control-high culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-control-lo {
     description "Show low priority control traffic information";
     output {
       container ddos-protocols-information {
         uses ddos-protocols-information-block;
       }
     }
   }
   rpc get-ddos-vchassis-control-lo-flows {
     description "Show control-low culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-vc-packets {
     description "Show all exception packets on vc link information";
     output {
       container ddos-protocols-information {
         uses ddos-protocols-information-block;
       }
     }
   }
   rpc get-ddos-vchassis-vc-packets-flows {
     description "Show vc-packets culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vchassis-vc-ttl-err {
     description "Show ttl errors information";
     output {
       container ddos-protocols-information {
         uses ddos-protocols-information-block;
       }
     }
   }
   rpc get-ddos-vchassis-vc-ttl-err-flows {
     description "Show vc-ttl-errors culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-icmp-information {
     description "Show ICMP traffic information";
     output {
       container ddos-protocols-information {
         uses ddos-protocols-information-block;
       }
     }
   }
   rpc get-ddos-icmp-parameters {
     description "Show ICMP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmp-statistics {
     description "Show ICMP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmp-violations {
     description "Show ICMP traffic violations";
     output {
       container ddos-protocols-information {
         uses ddos-protocols-information-block;
       }
     }
   }
   rpc get-ddos-icmp-flow-parameters {
     description "Show ICMP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmp-flows {
     description "Show ICMP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-icmp-aggregate {
     description "Show aggregate for all ICMP traffic information";
     output {
       container ddos-protocols-information {
         uses ddos-protocols-information-block;
       }
     }
   }
   rpc get-ddos-icmp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmp-information {
     description "Show IGMP traffic information";
     output {
       container ddos-protocols-information {
         uses ddos-protocols-information-block;
       }
     }
   }
   rpc get-ddos-igmp-parameters {
     description "Show IGMP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmp-statistics {
     description "Show IGMP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmp-violations {
     description "Show IGMP traffic violations";
     output {
       container ddos-protocols-information {
         uses ddos-protocols-information-block;
       }
     }
   }
   rpc get-ddos-igmp-flow-parameters {
     description "Show IGMP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmp-flows {
     description "Show IGMP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmp-aggregate {
     description "Show aggregate for all IGMP traffic information";
     output {
       container ddos-protocols-information {
         uses ddos-protocols-information-block;
       }
     }
   }
   rpc get-ddos-igmp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmp-query {
     description "Show IGMP Query traffic information";
     output {
       container ddos-protocols-information {
         uses ddos-protocols-information-block;
       }
     }
   }
   rpc get-ddos-igmp-query-flows {
     description "Show query culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmp-report {
     description "Show IGMP Report traffic information";
     output {
       container ddos-protocols-information {
         uses ddos-protocols-information-block;
       }
     }
   }
   rpc get-ddos-igmp-report-flows {
     description "Show report culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mld-information {
     description "Show MLD traffic information";
     output {
       container ddos-protocols-information {
         uses ddos-protocols-information-block;
       }
     }
   }
   rpc get-ddos-mld-parameters {
     description "Show MLD protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mld-statistics {
     description "Show MLD statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mld-violations {
     description "Show MLD traffic violations";
     output {
       container ddos-protocols-information {
         uses ddos-protocols-information-block;
       }
     }
   }
   rpc get-ddos-mld-flow-parameters {
     description "Show MLD flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mld-flows {
     description "Show MLD culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mld-aggregate {
     description "Show aggregate for all MLD traffic information";
     output {
       container ddos-protocols-information {
         uses ddos-protocols-information-block;
       }
     }
   }
   rpc get-ddos-mld-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospf-information {
     description "Show OSPF traffic information";
     output {
       container ddos-protocols-information {
         uses ddos-protocols-information-block;
       }
     }
   }
   rpc get-ddos-ospf-parameters {
     description "Show OSPF protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-statistics {
     description "Show OSPF statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-violations {
     description "Show OSPF traffic violations";
     output {
       container ddos-protocols-information {
         uses ddos-protocols-information-block;
       }
     }
   }
   rpc get-ddos-ospf-flow-parameters {
     description "Show OSPF flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-flows {
     description "Show OSPF culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospf-aggregate {
     description "Show aggregate for all OSPF traffic information";
     output {
       container ddos-protocols-information {
         uses ddos-protocols-information-block;
       }
     }
   }
   rpc get-ddos-ospf-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospf-ospf-uncls {
     description "Show Unclassified OSPF traffic information";
     output {
       container ddos-protocols-information {
         uses ddos-protocols-information-block;
       }
     }
   }
   rpc get-ddos-ospf-ospf-uncls-flows {
     description "Show ospf-uncls culprit flows";
     output {
       container ddos-protocols-information {
         uses ddos-protocols-information-block;
       }
     }
   }
   rpc get-ddos-ospf-ospf-hello {
     description "Show OSPF hello traffic information";
     output {
       container ddos-protocols-information {
         uses ddos-protocols-information-block;
       }
     }
   }
   rpc get-ddos-ospf-ospf-hello-flows {
     description "Show ospf-hello culprit flows";
     output {
       container ddos-protocols-information {
         uses ddos-protocols-information-block;
       }
     }
   }
   rpc get-ddos-rsvp-information {
     description "Show RSVP traffic information";
     output {
       container ddos-protocols-information {
         uses ddos-protocols-information-block;
       }
     }
   }
   rpc get-ddos-rsvp-parameters {
     description "Show RSVP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvp-statistics {
     description "Show RSVP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvp-violations {
     description "Show RSVP traffic violations";
     output {
       container ddos-protocols-information {
         uses ddos-protocols-information-block;
       }
     }
   }
   rpc get-ddos-rsvp-flow-parameters {
     description "Show RSVP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvp-flows {
     description "Show RSVP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rsvp-aggregate {
     description "Show aggregate for all RSVP traffic information";
     output {
       container ddos-protocols-information {
         uses ddos-protocols-information-block;
       }
     }
   }
   rpc get-ddos-rsvp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rsvp-rsvp-uncls {
     description "Show Unclassified RSVP traffic information";
     output {
       container ddos-protocols-information {
         uses ddos-protocols-information-block;
       }
     }
   }
   rpc get-ddos-rsvp-rsvp-uncls-flows {
     description "Show rsvp-uncls culprit flows";
     output {
       container ddos-protocols-information {
         uses ddos-protocols-information-block;
       }
     }
   }
   rpc get-ddos-rsvp-rsvp-hello {
     description "Show RSVP hello traffic information";
     output {
       container ddos-protocols-information {
         uses ddos-protocols-information-block;
       }
     }
   }
   rpc get-ddos-rsvp-rsvp-hello-flows {
     description "Show rsvp-hello culprit flows";
     output {
       container ddos-protocols-information {
         uses ddos-protocols-information-block;
       }
     }
   }
   rpc get-ddos-pim-information {
     description "Show PIM traffic information";
     output {
       container ddos-protocols-information {
         uses ddos-protocols-information-block;
       }
     }
   }
   rpc get-ddos-pim-parameters {
     description "Show PIM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-statistics {
     description "Show PIM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-violations {
     description "Show PIM traffic violations";
     output {
       container ddos-protocols-information {
         uses ddos-protocols-information-block;
       }
     }
   }
   rpc get-ddos-pim-flow-parameters {
     description "Show PIM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-flows {
     description "Show PIM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-aggregate {
     description "Show aggregate for all PIM traffic information";
     output {
       container ddos-protocols-information {
         uses ddos-protocols-information-block;
       }
     }
   }
   rpc get-ddos-pim-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rip-information {
     description "Show RIP traffic information";
     output {
       container ddos-protocols-information {
         uses ddos-protocols-information-block;
       }
     }
   }
   rpc get-ddos-rip-parameters {
     description "Show RIP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rip-statistics {
     description "Show RIP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rip-violations {
     description "Show RIP traffic violations";
     output {
       container ddos-protocols-information {
         uses ddos-protocols-information-block;
       }
     }
   }
   rpc get-ddos-rip-flow-parameters {
     description "Show RIP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rip-flows {
     description "Show RIP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rip-aggregate {
     description "Show aggregate for all RIP traffic information";
     output {
       container ddos-protocols-information {
         uses ddos-protocols-information-block;
       }
     }
   }
   rpc get-ddos-rip-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ptp-information {
     description "Show PTP traffic information";
     output {
       container ddos-protocols-information {
         uses ddos-protocols-information-block;
       }
     }
   }
   rpc get-ddos-ptp-parameters {
     description "Show PTP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptp-statistics {
     description "Show PTP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptp-violations {
     description "Show PTP traffic violations";
     output {
       container ddos-protocols-information {
         uses ddos-protocols-information-block;
       }
     }
   }
   rpc get-ddos-ptp-flow-parameters {
     description "Show PTP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptp-flows {
     description "Show PTP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ptp-aggregate {
     description "Show aggregate for all PTP traffic information";
     output {
       container ddos-protocols-information {
         uses ddos-protocols-information-block;
       }
     }
   }
   rpc get-ddos-ptp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfd-information {
     description "Show BFD traffic information";
     output {
       container ddos-protocols-information {
         uses ddos-protocols-information-block;
       }
     }
   }
   rpc get-ddos-bfd-parameters {
     description "Show BFD protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfd-statistics {
     description "Show BFD statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfd-violations {
     description "Show BFD traffic violations";
     output {
       container ddos-protocols-information {
         uses ddos-protocols-information-block;
       }
     }
   }
   rpc get-ddos-bfd-flow-parameters {
     description "Show BFD flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfd-flows {
     description "Show BFD culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfd-aggregate {
     description "Show aggregate for all BFD traffic information";
     output {
       container ddos-protocols-information {
         uses ddos-protocols-information-block;
       }
     }
   }
   rpc get-ddos-bfd-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfd-unclass {
     description "Show unclassified Unclassified BFD traffic information";
     output {
       container ddos-protocols-information {
         uses ddos-protocols-information-block;
       }
     }
   }
   rpc get-ddos-bfd-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfd-multihop-bfd {
     description "Show Multihop BFD traffic information";
     output {
       container ddos-protocols-information {
         uses ddos-protocols-information-block;
       }
     }
   }
   rpc get-ddos-bfd-multihop-bfd-flows {
     description "Show multihop-bfd culprit flows";
     output {
       container ddos-protocols-information {
         uses ddos-protocols-information-block;
       }
     }
   }
   rpc get-ddos-bfd-bundle-bfd {
     description "Show Bundle BFD traffic information";
     output {
       container ddos-protocols-information {
         uses ddos-protocols-information-block;
       }
     }
   }
   rpc get-ddos-bfd-bundle-bfd-flows {
     description "Show bundle-bfd culprit flows";
     output {
       container ddos-protocols-information {
         uses ddos-protocols-information-block;
       }
     }
   }
   rpc get-ddos-lmp-information {
     description "Show LMP traffic information";
     output {
       container ddos-protocols-information {
         uses ddos-protocols-information-block;
       }
     }
   }
   rpc get-ddos-lmp-parameters {
     description "Show LMP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmp-statistics {
     description "Show LMP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmp-violations {
     description "Show LMP traffic violations";
     output {
       container ddos-protocols-information {
         uses ddos-protocols-information-block;
       }
     }
   }
   rpc get-ddos-lmp-flow-parameters {
     description "Show LMP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmp-flows {
     description "Show LMP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-lmp-aggregate {
     description "Show aggregate for all LMP traffic information";
     output {
       container ddos-protocols-information {
         uses ddos-protocols-information-block;
       }
     }
   }
   rpc get-ddos-lmp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldp-information {
     description "Show LDP traffic information";
     output {
       container ddos-protocols-information {
         uses ddos-protocols-information-block;
       }
     }
   }
   rpc get-ddos-ldp-parameters {
     description "Show LDP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldp-statistics {
     description "Show LDP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldp-violations {
     description "Show LDP traffic violations";
     output {
       container ddos-protocols-information {
         uses ddos-protocols-information-block;
       }
     }
   }
   rpc get-ddos-ldp-flow-parameters {
     description "Show LDP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldp-flows {
     description "Show LDP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldp-aggregate {
     description "Show aggregate for all LDP traffic information";
     output {
       container ddos-protocols-information {
         uses ddos-protocols-information-block;
       }
     }
   }
   rpc get-ddos-ldp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldp-unclass {
     description "Show unclassified Unclassified LDP traffic information";
     output {
       container ddos-protocols-information {
         uses ddos-protocols-information-block;
       }
     }
   }
   rpc get-ddos-ldp-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldp-ldp-hello {
     description "Show LDP Hello traffic information";
     output {
       container ddos-protocols-information {
         uses ddos-protocols-information-block;
       }
     }
   }
   rpc get-ddos-ldp-ldp-hello-flows {
     description "Show ldp-hello culprit flows";
     output {
       container ddos-protocols-information {
         uses ddos-protocols-information-block;
       }
     }
   }
   rpc get-ddos-msdp-information {
     description "Show MSDP traffic information";
     output {
       container ddos-protocols-information {
         uses ddos-protocols-information-block;
       }
     }
   }
   rpc get-ddos-msdp-parameters {
     description "Show MSDP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdp-statistics {
     description "Show MSDP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdp-violations {
     description "Show MSDP traffic violations";
     output {
       container ddos-protocols-information {
         uses ddos-protocols-information-block;
       }
     }
   }
   rpc get-ddos-msdp-flow-parameters {
     description "Show MSDP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdp-flows {
     description "Show MSDP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-msdp-aggregate {
     description "Show aggregate for all MSDP traffic information";
     output {
       container ddos-protocols-information {
         uses ddos-protocols-information-block;
       }
     }
   }
   rpc get-ddos-msdp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bgp-information {
     description "Show BGP traffic information";
     output {
       container ddos-protocols-information {
         uses ddos-protocols-information-block;
       }
     }
   }
   rpc get-ddos-bgp-parameters {
     description "Show BGP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgp-statistics {
     description "Show BGP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgp-violations {
     description "Show BGP traffic violations";
     output {
       container ddos-protocols-information {
         uses ddos-protocols-information-block;
       }
     }
   }
   rpc get-ddos-bgp-flow-parameters {
     description "Show BGP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgp-flows {
     description "Show BGP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bgp-aggregate {
     description "Show aggregate for all BGP traffic information";
     output {
       container ddos-protocols-information {
         uses ddos-protocols-information-block;
       }
     }
   }
   rpc get-ddos-bgp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vrrp-information {
     description "Show VRRP traffic information";
     output {
       container ddos-protocols-information {
         uses ddos-protocols-information-block;
       }
     }
   }
   rpc get-ddos-vrrp-parameters {
     description "Show VRRP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrp-statistics {
     description "Show VRRP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrp-violations {
     description "Show VRRP traffic violations";
     output {
       container ddos-protocols-information {
         uses ddos-protocols-information-block;
       }
     }
   }
   rpc get-ddos-vrrp-flow-parameters {
     description "Show VRRP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrp-flows {
     description "Show VRRP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vrrp-aggregate {
     description "Show aggregate for all VRRP traffic information";
     output {
       container ddos-protocols-information {
         uses ddos-protocols-information-block;
       }
     }
   }
   rpc get-ddos-vrrp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-telnet-information {
     description "Show telnet traffic information";
     output {
       container ddos-protocols-information {
         uses ddos-protocols-information-block;
       }
     }
   }
   rpc get-ddos-telnet-parameters {
     description "Show Telnet protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnet-statistics {
     description "Show Telnet statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnet-violations {
     description "Show Telnet traffic violations";
     output {
       container ddos-protocols-information {
         uses ddos-protocols-information-block;
       }
     }
   }
   rpc get-ddos-telnet-flow-parameters {
     description "Show Telnet flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnet-flows {
     description "Show Telnet culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-telnet-aggregate {
     description "Show aggregate for all telnet traffic information";
     output {
       container ddos-protocols-information {
         uses ddos-protocols-information-block;
       }
     }
   }
   rpc get-ddos-telnet-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ftp-information {
     description "Show FTP traffic information";
     output {
       container ddos-protocols-information {
         uses ddos-protocols-information-block;
       }
     }
   }
   rpc get-ddos-ftp-parameters {
     description "Show FTP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftp-statistics {
     description "Show FTP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftp-violations {
     description "Show FTP traffic violations";
     output {
       container ddos-protocols-information {
         uses ddos-protocols-information-block;
       }
     }
   }
   rpc get-ddos-ftp-flow-parameters {
     description "Show FTP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftp-flows {
     description "Show FTP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ftp-aggregate {
     description "Show aggregate for all FTP traffic information";
     output {
       container ddos-protocols-information {
         uses ddos-protocols-information-block;
       }
     }
   }
   rpc get-ddos-ftp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ssh-information {
     description "Show SSH traffic information";
     output {
       container ddos-protocols-information {
         uses ddos-protocols-information-block;
       }
     }
   }
   rpc get-ddos-ssh-parameters {
     description "Show SSH protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ssh-statistics {
     description "Show SSH statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ssh-violations {
     description "Show SSH traffic violations";
     output {
       container ddos-protocols-information {
         uses ddos-protocols-information-block;
       }
     }
   }
   rpc get-ddos-ssh-flow-parameters {
     description "Show SSH flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ssh-flows {
     description "Show SSH culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ssh-aggregate {
     description "Show aggregate for all SSH traffic information";
     output {
       container ddos-protocols-information {
         uses ddos-protocols-information-block;
       }
     }
   }
   rpc get-ddos-ssh-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-snmp-information {
     description "Show SNMP traffic information";
     output {
       container ddos-protocols-information {
         uses ddos-protocols-information-block;
       }
     }
   }
   rpc get-ddos-snmp-parameters {
     description "Show SNMP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmp-statistics {
     description "Show SNMP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmp-violations {
     description "Show SNMP traffic violations";
     output {
       container ddos-protocols-information {
         uses ddos-protocols-information-block;
       }
     }
   }
   rpc get-ddos-snmp-flow-parameters {
     description "Show SNMP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmp-flows {
     description "Show SNMP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-snmp-aggregate {
     description "Show aggregate for all SNMP traffic information";
     output {
       container ddos-protocols-information {
         uses ddos-protocols-information-block;
       }
     }
   }
   rpc get-ddos-snmp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ancp-information {
     description "Show ANCP traffic information";
     output {
       container ddos-protocols-information {
         uses ddos-protocols-information-block;
       }
     }
   }
   rpc get-ddos-ancp-parameters {
     description "Show ANCP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancp-statistics {
     description "Show ANCP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancp-violations {
     description "Show ANCP traffic violations";
     output {
       container ddos-protocols-information {
         uses ddos-protocols-information-block;
       }
     }
   }
   rpc get-ddos-ancp-flow-parameters {
     description "Show ANCP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancp-flows {
     description "Show ANCP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ancp-aggregate {
     description "Show aggregate for all ANCP traffic information";
     output {
       container ddos-protocols-information {
         uses ddos-protocols-information-block;
       }
     }
   }
   rpc get-ddos-ancp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv6-information {
     description "Show IGMPv6 traffic information";
     output {
       container ddos-protocols-information {
         uses ddos-protocols-information-block;
       }
     }
   }
   rpc get-ddos-igmpv6-parameters {
     description "Show IGMPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv6-statistics {
     description "Show IGMPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv6-violations {
     description "Show IGMPv6 traffic violations";
     output {
       container ddos-protocols-information {
         uses ddos-protocols-information-block;
       }
     }
   }
   rpc get-ddos-igmpv6-flow-parameters {
     description "Show IGMPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv6-flows {
     description "Show IGMPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv6-aggregate {
     description "Show aggregate for all IGMPv6 traffic information";
     output {
       container ddos-protocols-information {
         uses ddos-protocols-information-block;
       }
     }
   }
   rpc get-ddos-igmpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv6-unclass {
     description "Show unclassified Unclassified IGMPv6 traffic information";
     output {
       container ddos-protocols-information {
         uses ddos-protocols-information-block;
       }
     }
   }
   rpc get-ddos-igmpv6-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv6-mld {
     description "Show MLD traffic information";
     output {
       container ddos-protocols-information {
         uses ddos-protocols-information-block;
       }
     }
   }
   rpc get-ddos-igmpv6-mld-flows {
     description "Show mld culprit flows";
     output {
       container ddos-protocols-information {
         uses ddos-protocols-information-block;
       }
     }
   }
   rpc get-ddos-igmpv6-mld-query {
     description "Show MLD Query traffic information";
     output {
       container ddos-protocols-information {
         uses ddos-protocols-information-block;
       }
     }
   }
   rpc get-ddos-igmpv6-mld-query-flows {
     description "Show mld-query culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv6-mld-report {
     description "Show MLD Report traffic information";
     output {
       container ddos-protocols-information {
         uses ddos-protocols-information-block;
       }
     }
   }
   rpc get-ddos-igmpv6-mld-report-flows {
     description "Show mld-report culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-egpv6-information {
     description "Show EGPv6 traffic information";
     output {
       container ddos-protocols-information {
         uses ddos-protocols-information-block;
       }
     }
   }
   rpc get-ddos-egpv6-parameters {
     description "Show EGPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-egpv6-statistics {
     description "Show EGPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-egpv6-violations {
     description "Show EGPv6 traffic violations";
     output {
       container ddos-protocols-information {
         uses ddos-protocols-information-block;
       }
     }
   }
   rpc get-ddos-egpv6-flow-parameters {
     description "Show EGPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-egpv6-flows {
     description "Show EGPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-egpv6-aggregate {
     description "Show aggregate for all EGPv6 traffic information";
     output {
       container ddos-protocols-information {
         uses ddos-protocols-information-block;
       }
     }
   }
   rpc get-ddos-egpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rsvpv6-information {
     description "Show RSVPv6 traffic information";
     output {
       container ddos-protocols-information {
         uses ddos-protocols-information-block;
       }
     }
   }
   rpc get-ddos-rsvpv6-parameters {
     description "Show RSVPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvpv6-statistics {
     description "Show RSVPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvpv6-violations {
     description "Show RSVPv6 traffic violations";
     output {
       container ddos-protocols-information {
         uses ddos-protocols-information-block;
       }
     }
   }
   rpc get-ddos-rsvpv6-flow-parameters {
     description "Show RSVPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rsvpv6-flows {
     description "Show RSVPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rsvpv6-aggregate {
     description "Show aggregate for all RSVPv6 traffic information";
     output {
       container ddos-protocols-information {
         uses ddos-protocols-information-block;
       }
     }
   }
   rpc get-ddos-rsvpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv4v6-information {
     description "Show IGMPv4-v6 traffic information";
     output {
       container ddos-protocols-information {
         uses ddos-protocols-information-block;
       }
     }
   }
   rpc get-ddos-igmpv4v6-parameters {
     description "Show IGMPv4v6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv4v6-statistics {
     description "Show IGMPv4v6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv4v6-violations {
     description "Show IGMPv4v6 traffic violations";
     output {
       container ddos-protocols-information {
         uses ddos-protocols-information-block;
       }
     }
   }
   rpc get-ddos-igmpv4v6-flow-parameters {
     description "Show IGMPv4v6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-igmpv4v6-flows {
     description "Show IGMPv4v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-igmpv4v6-aggregate {
     description "Show aggregate for all IGMPv4-v6 traffic information";
     output {
       container ddos-protocols-information {
         uses ddos-protocols-information-block;
       }
     }
   }
   rpc get-ddos-igmpv4v6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ripv6-information {
     description "Show RIPv6 traffic information";
     output {
       container ddos-protocols-information {
         uses ddos-protocols-information-block;
       }
     }
   }
   rpc get-ddos-ripv6-parameters {
     description "Show RIPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ripv6-statistics {
     description "Show RIPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ripv6-violations {
     description "Show RIPv6 traffic violations";
     output {
       container ddos-protocols-information {
         uses ddos-protocols-information-block;
       }
     }
   }
   rpc get-ddos-ripv6-flow-parameters {
     description "Show RIPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ripv6-flows {
     description "Show RIPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ripv6-aggregate {
     description "Show aggregate for all RIPv6 traffic information";
     output {
       container ddos-protocols-information {
         uses ddos-protocols-information-block;
       }
     }
   }
   rpc get-ddos-ripv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfdv6-information {
     description "Show BFDv6 traffic information";
     output {
       container ddos-protocols-information {
         uses ddos-protocols-information-block;
       }
     }
   }
   rpc get-ddos-bfdv6-parameters {
     description "Show BFDv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfdv6-statistics {
     description "Show BFDv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfdv6-violations {
     description "Show BFDv6 traffic violations";
     output {
       container ddos-protocols-information {
         uses ddos-protocols-information-block;
       }
     }
   }
   rpc get-ddos-bfdv6-flow-parameters {
     description "Show BFDv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bfdv6-flows {
     description "Show BFDv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bfdv6-aggregate {
     description "Show aggregate for all BFDv6 traffic information";
     output {
       container ddos-protocols-information {
         uses ddos-protocols-information-block;
       }
     }
   }
   rpc get-ddos-bfdv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-lmpv6-information {
     description "Show LMPv6 traffic information";
     output {
       container ddos-protocols-information {
         uses ddos-protocols-information-block;
       }
     }
   }
   rpc get-ddos-lmpv6-parameters {
     description "Show LMPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmpv6-statistics {
     description "Show LMPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmpv6-violations {
     description "Show LMPv6 traffic violations";
     output {
       container ddos-protocols-information {
         uses ddos-protocols-information-block;
       }
     }
   }
   rpc get-ddos-lmpv6-flow-parameters {
     description "Show LMPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lmpv6-flows {
     description "Show LMPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-lmpv6-aggregate {
     description "Show aggregate for all LMPv6 traffic information";
     output {
       container ddos-protocols-information {
         uses ddos-protocols-information-block;
       }
     }
   }
   rpc get-ddos-lmpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldpv6-information {
     description "Show LDPv6 traffic information";
     output {
       container ddos-protocols-information {
         uses ddos-protocols-information-block;
       }
     }
   }
   rpc get-ddos-ldpv6-parameters {
     description "Show LDPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldpv6-statistics {
     description "Show LDPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldpv6-violations {
     description "Show LDPv6 traffic violations";
     output {
       container ddos-protocols-information {
         uses ddos-protocols-information-block;
       }
     }
   }
   rpc get-ddos-ldpv6-flow-parameters {
     description "Show LDPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ldpv6-flows {
     description "Show LDPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ldpv6-aggregate {
     description "Show aggregate for all LDPv6 traffic information";
     output {
       container ddos-protocols-information {
         uses ddos-protocols-information-block;
       }
     }
   }
   rpc get-ddos-ldpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-msdpv6-information {
     description "Show MSDPv6 traffic information";
     output {
       container ddos-protocols-information {
         uses ddos-protocols-information-block;
       }
     }
   }
   rpc get-ddos-msdpv6-parameters {
     description "Show MSDPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdpv6-statistics {
     description "Show MSDPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdpv6-violations {
     description "Show MSDPv6 traffic violations";
     output {
       container ddos-protocols-information {
         uses ddos-protocols-information-block;
       }
     }
   }
   rpc get-ddos-msdpv6-flow-parameters {
     description "Show MSDPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-msdpv6-flows {
     description "Show MSDPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-msdpv6-aggregate {
     description "Show aggregate for all MSDPv6 traffic information";
     output {
       container ddos-protocols-information {
         uses ddos-protocols-information-block;
       }
     }
   }
   rpc get-ddos-msdpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bgpv6-information {
     description "Show BGPv6 traffic information";
     output {
       container ddos-protocols-information {
         uses ddos-protocols-information-block;
       }
     }
   }
   rpc get-ddos-bgpv6-parameters {
     description "Show BGPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgpv6-statistics {
     description "Show BGPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgpv6-violations {
     description "Show BGPv6 traffic violations";
     output {
       container ddos-protocols-information {
         uses ddos-protocols-information-block;
       }
     }
   }
   rpc get-ddos-bgpv6-flow-parameters {
     description "Show BGPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-bgpv6-flows {
     description "Show BGPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-bgpv6-aggregate {
     description "Show aggregate for all BGPv6 traffic information";
     output {
       container ddos-protocols-information {
         uses ddos-protocols-information-block;
       }
     }
   }
   rpc get-ddos-bgpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vrrpv6-information {
     description "Show VRRPv6 traffic information";
     output {
       container ddos-protocols-information {
         uses ddos-protocols-information-block;
       }
     }
   }
   rpc get-ddos-vrrpv6-parameters {
     description "Show VRRPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrpv6-statistics {
     description "Show VRRPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrpv6-violations {
     description "Show VRRPv6 traffic violations";
     output {
       container ddos-protocols-information {
         uses ddos-protocols-information-block;
       }
     }
   }
   rpc get-ddos-vrrpv6-flow-parameters {
     description "Show VRRPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vrrpv6-flows {
     description "Show VRRPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vrrpv6-aggregate {
     description "Show aggregate for all VRRPv6 traffic information";
     output {
       container ddos-protocols-information {
         uses ddos-protocols-information-block;
       }
     }
   }
   rpc get-ddos-vrrpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-telnetv6-information {
     description "Show telnet-v6 traffic information";
     output {
       container ddos-protocols-information {
         uses ddos-protocols-information-block;
       }
     }
   }
   rpc get-ddos-telnetv6-parameters {
     description "Show Telnetv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnetv6-statistics {
     description "Show Telnetv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnetv6-violations {
     description "Show Telnetv6 traffic violations";
     output {
       container ddos-protocols-information {
         uses ddos-protocols-information-block;
       }
     }
   }
   rpc get-ddos-telnetv6-flow-parameters {
     description "Show Telnetv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-telnetv6-flows {
     description "Show Telnetv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-telnetv6-aggregate {
     description "Show aggregate for all telnet-v6 traffic information";
     output {
       container ddos-protocols-information {
         uses ddos-protocols-information-block;
       }
     }
   }
   rpc get-ddos-telnetv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ftpv6-information {
     description "Show FTPv6 traffic information";
     output {
       container ddos-protocols-information {
         uses ddos-protocols-information-block;
       }
     }
   }
   rpc get-ddos-ftpv6-parameters {
     description "Show FTPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftpv6-statistics {
     description "Show FTPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftpv6-violations {
     description "Show FTPv6 traffic violations";
     output {
       container ddos-protocols-information {
         uses ddos-protocols-information-block;
       }
     }
   }
   rpc get-ddos-ftpv6-flow-parameters {
     description "Show FTPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ftpv6-flows {
     description "Show FTPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ftpv6-aggregate {
     description "Show aggregate for all FTPv6 traffic information";
     output {
       container ddos-protocols-information {
         uses ddos-protocols-information-block;
       }
     }
   }
   rpc get-ddos-ftpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sshv6-information {
     description "Show SSHv6 traffic information";
     output {
       container ddos-protocols-information {
         uses ddos-protocols-information-block;
       }
     }
   }
   rpc get-ddos-sshv6-parameters {
     description "Show SSHv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sshv6-statistics {
     description "Show SSHv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sshv6-violations {
     description "Show SSHv6 traffic violations";
     output {
       container ddos-protocols-information {
         uses ddos-protocols-information-block;
       }
     }
   }
   rpc get-ddos-sshv6-flow-parameters {
     description "Show SSHv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sshv6-flows {
     description "Show SSHv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sshv6-aggregate {
     description "Show aggregate for all SSHv6 traffic information";
     output {
       container ddos-protocols-information {
         uses ddos-protocols-information-block;
       }
     }
   }
   rpc get-ddos-sshv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-snmpv6-information {
     description "Show SNMPv6 traffic information";
     output {
       container ddos-protocols-information {
         uses ddos-protocols-information-block;
       }
     }
   }
   rpc get-ddos-snmpv6-parameters {
     description "Show SNMPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmpv6-statistics {
     description "Show SNMPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmpv6-violations {
     description "Show SNMPv6 traffic violations";
     output {
       container ddos-protocols-information {
         uses ddos-protocols-information-block;
       }
     }
   }
   rpc get-ddos-snmpv6-flow-parameters {
     description "Show SNMPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-snmpv6-flows {
     description "Show SNMPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-snmpv6-aggregate {
     description "Show aggregate for all SNMPv6 traffic information";
     output {
       container ddos-protocols-information {
         uses ddos-protocols-information-block;
       }
     }
   }
   rpc get-ddos-snmpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ancpv6-information {
     description "Show ANCPv6 traffic information";
     output {
       container ddos-protocols-information {
         uses ddos-protocols-information-block;
       }
     }
   }
   rpc get-ddos-ancpv6-parameters {
     description "Show ANCPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancpv6-statistics {
     description "Show ANCPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancpv6-violations {
     description "Show ANCPv6 traffic violations";
     output {
       container ddos-protocols-information {
         uses ddos-protocols-information-block;
       }
     }
   }
   rpc get-ddos-ancpv6-flow-parameters {
     description "Show ANCPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ancpv6-flows {
     description "Show ANCPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ancpv6-aggregate {
     description "Show aggregate for all ANCPv6 traffic information";
     output {
       container ddos-protocols-information {
         uses ddos-protocols-information-block;
       }
     }
   }
   rpc get-ddos-ancpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospfv3v6-information {
     description "Show OSPFv3v6 traffic information";
     output {
       container ddos-protocols-information {
         uses ddos-protocols-information-block;
       }
     }
   }
   rpc get-ddos-ospfv3v6-parameters {
     description "Show OSPFv3v6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospfv3v6-statistics {
     description "Show OSPFv3v6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospfv3v6-violations {
     description "Show OSPFv3v6 traffic violations";
     output {
       container ddos-protocols-information {
         uses ddos-protocols-information-block;
       }
     }
   }
   rpc get-ddos-ospfv3v6-flow-parameters {
     description "Show OSPFv3v6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospfv3v6-flows {
     description "Show OSPFv3v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospfv3v6-aggregate {
     description "Show aggregate for all OSPFv3v6 traffic information";
     output {
       container ddos-protocols-information {
         uses ddos-protocols-information-block;
       }
     }
   }
   rpc get-ddos-ospfv3v6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospfv3v6-ospfv3v6-uncls {
     description "Show Unclassified OSPFV3V6 traffic information";
     output {
       container ddos-protocols-information {
         uses ddos-protocols-information-block;
       }
     }
   }
   rpc get-ddos-ospfv3v6-ospfv3v6-uncls-flows {
     description "Show ospfv3v6-uncls culprit flows";
     output {
       container ddos-protocols-information {
         uses ddos-protocols-information-block;
       }
     }
   }
   rpc get-ddos-ospfv3v6-ospfv3v6-hello {
     description "Show OSPFV3V6 hello traffic information";
     output {
       container ddos-protocols-information {
         uses ddos-protocols-information-block;
       }
     }
   }
   rpc get-ddos-ospfv3v6-ospfv3v6-hello-flows {
     description "Show ospfv3v6-hello culprit flows";
     output {
       container ddos-protocols-information {
         uses ddos-protocols-information-block;
       }
     }
   }
   rpc get-ddos-lacp-information {
     description "Show LACP traffic information";
     output {
       container ddos-protocols-information {
         uses ddos-protocols-information-block;
       }
     }
   }
   rpc get-ddos-lacp-parameters {
     description "Show LACP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lacp-statistics {
     description "Show LACP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lacp-violations {
     description "Show LACP traffic violations";
     output {
       container ddos-protocols-information {
         uses ddos-protocols-information-block;
       }
     }
   }
   rpc get-ddos-lacp-flow-parameters {
     description "Show LACP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lacp-flows {
     description "Show LACP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-lacp-aggregate {
     description "Show aggregate for all LACP traffic information";
     output {
       container ddos-protocols-information {
         uses ddos-protocols-information-block;
       }
     }
   }
   rpc get-ddos-lacp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-stp-information {
     description "Show STP traffic information";
     output {
       container ddos-protocols-information {
         uses ddos-protocols-information-block;
       }
     }
   }
   rpc get-ddos-stp-parameters {
     description "Show STP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-stp-statistics {
     description "Show STP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-stp-violations {
     description "Show STP traffic violations";
     output {
       container ddos-protocols-information {
         uses ddos-protocols-information-block;
       }
     }
   }
   rpc get-ddos-stp-flow-parameters {
     description "Show STP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-stp-flows {
     description "Show STP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-stp-aggregate {
     description "Show aggregate for all STP traffic information";
     output {
       container ddos-protocols-information {
         uses ddos-protocols-information-block;
       }
     }
   }
   rpc get-ddos-stp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-esmc-information {
     description "Show ESMC traffic information";
     output {
       container ddos-protocols-information {
         uses ddos-protocols-information-block;
       }
     }
   }
   rpc get-ddos-esmc-parameters {
     description "Show ESMC protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-esmc-statistics {
     description "Show ESMC statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-esmc-violations {
     description "Show ESMC traffic violations";
     output {
       container ddos-protocols-information {
         uses ddos-protocols-information-block;
       }
     }
   }
   rpc get-ddos-esmc-flow-parameters {
     description "Show ESMC flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-esmc-flows {
     description "Show ESMC culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-esmc-aggregate {
     description "Show aggregate for all ESMC traffic information";
     output {
       container ddos-protocols-information {
         uses ddos-protocols-information-block;
       }
     }
   }
   rpc get-ddos-esmc-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-oam-lfm-information {
     description "Show OAM-LFM traffic information";
     output {
       container ddos-protocols-information {
         uses ddos-protocols-information-block;
       }
     }
   }
   rpc get-ddos-oam-lfm-parameters {
     description "Show OAM-LFM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-oam-lfm-statistics {
     description "Show OAM-LFM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-oam-lfm-violations {
     description "Show OAM-LFM traffic violations";
     output {
       container ddos-protocols-information {
         uses ddos-protocols-information-block;
       }
     }
   }
   rpc get-ddos-oam-lfm-flow-parameters {
     description "Show OAM-LFM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-oam-lfm-flows {
     description "Show OAM-LFM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-oam-lfm-aggregate {
     description "Show aggregate for all OAM-LFM traffic information";
     output {
       container ddos-protocols-information {
         uses ddos-protocols-information-block;
       }
     }
   }
   rpc get-ddos-oam-lfm-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-eoam-information {
     description "Show EOAM traffic information";
     output {
       container ddos-protocols-information {
         uses ddos-protocols-information-block;
       }
     }
   }
   rpc get-ddos-eoam-parameters {
     description "Show EOAM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-eoam-statistics {
     description "Show EOAM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-eoam-violations {
     description "Show EOAM traffic violations";
     output {
       container ddos-protocols-information {
         uses ddos-protocols-information-block;
       }
     }
   }
   rpc get-ddos-eoam-flow-parameters {
     description "Show EOAM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-eoam-flows {
     description "Show EOAM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-eoam-aggregate {
     description "Show aggregate for all EOAM traffic information";
     output {
       container ddos-protocols-information {
         uses ddos-protocols-information-block;
       }
     }
   }
   rpc get-ddos-eoam-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-eoam-unclass {
     description "Show unclassified Unclassified EOAM traffic information";
     output {
       container ddos-protocols-information {
         uses ddos-protocols-information-block;
       }
     }
   }
   rpc get-ddos-eoam-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-eoam-oam-cfm {
     description "Show OAM-CFM traffic information";
     output {
       container ddos-protocols-information {
         uses ddos-protocols-information-block;
       }
     }
   }
   rpc get-ddos-eoam-oam-cfm-flows {
     description "Show oam-cfm culprit flows";
     output {
       container ddos-protocols-information {
         uses ddos-protocols-information-block;
       }
     }
   }
   rpc get-ddos-lldp-information {
     description "Show LLDP traffic information";
     output {
       container ddos-protocols-information {
         uses ddos-protocols-information-block;
       }
     }
   }
   rpc get-ddos-lldp-parameters {
     description "Show LLDP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lldp-statistics {
     description "Show LLDP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lldp-violations {
     description "Show LLDP traffic violations";
     output {
       container ddos-protocols-information {
         uses ddos-protocols-information-block;
       }
     }
   }
   rpc get-ddos-lldp-flow-parameters {
     description "Show LLDP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-lldp-flows {
     description "Show LLDP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-lldp-aggregate {
     description "Show aggregate for all LLDP traffic information";
     output {
       container ddos-protocols-information {
         uses ddos-protocols-information-block;
       }
     }
   }
   rpc get-ddos-lldp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mvrp-information {
     description "Show MVRP traffic information";
     output {
       container ddos-protocols-information {
         uses ddos-protocols-information-block;
       }
     }
   }
   rpc get-ddos-mvrp-parameters {
     description "Show MVRP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mvrp-statistics {
     description "Show MVRP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mvrp-violations {
     description "Show MVRP traffic violations";
     output {
       container ddos-protocols-information {
         uses ddos-protocols-information-block;
       }
     }
   }
   rpc get-ddos-mvrp-flow-parameters {
     description "Show MVRP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mvrp-flows {
     description "Show MVRP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mvrp-aggregate {
     description "Show aggregate for all MVRP traffic information";
     output {
       container ddos-protocols-information {
         uses ddos-protocols-information-block;
       }
     }
   }
   rpc get-ddos-mvrp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pmvrp-information {
     description "Show PMVRP traffic information";
     output {
       container ddos-protocols-information {
         uses ddos-protocols-information-block;
       }
     }
   }
   rpc get-ddos-pmvrp-parameters {
     description "Show PMVRP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pmvrp-statistics {
     description "Show PMVRP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pmvrp-violations {
     description "Show PMVRP traffic violations";
     output {
       container ddos-protocols-information {
         uses ddos-protocols-information-block;
       }
     }
   }
   rpc get-ddos-pmvrp-flow-parameters {
     description "Show PMVRP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pmvrp-flows {
     description "Show PMVRP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pmvrp-aggregate {
     description "Show aggregate for all PMVRP traffic information";
     output {
       container ddos-protocols-information {
         uses ddos-protocols-information-block;
       }
     }
   }
   rpc get-ddos-pmvrp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-arp-information {
     description "Show ARP traffic information";
     output {
       container ddos-protocols-information {
         uses ddos-protocols-information-block;
       }
     }
   }
   rpc get-ddos-arp-parameters {
     description "Show ARP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-arp-statistics {
     description "Show ARP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-arp-violations {
     description "Show ARP traffic violations";
     output {
       container ddos-protocols-information {
         uses ddos-protocols-information-block;
       }
     }
   }
   rpc get-ddos-arp-flow-parameters {
     description "Show ARP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-arp-flows {
     description "Show ARP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-arp-aggregate {
     description "Show aggregate for all ARP traffic information";
     output {
       container ddos-protocols-information {
         uses ddos-protocols-information-block;
       }
     }
   }
   rpc get-ddos-arp-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-arp-unclass {
     description "Show unclassified ARP traffic information";
     output {
       container ddos-protocols-information {
         uses ddos-protocols-information-block;
       }
     }
   }
   rpc get-ddos-arp-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-arp-arp {
     description "Show ARP traffic information";
     output {
       container ddos-protocols-information {
         uses ddos-protocols-information-block;
       }
     }
   }
   rpc get-ddos-arp-arp-flows {
     description "Show arp culprit flows";
     output {
       container ddos-protocols-information {
         uses ddos-protocols-information-block;
       }
     }
   }
   rpc get-ddos-arp-ucast {
     description "Show ARP unicast traffic information";
     output {
       container ddos-protocols-information {
         uses ddos-protocols-information-block;
       }
     }
   }
   rpc get-ddos-arp-ucast-flows {
     description "Show ucast culprit flows";
     output {
       container ddos-protocols-information {
         uses ddos-protocols-information-block;
       }
     }
   }
   rpc get-ddos-arp-bcast {
     description "Show ARP broadcast traffic information";
     output {
       container ddos-protocols-information {
         uses ddos-protocols-information-block;
       }
     }
   }
   rpc get-ddos-arp-bcast-flows {
     description "Show bcast culprit flows";
     output {
       container ddos-protocols-information {
         uses ddos-protocols-information-block;
       }
     }
   }
   rpc get-ddos-pvstp-information {
     description "Show PVSTP traffic information";
     output {
       container ddos-protocols-information {
         uses ddos-protocols-information-block;
       }
     }
   }
   rpc get-ddos-pvstp-parameters {
     description "Show PVSTP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pvstp-statistics {
     description "Show PVSTP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pvstp-violations {
     description "Show PVSTP traffic violations";
     output {
       container ddos-protocols-information {
         uses ddos-protocols-information-block;
       }
     }
   }
   rpc get-ddos-pvstp-flow-parameters {
     description "Show PVSTP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pvstp-flows {
     description "Show PVSTP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pvstp-aggregate {
     description "Show aggregate for all PVSTP traffic information";
     output {
       container ddos-protocols-information {
         uses ddos-protocols-information-block;
       }
     }
   }
   rpc get-ddos-pvstp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-isis-information {
     description "Show ISIS Data traffic information";
     output {
       container ddos-protocols-information {
         uses ddos-protocols-information-block;
       }
     }
   }
   rpc get-ddos-isis-parameters {
     description "Show ISIS protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-isis-statistics {
     description "Show ISIS statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-isis-violations {
     description "Show ISIS traffic violations";
     output {
       container ddos-protocols-information {
         uses ddos-protocols-information-block;
       }
     }
   }
   rpc get-ddos-isis-flow-parameters {
     description "Show ISIS flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-isis-flows {
     description "Show ISIS culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-isis-aggregate {
     description "Show aggregate for all ISIS Data traffic information";
     output {
       container ddos-protocols-information {
         uses ddos-protocols-information-block;
       }
     }
   }
   rpc get-ddos-isis-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-isis-unclass {
     description "Show unclassified ISIS traffic information";
     output {
       container ddos-protocols-information {
         uses ddos-protocols-information-block;
       }
     }
   }
   rpc get-ddos-isis-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-isis-isis-hello {
     description "Show ISIS Hello traffic information";
     output {
       container ddos-protocols-information {
         uses ddos-protocols-information-block;
       }
     }
   }
   rpc get-ddos-isis-isis-hello-flows {
     description "Show isis-hello culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-isis-isis-data {
     description "Show ISIS Data traffic information";
     output {
       container ddos-protocols-information {
         uses ddos-protocols-information-block;
       }
     }
   }
   rpc get-ddos-isis-isis-data-flows {
     description "Show isis-data culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pos-information {
     description "Show POS traffic information";
     output {
       container ddos-protocols-information {
         uses ddos-protocols-information-block;
       }
     }
   }
   rpc get-ddos-pos-parameters {
     description "Show POS protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pos-statistics {
     description "Show POS statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pos-violations {
     description "Show POS traffic violations";
     output {
       container ddos-protocols-information {
         uses ddos-protocols-information-block;
       }
     }
   }
   rpc get-ddos-pos-flow-parameters {
     description "Show POS flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pos-flows {
     description "Show POS culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pos-aggregate {
     description "Show aggregate for all POS traffic information";
     output {
       container ddos-protocols-information {
         uses ddos-protocols-information-block;
       }
     }
   }
   rpc get-ddos-pos-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-information {
     description "Show MLP traffic information";
     output {
       container ddos-protocols-information {
         uses ddos-protocols-information-block;
       }
     }
   }
   rpc get-ddos-mlp-parameters {
     description "Show MLP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mlp-statistics {
     description "Show MLP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mlp-violations {
     description "Show MLP traffic violations";
     output {
       container ddos-protocols-information {
         uses ddos-protocols-information-block;
       }
     }
   }
   rpc get-ddos-mlp-flow-parameters {
     description "Show MLP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mlp-flows {
     description "Show MLP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-aggregate {
     description "Show aggregate for all MLP traffic information";
     output {
       container ddos-protocols-information {
         uses ddos-protocols-information-block;
       }
     }
   }
   rpc get-ddos-mlp-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-unclass {
     description "Show unclassified MLP traffic information";
     output {
       container ddos-protocols-information {
         uses ddos-protocols-information-block;
       }
     }
   }
   rpc get-ddos-mlp-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-lookup {
     description "Show MLP lookup request information";
     output {
       container ddos-protocols-information {
         uses ddos-protocols-information-block;
       }
     }
   }
   rpc get-ddos-mlp-lookup-flows {
     description "Show lookup culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-add {
     description "Show MLP add request information";
     output {
       container ddos-protocols-information {
         uses ddos-protocols-information-block;
       }
     }
   }
   rpc get-ddos-mlp-add-flows {
     description "Show add culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-delete {
     description "Show MLP delete request information";
     output {
       container ddos-protocols-information {
         uses ddos-protocols-information-block;
       }
     }
   }
   rpc get-ddos-mlp-delete-flows {
     description "Show delete culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mlp-mac-pinning {
     description "Show MAC-pinning exceptions information";
     output {
       container ddos-protocols-information {
         uses ddos-protocols-information-block;
       }
     }
   }
   rpc get-ddos-mlp-mac-pinning-flows {
     description "Show macpin-exception culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-jfm-information {
     description "Show JFM traffic information";
     output {
       container ddos-protocols-information {
         uses ddos-protocols-information-block;
       }
     }
   }
   rpc get-ddos-jfm-parameters {
     description "Show JFM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-jfm-statistics {
     description "Show JFM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-jfm-violations {
     description "Show JFM traffic violations";
     output {
       container ddos-protocols-information {
         uses ddos-protocols-information-block;
       }
     }
   }
   rpc get-ddos-jfm-flow-parameters {
     description "Show JFM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-jfm-flows {
     description "Show JFM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-jfm-aggregate {
     description "Show aggregate for all JFM traffic information";
     output {
       container ddos-protocols-information {
         uses ddos-protocols-information-block;
       }
     }
   }
   rpc get-ddos-jfm-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-atm-information {
     description "Show ATM traffic information";
     output {
       container ddos-protocols-information {
         uses ddos-protocols-information-block;
       }
     }
   }
   rpc get-ddos-atm-parameters {
     description "Show ATM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-atm-statistics {
     description "Show ATM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-atm-violations {
     description "Show ATM traffic violations";
     output {
       container ddos-protocols-information {
         uses ddos-protocols-information-block;
       }
     }
   }
   rpc get-ddos-atm-flow-parameters {
     description "Show ATM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-atm-flows {
     description "Show ATM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-atm-aggregate {
     description "Show aggregate for all ATM traffic information";
     output {
       container ddos-protocols-information {
         uses ddos-protocols-information-block;
       }
     }
   }
   rpc get-ddos-atm-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pfe-alive-information {
     description "Show pfe alive traffic information";
     output {
       container ddos-protocols-information {
         uses ddos-protocols-information-block;
       }
     }
   }
   rpc get-ddos-pfe-alive-parameters {
     description "Show Pfe-Alive protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfe-alive-statistics {
     description "Show Pfe-Alive statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfe-alive-violations {
     description "Show Pfe-Alive traffic violations";
     output {
       container ddos-protocols-information {
         uses ddos-protocols-information-block;
       }
     }
   }
   rpc get-ddos-pfe-alive-flow-parameters {
     description "Show Pfe-Alive flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfe-alive-flows {
     description "Show Pfe-Alive culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pfe-alive-aggregate {
     description "Show aggregate for all pfe alive traffic information";
     output {
       container ddos-protocols-information {
         uses ddos-protocols-information-block;
       }
     }
   }
   rpc get-ddos-pfe-alive-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ttl-information {
     description "Show ttl traffic information";
     output {
       container ddos-protocols-information {
         uses ddos-protocols-information-block;
       }
     }
   }
   rpc get-ddos-ttl-parameters {
     description "Show TTL protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ttl-statistics {
     description "Show TTL statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ttl-violations {
     description "Show TTL traffic violations";
     output {
       container ddos-protocols-information {
         uses ddos-protocols-information-block;
       }
     }
   }
   rpc get-ddos-ttl-flow-parameters {
     description "Show TTL flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ttl-flows {
     description "Show TTL culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ttl-aggregate {
     description "Show aggregate for all ttl traffic information";
     output {
       container ddos-protocols-information {
         uses ddos-protocols-information-block;
       }
     }
   }
   rpc get-ddos-ttl-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-opt-information {
     description "Show ip options traffic information";
     output {
       container ddos-protocols-information {
         uses ddos-protocols-information-block;
       }
     }
   }
   rpc get-ddos-ip-opt-parameters {
     description "Show IP-Options protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-opt-statistics {
     description "Show IP-Options statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-opt-violations {
     description "Show IP-Options traffic violations";
     output {
       container ddos-protocols-information {
         uses ddos-protocols-information-block;
       }
     }
   }
   rpc get-ddos-ip-opt-flow-parameters {
     description "Show IP-Options flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-opt-flows {
     description "Show IP-Options culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-opt-aggregate {
     description "Show aggregate for all ip options traffic information";
     output {
       container ddos-protocols-information {
         uses ddos-protocols-information-block;
       }
     }
   }
   rpc get-ddos-ip-opt-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-opt-unclass {
     description "Show Unclassified options traffic information";
     output {
       container ddos-protocols-information {
         uses ddos-protocols-information-block;
       }
     }
   }
   rpc get-ddos-ip-opt-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-opt-rt-alert {
     description "Show Router alert options traffic information";
     output {
       container ddos-protocols-information {
         uses ddos-protocols-information-block;
       }
     }
   }
   rpc get-ddos-ip-opt-rt-alert-flows {
     description "Show router-alert culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-opt-non-v4v6 {
     description "Show Non IPv4/v6 options traffic information";
     output {
       container ddos-protocols-information {
         uses ddos-protocols-information-block;
       }
     }
   }
   rpc get-ddos-ip-opt-non-v4v6-flows {
     description "Show non-v4v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-redirect-information {
     description "Show packets to trigger ICMP redirect information";
     output {
       container ddos-protocols-information {
         uses ddos-protocols-information-block;
       }
     }
   }
   rpc get-ddos-redirect-parameters {
     description "Show Redirect protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-redirect-statistics {
     description "Show Redirect statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-redirect-violations {
     description "Show Redirect traffic violations";
     output {
       container ddos-protocols-information {
         uses ddos-protocols-information-block;
       }
     }
   }
   rpc get-ddos-redirect-flow-parameters {
     description "Show Redirect flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-redirect-flows {
     description "Show Redirect culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-redirect-aggregate {
     description "Show aggregate for all packets to trigger ICMP redirect information";
     output {
       container ddos-protocols-information {
         uses ddos-protocols-information-block;
       }
     }
   }
   rpc get-ddos-redirect-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-copy-information {
     description "Show host copy due to multicast routing information";
     status deprecated;
     output {
       container ddos-protocols-information {
         uses ddos-protocols-information-block;
       }
     }
   }
   rpc get-ddos-mcast-copy-parameters {
     description "Show Multicast-Copy protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-copy-statistics {
     description "Show Multicast-Copy statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-copy-violations {
     description "Show Multicast-Copy traffic violations";
     output {
       container ddos-protocols-information {
         uses ddos-protocols-information-block;
       }
     }
   }
   rpc get-ddos-mcast-copy-flow-parameters {
     description "Show Multicast-Copy flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-copy-flows {
     description "Show Multicast-Copy culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-copy-aggregate {
     description "Show aggregate for all host copy due to multicast routing information";
     output {
       container ddos-protocols-information {
         uses ddos-protocols-information-block;
       }
     }
   }
   rpc get-ddos-mcast-copy-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-exception-information {
     description "Show exception traffic sent to host information";
     output {
       container ddos-protocols-information {
         uses ddos-protocols-information-block;
       }
     }
   }
   rpc get-ddos-exception-parameters {
     description "Show Exceptions protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-exception-statistics {
     description "Show Exceptions statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-exception-violations {
     description "Show Exceptions traffic violations";
     output {
       container ddos-protocols-information {
         uses ddos-protocols-information-block;
       }
     }
   }
   rpc get-ddos-exception-flow-parameters {
     description "Show Exceptions flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-exception-flows {
     description "Show Exceptions culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-exception-aggregate {
     description "Show aggregate for all exception traffic sent to host information";
     output {
       container ddos-protocols-information {
         uses ddos-protocols-information-block;
       }
     }
   }
   rpc get-ddos-exception-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-exception-unclass {
     description "Show all unclassified discards information";
     output {
       container ddos-protocols-information {
         uses ddos-protocols-information-block;
       }
     }
   }
   rpc get-ddos-exception-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-exception-mtu-exceed {
     description "Show packets exceeded MTU information";
     output {
       container ddos-protocols-information {
         uses ddos-protocols-information-block;
       }
     }
   }
   rpc get-ddos-exception-mtu-exceed-flows {
     description "Show mtu-exceeded culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-exception-mcast-rpf {
     description "Show packets failed the multicast RPF check information";
     output {
       container ddos-protocols-information {
         uses ddos-protocols-information-block;
       }
     }
   }
   rpc get-ddos-exception-mcast-rpf-flows {
     description "Show mcast-rpf-err culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mac-host-information {
     description "Show L2-MAC configured 'send-to-host' information";
     output {
       container ddos-protocols-information {
         uses ddos-protocols-information-block;
       }
     }
   }
   rpc get-ddos-mac-host-parameters {
     description "Show Mac-Host protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mac-host-statistics {
     description "Show Mac-Host statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mac-host-violations {
     description "Show Mac-Host traffic violations";
     output {
       container ddos-protocols-information {
         uses ddos-protocols-information-block;
       }
     }
   }
   rpc get-ddos-mac-host-flow-parameters {
     description "Show Mac-Host flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mac-host-flows {
     description "Show Mac-Host culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mac-host-aggregate {
     description "Show aggregate for all L2-MAC configured 'send-to-host' information";
     output {
       container ddos-protocols-information {
         uses ddos-protocols-information-block;
       }
     }
   }
   rpc get-ddos-mac-host-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tun-frag-information {
     description "Show tunnel fragment information";
     output {
       container ddos-protocols-information {
         uses ddos-protocols-information-block;
       }
     }
   }
   rpc get-ddos-tun-frag-parameters {
     description "Show Tunnel-Fragment protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tun-frag-statistics {
     description "Show Tunnel-Fragment statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tun-frag-violations {
     description "Show Tunnel-Fragment traffic violations";
     output {
       container ddos-protocols-information {
         uses ddos-protocols-information-block;
       }
     }
   }
   rpc get-ddos-tun-frag-flow-parameters {
     description "Show Tunnel-Fragment flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tun-frag-flows {
     description "Show Tunnel-Fragment culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tun-frag-aggregate {
     description "Show aggregate for all tunnel fragment information";
     output {
       container ddos-protocols-information {
         uses ddos-protocols-information-block;
       }
     }
   }
   rpc get-ddos-tun-frag-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-snoop-information {
     description "Show snooped multicast control traffic information";
     output {
       container ddos-protocols-information {
         uses ddos-protocols-information-block;
       }
     }
   }
   rpc get-ddos-mcast-snoop-parameters {
     description "Show MCAST-Snoop protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-snoop-statistics {
     description "Show MCAST-Snoop statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-snoop-violations {
     description "Show MCAST-Snoop traffic violations";
     output {
       container ddos-protocols-information {
         uses ddos-protocols-information-block;
       }
     }
   }
   rpc get-ddos-mcast-snoop-flow-parameters {
     description "Show MCAST-Snoop flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-mcast-snoop-flows {
     description "Show MCAST-Snoop culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-snoop-aggregate {
     description "Show aggregate for all snooped multicast control traffic information";
     output {
       container ddos-protocols-information {
         uses ddos-protocols-information-block;
       }
     }
   }
   rpc get-ddos-mcast-snoop-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-snoop-igmp {
     description "Show snooped igmp traffic information";
     output {
       container ddos-protocols-information {
         uses ddos-protocols-information-block;
       }
     }
   }
   rpc get-ddos-mcast-snoop-igmp-flows {
     description "Show igmp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-snoop-pim {
     description "Show snooped pim traffic information";
     output {
       container ddos-protocols-information {
         uses ddos-protocols-information-block;
       }
     }
   }
   rpc get-ddos-mcast-snoop-pim-flows {
     description "Show pim culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-mcast-snoop-mld {
     description "Show snooped mld traffic information";
     output {
       container ddos-protocols-information {
         uses ddos-protocols-information-block;
       }
     }
   }
   rpc get-ddos-mcast-snoop-mld-flows {
     description "Show mld culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-services-information {
     description "Show services information";
     output {
       container ddos-protocols-information {
         uses ddos-protocols-information-block;
       }
     }
   }
   rpc get-ddos-services-parameters {
     description "Show Services protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-services-statistics {
     description "Show Services statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-services-violations {
     description "Show Services traffic violations";
     output {
       container ddos-protocols-information {
         uses ddos-protocols-information-block;
       }
     }
   }
   rpc get-ddos-services-flow-parameters {
     description "Show Services flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-services-flows {
     description "Show Services culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-services-aggregate {
     description "Show aggregate for all services information";
     output {
       container ddos-protocols-information {
         uses ddos-protocols-information-block;
       }
     }
   }
   rpc get-ddos-services-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-services-packet {
     description "Show Service packets information";
     output {
       container ddos-protocols-information {
         uses ddos-protocols-information-block;
       }
     }
   }
   rpc get-ddos-services-packet-flows {
     description "Show packet culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-services-bsdt {
     description "Show Test packets information";
     output {
       container ddos-protocols-information {
         uses ddos-protocols-information-block;
       }
     }
   }
   rpc get-ddos-services-bsdt-flows {
     description "Show bsdt culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-demuxauto-information {
     description "Show demux autosense traffic information";
     output {
       container ddos-protocols-information {
         uses ddos-protocols-information-block;
       }
     }
   }
   rpc get-ddos-demuxauto-parameters {
     description "Show Demux-Autosense protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-demuxauto-statistics {
     description "Show Demux-Autosense statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-demuxauto-violations {
     description "Show Demux-Autosense traffic violations";
     output {
       container ddos-protocols-information {
         uses ddos-protocols-information-block;
       }
     }
   }
   rpc get-ddos-demuxauto-flow-parameters {
     description "Show Demux-Autosense flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-demuxauto-flows {
     description "Show Demux-Autosense culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-demuxauto-aggregate {
     description "Show aggregate for all demux autosense traffic information";
     output {
       container ddos-protocols-information {
         uses ddos-protocols-information-block;
       }
     }
   }
   rpc get-ddos-demuxauto-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-reject-information {
     description "Show packets via 'reject' action information";
     output {
       container ddos-protocols-information {
         uses ddos-protocols-information-block;
       }
     }
   }
   rpc get-ddos-reject-parameters {
     description "Show Reject protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-reject-statistics {
     description "Show Reject statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-reject-violations {
     description "Show Reject traffic violations";
     output {
       container ddos-protocols-information {
         uses ddos-protocols-information-block;
       }
     }
   }
   rpc get-ddos-reject-flow-parameters {
     description "Show Reject flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-reject-flows {
     description "Show Reject culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-reject-aggregate {
     description "Show aggregate for all packets via 'reject' action information";
     output {
       container ddos-protocols-information {
         uses ddos-protocols-information-block;
       }
     }
   }
   rpc get-ddos-reject-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fw-host-information {
     description "Show packets via firewall 'send-to-host' action information";
     output {
       container ddos-protocols-information {
         uses ddos-protocols-information-block;
       }
     }
   }
   rpc get-ddos-fw-host-parameters {
     description "Show Firewall-Host protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fw-host-statistics {
     description "Show Firewall-Host statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fw-host-violations {
     description "Show Firewall-Host traffic violations";
     output {
       container ddos-protocols-information {
         uses ddos-protocols-information-block;
       }
     }
   }
   rpc get-ddos-fw-host-flow-parameters {
     description "Show Firewall-Host flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fw-host-flows {
     description "Show Firewall-Host culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fw-host-aggregate {
     description "Show aggregate for all packets via firewall 'send-to-host' action information";
     output {
       container ddos-protocols-information {
         uses ddos-protocols-information-block;
       }
     }
   }
   rpc get-ddos-fw-host-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sctp-information {
     description "Show sctp packets information";
     output {
       container ddos-protocols-information {
         uses ddos-protocols-information-block;
       }
     }
   }
   rpc get-ddos-sctp-parameters {
     description "Show SCTP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sctp-statistics {
     description "Show SCTP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sctp-violations {
     description "Show SCTP traffic violations";
     output {
       container ddos-protocols-information {
         uses ddos-protocols-information-block;
       }
     }
   }
   rpc get-ddos-sctp-flow-parameters {
     description "Show SCTP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sctp-flows {
     description "Show SCTP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sctp-aggregate {
     description "Show aggregate for all sctp packets information";
     output {
       container ddos-protocols-information {
         uses ddos-protocols-information-block;
       }
     }
   }
   rpc get-ddos-sctp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcp-flags-information {
     description "Show packets with tcp flags information";
     output {
       container ddos-protocols-information {
         uses ddos-protocols-information-block;
       }
     }
   }
   rpc get-ddos-tcp-flags-parameters {
     description "Show TCP-Flags protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcp-flags-statistics {
     description "Show TCP-Flags statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcp-flags-violations {
     description "Show TCP-Flags traffic violations";
     output {
       container ddos-protocols-information {
         uses ddos-protocols-information-block;
       }
     }
   }
   rpc get-ddos-tcp-flags-flow-parameters {
     description "Show TCP-Flags flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcp-flags-flows {
     description "Show TCP-Flags culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcp-flags-aggregate {
     description "Show aggregate for all packets with tcp flags information";
     output {
       container ddos-protocols-information {
         uses ddos-protocols-information-block;
       }
     }
   }
   rpc get-ddos-tcp-flags-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcp-flags-unclass {
     description "Show TCP packets with other tcp flags information";
     output {
       container ddos-protocols-information {
         uses ddos-protocols-information-block;
       }
     }
   }
   rpc get-ddos-tcp-flags-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcp-flags-initial {
     description "Show First packets of TCP sessions (SYN & !ACK) information";
     output {
       container ddos-protocols-information {
         uses ddos-protocols-information-block;
       }
     }
   }
   rpc get-ddos-tcp-flags-initial-flows {
     description "Show initial culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcp-flags-establish {
     description "Show Non-first packets of TCP sessions (ACK | RST) information";
     output {
       container ddos-protocols-information {
         uses ddos-protocols-information-block;
       }
     }
   }
   rpc get-ddos-tcp-flags-establish-flows {
     description "Show established culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dtcp-information {
     description "Show dtcp traffic information";
     output {
       container ddos-protocols-information {
         uses ddos-protocols-information-block;
       }
     }
   }
   rpc get-ddos-dtcp-parameters {
     description "Show dtcp protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dtcp-statistics {
     description "Show dtcp statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dtcp-violations {
     description "Show dtcp traffic violations";
     output {
       container ddos-protocols-information {
         uses ddos-protocols-information-block;
       }
     }
   }
   rpc get-ddos-dtcp-flow-parameters {
     description "Show dtcp flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dtcp-flows {
     description "Show dtcp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dtcp-aggregate {
     description "Show aggregate for all dtcp traffic information";
     output {
       container ddos-protocols-information {
         uses ddos-protocols-information-block;
       }
     }
   }
   rpc get-ddos-dtcp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-radius-information {
     description "Show Radius traffic information";
     output {
       container ddos-protocols-information {
         uses ddos-protocols-information-block;
       }
     }
   }
   rpc get-ddos-radius-parameters {
     description "Show Radius protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-radius-statistics {
     description "Show Radius statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-radius-violations {
     description "Show Radius traffic violations";
     output {
       container ddos-protocols-information {
         uses ddos-protocols-information-block;
       }
     }
   }
   rpc get-ddos-radius-flow-parameters {
     description "Show Radius flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-radius-flows {
     description "Show Radius culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-radius-aggregate {
     description "Show aggregate for all Radius traffic information";
     output {
       container ddos-protocols-information {
         uses ddos-protocols-information-block;
       }
     }
   }
   rpc get-ddos-radius-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-radius-server {
     description "Show Radius server traffic information";
     output {
       container ddos-protocols-information {
         uses ddos-protocols-information-block;
       }
     }
   }
   rpc get-ddos-radius-server-flows {
     description "Show server culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-radius-account {
     description "Show Radius accounting traffic information";
     output {
       container ddos-protocols-information {
         uses ddos-protocols-information-block;
       }
     }
   }
   rpc get-ddos-radius-account-flows {
     description "Show accounting culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-radius-auth {
     description "Show Radius authorization traffic information";
     output {
       container ddos-protocols-information {
         uses ddos-protocols-information-block;
       }
     }
   }
   rpc get-ddos-radius-auth-flows {
     description "Show authorization culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ntp-information {
     description "Show NTP traffic information";
     output {
       container ddos-protocols-information {
         uses ddos-protocols-information-block;
       }
     }
   }
   rpc get-ddos-ntp-parameters {
     description "Show NTP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ntp-statistics {
     description "Show NTP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ntp-violations {
     description "Show NTP traffic violations";
     output {
       container ddos-protocols-information {
         uses ddos-protocols-information-block;
       }
     }
   }
   rpc get-ddos-ntp-flow-parameters {
     description "Show NTP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ntp-flows {
     description "Show NTP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ntp-aggregate {
     description "Show aggregate for all NTP traffic information";
     output {
       container ddos-protocols-information {
         uses ddos-protocols-information-block;
       }
     }
   }
   rpc get-ddos-ntp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tacacs-information {
     description "Show TACACS traffic information";
     output {
       container ddos-protocols-information {
         uses ddos-protocols-information-block;
       }
     }
   }
   rpc get-ddos-tacacs-parameters {
     description "Show TACACS protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tacacs-statistics {
     description "Show TACACS statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tacacs-violations {
     description "Show TACACS traffic violations";
     output {
       container ddos-protocols-information {
         uses ddos-protocols-information-block;
       }
     }
   }
   rpc get-ddos-tacacs-flow-parameters {
     description "Show TACACS flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tacacs-flows {
     description "Show TACACS culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tacacs-aggregate {
     description "Show aggregate for all TACACS traffic information";
     output {
       container ddos-protocols-information {
         uses ddos-protocols-information-block;
       }
     }
   }
   rpc get-ddos-tacacs-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dns-information {
     description "Show DNS traffic information";
     output {
       container ddos-protocols-information {
         uses ddos-protocols-information-block;
       }
     }
   }
   rpc get-ddos-dns-parameters {
     description "Show DNS protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dns-statistics {
     description "Show DNS statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dns-violations {
     description "Show DNS traffic violations";
     output {
       container ddos-protocols-information {
         uses ddos-protocols-information-block;
       }
     }
   }
   rpc get-ddos-dns-flow-parameters {
     description "Show DNS flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dns-flows {
     description "Show DNS culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dns-aggregate {
     description "Show aggregate for all DNS traffic information";
     output {
       container ddos-protocols-information {
         uses ddos-protocols-information-block;
       }
     }
   }
   rpc get-ddos-dns-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-diameter-information {
     description "Show Diameter/Gx+ traffic information";
     output {
       container ddos-protocols-information {
         uses ddos-protocols-information-block;
       }
     }
   }
   rpc get-ddos-diameter-parameters {
     description "Show Diameter protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-diameter-statistics {
     description "Show Diameter statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-diameter-violations {
     description "Show Diameter traffic violations";
     output {
       container ddos-protocols-information {
         uses ddos-protocols-information-block;
       }
     }
   }
   rpc get-ddos-diameter-flow-parameters {
     description "Show Diameter flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-diameter-flows {
     description "Show Diameter culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-diameter-aggregate {
     description "Show aggregate for all Diameter/Gx+ traffic information";
     output {
       container ddos-protocols-information {
         uses ddos-protocols-information-block;
       }
     }
   }
   rpc get-ddos-diameter-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-frag-information {
     description "Show IP-Fragments information";
     output {
       container ddos-protocols-information {
         uses ddos-protocols-information-block;
       }
     }
   }
   rpc get-ddos-ip-frag-parameters {
     description "Show IP-Fragments protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-frag-statistics {
     description "Show IP-Fragments statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-frag-violations {
     description "Show IP-Fragments traffic violations";
     output {
       container ddos-protocols-information {
         uses ddos-protocols-information-block;
       }
     }
   }
   rpc get-ddos-ip-frag-flow-parameters {
     description "Show IP-Fragments flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ip-frag-flows {
     description "Show IP-Fragments culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-frag-aggregate {
     description "Show aggregate for all IP-Fragments information";
     output {
       container ddos-protocols-information {
         uses ddos-protocols-information-block;
       }
     }
   }
   rpc get-ddos-ip-frag-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-frag-first-frag {
     description "Show First IP fragment information";
     output {
       container ddos-protocols-information {
         uses ddos-protocols-information-block;
       }
     }
   }
   rpc get-ddos-ip-frag-first-frag-flows {
     description "Show first-fragment culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ip-frag-trail-frag {
     description "Show Trailing IP fragment information";
     output {
       container ddos-protocols-information {
         uses ddos-protocols-information-block;
       }
     }
   }
   rpc get-ddos-ip-frag-trail-frag-flows {
     description "Show trail-fragment culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l2tp-information {
     description "Show l2tp traffic information";
     output {
       container ddos-protocols-information {
         uses ddos-protocols-information-block;
       }
     }
   }
   rpc get-ddos-l2tp-parameters {
     description "Show L2TP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2tp-statistics {
     description "Show L2TP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2tp-violations {
     description "Show L2TP traffic violations";
     output {
       container ddos-protocols-information {
         uses ddos-protocols-information-block;
       }
     }
   }
   rpc get-ddos-l2tp-flow-parameters {
     description "Show L2TP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2tp-flows {
     description "Show L2TP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l2tp-aggregate {
     description "Show aggregate for all l2tp traffic information";
     output {
       container ddos-protocols-information {
         uses ddos-protocols-information-block;
       }
     }
   }
   rpc get-ddos-l2tp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gre-information {
     description "Show GRE traffic information";
     output {
       container ddos-protocols-information {
         uses ddos-protocols-information-block;
       }
     }
   }
   rpc get-ddos-gre-parameters {
     description "Show GRE protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gre-statistics {
     description "Show GRE statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gre-violations {
     description "Show GRE traffic violations";
     output {
       container ddos-protocols-information {
         uses ddos-protocols-information-block;
       }
     }
   }
   rpc get-ddos-gre-flow-parameters {
     description "Show GRE flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gre-flows {
     description "Show GRE culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gre-aggregate {
     description "Show aggregate for all GRE traffic information";
     output {
       container ddos-protocols-information {
         uses ddos-protocols-information-block;
       }
     }
   }
   rpc get-ddos-gre-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gre-hbc {
     description "Show Host GRE traffic information";
     output {
       container ddos-protocols-information {
         uses ddos-protocols-information-block;
       }
     }
   }
   rpc get-ddos-gre-hbc-flows {
     description "Show hbc culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gre-punt {
     description "Show PFE GRE traffic information";
     output {
       container ddos-protocols-information {
         uses ddos-protocols-information-block;
       }
     }
   }
   rpc get-ddos-gre-punt-flows {
     description "Show punt culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gre-hag {
     description "Show PFE GRE HAG Hello traffic information";
     output {
       container ddos-protocols-information {
         uses ddos-protocols-information-block;
       }
     }
   }
   rpc get-ddos-gre-hag-flows {
     description "Show hag culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-information {
     description "Show IPSEC traffic information";
     output {
       container ddos-protocols-information {
         uses ddos-protocols-information-block;
       }
     }
   }
   rpc get-ddos-ipsec-parameters {
     description "Show ipsec protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipsec-statistics {
     description "Show ipsec statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipsec-violations {
     description "Show ipsec traffic violations";
     output {
       container ddos-protocols-information {
         uses ddos-protocols-information-block;
       }
     }
   }
   rpc get-ddos-ipsec-flow-parameters {
     description "Show ipsec flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipsec-flows {
     description "Show ipsec culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-aggregate {
     description "Show aggregate for all IPSEC traffic information";
     output {
       container ddos-protocols-information {
         uses ddos-protocols-information-block;
       }
     }
   }
   rpc get-ddos-ipsec-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-unclass {
     description "Show unclassified IPSEC traffic information";
     output {
       container ddos-protocols-information {
         uses ddos-protocols-information-block;
       }
     }
   }
   rpc get-ddos-ipsec-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-ike {
     description "Show IPSEC IKE via datapath information";
     output {
       container ddos-protocols-information {
         uses ddos-protocols-information-block;
       }
     }
   }
   rpc get-ddos-ipsec-ike-flows {
     description "Show ike culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-spi-inval {
     description "Show IPSEC SPI invalid packets information";
     output {
       container ddos-protocols-information {
         uses ddos-protocols-information-block;
       }
     }
   }
   rpc get-ddos-ipsec-spi-inval-flows {
     description "Show spi-inval culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-sn-alarm {
     description "Show IPSEC SN threshold alarms information";
     output {
       container ddos-protocols-information {
         uses ddos-protocols-information-block;
       }
     }
   }
   rpc get-ddos-ipsec-sn-alarm-flows {
     description "Show sn-alarm culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-mtu-error {
     description "Show IPSEC MTU exceeded packets information";
     output {
       container ddos-protocols-information {
         uses ddos-protocols-information-block;
       }
     }
   }
   rpc get-ddos-ipsec-mtu-error-flows {
     description "Show mtu-error culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-tx-alarm {
     description "Show IPSEC Tunnel TX disable alarms information";
     output {
       container ddos-protocols-information {
         uses ddos-protocols-information-block;
       }
     }
   }
   rpc get-ddos-ipsec-tx-alarm-flows {
     description "Show tx-alarm culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipsec-on-trigger {
     description "Show IPSEC Tunnel creation trigger information";
     output {
       container ddos-protocols-information {
         uses ddos-protocols-information-block;
       }
     }
   }
   rpc get-ddos-ipsec-on-trigger-flows {
     description "Show on-trigger culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pimv6-information {
     description "Show PIMv6 traffic information";
     output {
       container ddos-protocols-information {
         uses ddos-protocols-information-block;
       }
     }
   }
   rpc get-ddos-pimv6-parameters {
     description "Show PIMv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pimv6-statistics {
     description "Show PIMv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pimv6-violations {
     description "Show PIMv6 traffic violations";
     output {
       container ddos-protocols-information {
         uses ddos-protocols-information-block;
       }
     }
   }
   rpc get-ddos-pimv6-flow-parameters {
     description "Show PIMv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pimv6-flows {
     description "Show PIMv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pimv6-aggregate {
     description "Show aggregate for all PIMv6 traffic information";
     output {
       container ddos-protocols-information {
         uses ddos-protocols-information-block;
       }
     }
   }
   rpc get-ddos-pimv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-icmpv6-information {
     description "Show ICMPv6 traffic information";
     output {
       container ddos-protocols-information {
         uses ddos-protocols-information-block;
       }
     }
   }
   rpc get-ddos-icmpv6-parameters {
     description "Show ICMPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmpv6-statistics {
     description "Show ICMPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmpv6-violations {
     description "Show ICMPv6 traffic violations";
     output {
       container ddos-protocols-information {
         uses ddos-protocols-information-block;
       }
     }
   }
   rpc get-ddos-icmpv6-flow-parameters {
     description "Show ICMPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-icmpv6-flows {
     description "Show ICMPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-icmpv6-aggregate {
     description "Show aggregate for all ICMPv6 traffic information";
     output {
       container ddos-protocols-information {
         uses ddos-protocols-information-block;
       }
     }
   }
   rpc get-ddos-icmpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-information {
     description "Show NDPv6 traffic information";
     output {
       container ddos-protocols-information {
         uses ddos-protocols-information-block;
       }
     }
   }
   rpc get-ddos-ndpv6-parameters {
     description "Show NDPv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ndpv6-statistics {
     description "Show NDPv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ndpv6-violations {
     description "Show NDPv6 traffic violations";
     output {
       container ddos-protocols-information {
         uses ddos-protocols-information-block;
       }
     }
   }
   rpc get-ddos-ndpv6-flow-parameters {
     description "Show NDPv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ndpv6-flows {
     description "Show NDPv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-aggregate {
     description "Show aggregate for all NDPv6 traffic information";
     output {
       container ddos-protocols-information {
         uses ddos-protocols-information-block;
       }
     }
   }
   rpc get-ddos-ndpv6-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-router-sol {
     description "Show NDPv6 router-solicitation information";
     output {
       container ddos-protocols-information {
         uses ddos-protocols-information-block;
       }
     }
   }
   rpc get-ddos-ndpv6-router-sol-flows {
     description "Show router-solicitation culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-router-adv {
     description "Show NDPv6 router-advertisement information";
     output {
       container ddos-protocols-information {
         uses ddos-protocols-information-block;
       }
     }
   }
   rpc get-ddos-ndpv6-router-adv-flows {
     description "Show router-advertisement culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-neighb-sol {
     description "Show NDPv6 neighbor-solicitation information";
     output {
       container ddos-protocols-information {
         uses ddos-protocols-information-block;
       }
     }
   }
   rpc get-ddos-ndpv6-neighb-sol-flows {
     description "Show neighbor-solicitation culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-neighb-adv {
     description "Show NDPv6 neighbor-advertisement information";
     output {
       container ddos-protocols-information {
         uses ddos-protocols-information-block;
       }
     }
   }
   rpc get-ddos-ndpv6-neighb-adv-flows {
     description "Show neighbor-advertisement culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-redirect {
     description "Show NDPv6 redirect information";
     output {
       container ddos-protocols-information {
         uses ddos-protocols-information-block;
       }
     }
   }
   rpc get-ddos-ndpv6-redirect-flows {
     description "Show redirect culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ndpv6-inval-hop {
     description "Show NDPv6 with invalid hop limit information";
     output {
       container ddos-protocols-information {
         uses ddos-protocols-information-block;
       }
     }
   }
   rpc get-ddos-ndpv6-inval-hop-flows {
     description "Show invalid-hop-limit culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-information {
     description "Show sampled traffic information";
     output {
       container ddos-protocols-information {
         uses ddos-protocols-information-block;
       }
     }
   }
   rpc get-ddos-sample-parameters {
     description "Show Sample protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-statistics {
     description "Show Sample statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-violations {
     description "Show Sample traffic violations";
     output {
       container ddos-protocols-information {
         uses ddos-protocols-information-block;
       }
     }
   }
   rpc get-ddos-sample-flow-parameters {
     description "Show Sample flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-flows {
     description "Show Sample culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-aggregate {
     description "Show aggregate for all sampled traffic information";
     output {
       container ddos-protocols-information {
         uses ddos-protocols-information-block;
       }
     }
   }
   rpc get-ddos-sample-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-syslog {
     description "Show Syslog sample traffic information";
     output {
       container ddos-protocols-information {
         uses ddos-protocols-information-block;
       }
     }
   }
   rpc get-ddos-sample-syslog-flows {
     description "Show syslog culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-host {
     description "Show Host sample traffic information";
     output {
       container ddos-protocols-information {
         uses ddos-protocols-information-block;
       }
     }
   }
   rpc get-ddos-sample-host-flows {
     description "Show host culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-pfe {
     description "Show PFE sample traffic information";
     output {
       container ddos-protocols-information {
         uses ddos-protocols-information-block;
       }
     }
   }
   rpc get-ddos-sample-pfe-flows {
     description "Show pfe culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-tap {
     description "Show Tap sample traffic information";
     output {
       container ddos-protocols-information {
         uses ddos-protocols-information-block;
       }
     }
   }
   rpc get-ddos-sample-tap-flows {
     description "Show tap culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-sflow {
     description "Show Sflow sample traffic information";
     output {
       container ddos-protocols-information {
         uses ddos-protocols-information-block;
       }
     }
   }
   rpc get-ddos-sample-sflow-flows {
     description "Show sflow culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-information {
     description "Show RE Services IPv4 traffic information";
     output {
       container ddos-protocols-information {
         uses ddos-protocols-information-block;
       }
     }
   }
   rpc get-ddos-re-services-parameters {
     description "Show RE-services protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-statistics {
     description "Show RE-services statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-violations {
     description "Show RE-services traffic violations";
     output {
       container ddos-protocols-information {
         uses ddos-protocols-information-block;
       }
     }
   }
   rpc get-ddos-re-services-flow-parameters {
     description "Show RE-services flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-flows {
     description "Show RE-services culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-aggregate {
     description "Show aggregate for all RE Services IPv4 traffic information";
     output {
       container ddos-protocols-information {
         uses ddos-protocols-information-block;
       }
     }
   }
   rpc get-ddos-re-services-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-captive-portal {
     description "Show Captive Portal IPv4 traffic information";
     output {
       container ddos-protocols-information {
         uses ddos-protocols-information-block;
       }
     }
   }
   rpc get-ddos-re-services-captive-portal-flows {
     description "Show captive-portal culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-v6-information {
     description "Show RE Services IPv6 traffic information";
     output {
       container ddos-protocols-information {
         uses ddos-protocols-information-block;
       }
     }
   }
   rpc get-ddos-re-services-v6-parameters {
     description "Show RE-services-v6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-v6-statistics {
     description "Show RE-services-v6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-v6-violations {
     description "Show RE-services-v6 traffic violations";
     output {
       container ddos-protocols-information {
         uses ddos-protocols-information-block;
       }
     }
   }
   rpc get-ddos-re-services-v6-flow-parameters {
     description "Show RE-services-v6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-re-services-v6-flows {
     description "Show RE-services-v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-v6-aggregate {
     description "Show aggregate for all RE Services IPv6 traffic information";
     output {
       container ddos-protocols-information {
         uses ddos-protocols-information-block;
       }
     }
   }
   rpc get-ddos-re-services-v6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-re-services-v6-captive-portal-v6 {
     description "Show Captive Portal IPv6 traffic information";
     output {
       container ddos-protocols-information {
         uses ddos-protocols-information-block;
       }
     }
   }
   rpc get-ddos-re-services-v6-captive-portal-v6-flows {
     description "Show captive-portal culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fab-probe-information {
     description "Show fab out probe packets information";
     output {
       container ddos-protocols-information {
         uses ddos-protocols-information-block;
       }
     }
   }
   rpc get-ddos-fab-probe-parameters {
     description "Show Fab-Probe protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fab-probe-statistics {
     description "Show Fab-Probe statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fab-probe-violations {
     description "Show Fab-Probe traffic violations";
     output {
       container ddos-protocols-information {
         uses ddos-protocols-information-block;
       }
     }
   }
   rpc get-ddos-fab-probe-flow-parameters {
     description "Show Fab-Probe flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fab-probe-flows {
     description "Show Fab-Probe culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fab-probe-aggregate {
     description "Show aggregate for all fab out probe packets information";
     output {
       container ddos-protocols-information {
         uses ddos-protocols-information-block;
       }
     }
   }
   rpc get-ddos-fab-probe-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-uncls-information {
     description "Show unclassified host-bound traffic information";
     output {
       container ddos-protocols-information {
         uses ddos-protocols-information-block;
       }
     }
   }
   rpc get-ddos-uncls-parameters {
     description "Show unclassified protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-uncls-statistics {
     description "Show unclassified statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-uncls-violations {
     description "Show unclassified traffic violations";
     output {
       container ddos-protocols-information {
         uses ddos-protocols-information-block;
       }
     }
   }
   rpc get-ddos-uncls-flow-parameters {
     description "Show unclassified flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-uncls-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-uncls-aggregate {
     description "Show aggregate for all unclassified host-bound traffic information";
     output {
       container ddos-protocols-information {
         uses ddos-protocols-information-block;
       }
     }
   }
   rpc get-ddos-uncls-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-uncls-other {
     description "Show all other unclassified packets information";
     output {
       container ddos-protocols-information {
         uses ddos-protocols-information-block;
       }
     }
   }
   rpc get-ddos-uncls-other-flows {
     description "Show other culprit flows";
     output {
       container ddos-protocols-information {
         uses ddos-protocols-information-block;
       }
     }
   }
   rpc get-ddos-uncls-resolve-v4 {
     description "Show unclassified v4 resolve packets information";
     status deprecated;
     output {
       container ddos-protocols-information {
         uses ddos-protocols-information-block;
       }
     }
   }
   rpc get-ddos-uncls-resolve-v4-flows {
     description "Show resolve-v4 culprit flows";
     output {
       container ddos-protocols-information {
         uses ddos-protocols-information-block;
       }
     }
   }
   rpc get-ddos-uncls-resolve-v6 {
     description "Show unclassified v6 resolve packets information";
     status deprecated;
     output {
       container ddos-protocols-information {
         uses ddos-protocols-information-block;
       }
     }
   }
   rpc get-ddos-uncls-resolve-v6-flows {
     description "Show resolve-v6 culprit flows";
     output {
       container ddos-protocols-information {
         uses ddos-protocols-information-block;
       }
     }
   }
   rpc get-ddos-uncls-control-v4 {
     description "Show unclassified v4 control packets information";
     output {
       container ddos-protocols-information {
         uses ddos-protocols-information-block;
       }
     }
   }
   rpc get-ddos-uncls-control-v4-flows {
     description "Show control-v4 culprit flows";
     output {
       container ddos-protocols-information {
         uses ddos-protocols-information-block;
       }
     }
   }
   rpc get-ddos-uncls-control-v6 {
     description "Show unclassified v6 control packets information";
     output {
       container ddos-protocols-information {
         uses ddos-protocols-information-block;
       }
     }
   }
   rpc get-ddos-uncls-control-v6-flows {
     description "Show control-v6 culprit flows";
     output {
       container ddos-protocols-information {
         uses ddos-protocols-information-block;
       }
     }
   }
   rpc get-ddos-uncls-host-rt-v4 {
     description "Show unclassified v4 hostbound packets information";
     output {
       container ddos-protocols-information {
         uses ddos-protocols-information-block;
       }
     }
   }
   rpc get-ddos-uncls-host-rt-v4-flows {
     description "Show host-route-v4 culprit flows";
     output {
       container ddos-protocols-information {
         uses ddos-protocols-information-block;
       }
     }
   }
   rpc get-ddos-uncls-host-rt-v6 {
     description "Show unclassified v6 hostbound packets information";
     output {
       container ddos-protocols-information {
         uses ddos-protocols-information-block;
       }
     }
   }
   rpc get-ddos-uncls-host-rt-v6-flows {
     description "Show host-route-v6 culprit flows";
     output {
       container ddos-protocols-information {
         uses ddos-protocols-information-block;
       }
     }
   }
   rpc get-ddos-uncls-host-rt-udp-v4 {
     description "Show unclassified udp v4 hostbound packets information";
     output {
       container ddos-protocols-information {
         uses ddos-protocols-information-block;
       }
     }
   }
   rpc get-ddos-uncls-host-rt-udp-v4-flows {
     description "Show host-route-udp-v4 culprit flows";
     output {
       container ddos-protocols-information {
         uses ddos-protocols-information-block;
       }
     }
   }
   rpc get-ddos-uncls-host-rt-tcp-v4 {
     description "Show unclassified tcp v4 hostbound packets information";
     output {
       container ddos-protocols-information {
         uses ddos-protocols-information-block;
       }
     }
   }
   rpc get-ddos-uncls-host-rt-tcp-v4-flows {
     description "Show host-route-tcp-v4 culprit flows";
     output {
       container ddos-protocols-information {
         uses ddos-protocols-information-block;
       }
     }
   }
   rpc get-ddos-uncls-filter-v4 {
     description "Show unclassified v4 filter action packets information";
     status deprecated;
     output {
       container ddos-protocols-information {
         uses ddos-protocols-information-block;
       }
     }
   }
   rpc get-ddos-uncls-filter-v4-flows {
     description "Show filter-v4 culprit flows";
     output {
       container ddos-protocols-information {
         uses ddos-protocols-information-block;
       }
     }
   }
   rpc get-ddos-uncls-filter-v6 {
     description "Show unclassified v6 filter action packets information";
     status deprecated;
     output {
       container ddos-protocols-information {
         uses ddos-protocols-information-block;
       }
     }
   }
   rpc get-ddos-uncls-filter-v6-flows {
     description "Show filter-v6 culprit flows";
     output {
       container ddos-protocols-information {
         uses ddos-protocols-information-block;
       }
     }
   }
   rpc get-ddos-uncls-control-l2 {
     description "Show unclassified layer2 control packets information";
     output {
       container ddos-protocols-information {
         uses ddos-protocols-information-block;
       }
     }
   }
   rpc get-ddos-uncls-control-l2-flows {
     description "Show control-layer2 culprit flows";
     output {
       container ddos-protocols-information {
         uses ddos-protocols-information-block;
       }
     }
   }
   rpc get-ddos-uncls-fw-host {
     description "Show Unclassified send to host fw traffic information";
     output {
       container ddos-protocols-information {
         uses ddos-protocols-information-block;
       }
     }
   }
   rpc get-ddos-uncls-fw-host-flows {
     description "Show fw-host culprit flows";
     output {
       container ddos-protocols-information {
         uses ddos-protocols-information-block;
       }
     }
   }
   rpc get-ddos-uncls-mcast-copy {
     description "Show Unclassified host copy due to multicast routing information";
     output {
       container ddos-protocols-information {
         uses ddos-protocols-information-block;
       }
     }
   }
   rpc get-ddos-uncls-mcast-copy-flows {
     description "Show mcast-copy culprit flows";
     output {
       container ddos-protocols-information {
         uses ddos-protocols-information-block;
       }
     }
   }
   rpc get-ddos-rejectv6-information {
     description "Show packets via 'rejectv6' action information";
     output {
       container ddos-protocols-information {
         uses ddos-protocols-information-block;
       }
     }
   }
   rpc get-ddos-rejectv6-parameters {
     description "Show Rejectv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rejectv6-statistics {
     description "Show Rejectv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rejectv6-violations {
     description "Show Rejectv6 traffic violations";
     output {
       container ddos-protocols-information {
         uses ddos-protocols-information-block;
       }
     }
   }
   rpc get-ddos-rejectv6-flow-parameters {
     description "Show Rejectv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-rejectv6-flows {
     description "Show Rejectv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-rejectv6-aggregate {
     description "Show aggregate for all packets via 'rejectv6' action information";
     output {
       container ddos-protocols-information {
         uses ddos-protocols-information-block;
       }
     }
   }
   rpc get-ddos-rejectv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l2pt-information {
     description "Show Layer 2 protocol tunneling information";
     output {
       container ddos-protocols-information {
         uses ddos-protocols-information-block;
       }
     }
   }
   rpc get-ddos-l2pt-parameters {
     description "Show l2pt protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2pt-statistics {
     description "Show l2pt statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2pt-violations {
     description "Show l2pt traffic violations";
     output {
       container ddos-protocols-information {
         uses ddos-protocols-information-block;
       }
     }
   }
   rpc get-ddos-l2pt-flow-parameters {
     description "Show l2pt flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l2pt-flows {
     description "Show l2pt culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l2pt-aggregate {
     description "Show aggregate for all Layer 2 protocol tunneling information";
     output {
       container ddos-protocols-information {
         uses ddos-protocols-information-block;
       }
     }
   }
   rpc get-ddos-l2pt-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tunnel-ka-information {
     description "Show tunnel keepalive packets information";
     output {
       container ddos-protocols-information {
         uses ddos-protocols-information-block;
       }
     }
   }
   rpc get-ddos-tunnel-ka-parameters {
     description "Show Tunnel-KA protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tunnel-ka-statistics {
     description "Show Tunnel-KA statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tunnel-ka-violations {
     description "Show Tunnel-KA traffic violations";
     output {
       container ddos-protocols-information {
         uses ddos-protocols-information-block;
       }
     }
   }
   rpc get-ddos-tunnel-ka-flow-parameters {
     description "Show Tunnel-KA flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tunnel-ka-flows {
     description "Show Tunnel-KA culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tunnel-ka-aggregate {
     description "Show aggregate for all tunnel keepalive packets information";
     output {
       container ddos-protocols-information {
         uses ddos-protocols-information-block;
       }
     }
   }
   rpc get-ddos-tunnel-ka-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-inline-ka-information {
     description "Show inline keepalive packets information";
     output {
       container ddos-protocols-information {
         uses ddos-protocols-information-block;
       }
     }
   }
   rpc get-ddos-inline-ka-parameters {
     description "Show Inline-KA protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-ka-statistics {
     description "Show Inline-KA statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-ka-violations {
     description "Show Inline-KA traffic violations";
     output {
       container ddos-protocols-information {
         uses ddos-protocols-information-block;
       }
     }
   }
   rpc get-ddos-inline-ka-flow-parameters {
     description "Show Inline-KA flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-ka-flows {
     description "Show Inline-KA culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-inline-ka-aggregate {
     description "Show aggregate for all inline keepalive packets information";
     output {
       container ddos-protocols-information {
         uses ddos-protocols-information-block;
       }
     }
   }
   rpc get-ddos-inline-ka-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-inline-svcs-information {
     description "Show inline services information";
     output {
       container ddos-protocols-information {
         uses ddos-protocols-information-block;
       }
     }
   }
   rpc get-ddos-inline-svcs-parameters {
     description "Show Inline-SVCS protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-svcs-statistics {
     description "Show Inline-SVCS statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-svcs-violations {
     description "Show Inline-SVCS traffic violations";
     output {
       container ddos-protocols-information {
         uses ddos-protocols-information-block;
       }
     }
   }
   rpc get-ddos-inline-svcs-flow-parameters {
     description "Show Inline-SVCS flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-inline-svcs-flows {
     description "Show Inline-SVCS culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-inline-svcs-aggregate {
     description "Show aggregate for all inline services information";
     output {
       container ddos-protocols-information {
         uses ddos-protocols-information-block;
       }
     }
   }
   rpc get-ddos-inline-svcs-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-frame-relay-information {
     description "Show frame relay control packets information";
     output {
       container ddos-protocols-information {
         uses ddos-protocols-information-block;
       }
     }
   }
   rpc get-ddos-frame-relay-parameters {
     description "Show Frame-relay protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-frame-relay-statistics {
     description "Show Frame-relay statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-frame-relay-violations {
     description "Show Frame-relay traffic violations";
     output {
       container ddos-protocols-information {
         uses ddos-protocols-information-block;
       }
     }
   }
   rpc get-ddos-frame-relay-flow-parameters {
     description "Show Frame-relay flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-frame-relay-flows {
     description "Show Frame-relay culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-frame-relay-aggregate {
     description "Show aggregate for all frame relay control packets information";
     output {
       container ddos-protocols-information {
         uses ddos-protocols-information-block;
       }
     }
   }
   rpc get-ddos-frame-relay-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-frame-relay-frf15 {
     description "Show Multilink frame relay FRF.15 ctrl packets information";
     output {
       container ddos-protocols-information {
         uses ddos-protocols-information-block;
       }
     }
   }
   rpc get-ddos-frame-relay-frf15-flows {
     description "Show frf15 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-frame-relay-frf16 {
     description "Show Multilink frame relay FRF.16 ctrl packets information";
     output {
       container ddos-protocols-information {
         uses ddos-protocols-information-block;
       }
     }
   }
   rpc get-ddos-frame-relay-frf16-flows {
     description "Show frf16 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-amtv4-information {
     description "Show AMT v4 control packets information";
     output {
       container ddos-protocols-information {
         uses ddos-protocols-information-block;
       }
     }
   }
   rpc get-ddos-amtv4-parameters {
     description "Show AMTv4 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv4-statistics {
     description "Show AMTv4 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv4-violations {
     description "Show AMTv4 traffic violations";
     output {
       container ddos-protocols-information {
         uses ddos-protocols-information-block;
       }
     }
   }
   rpc get-ddos-amtv4-flow-parameters {
     description "Show AMTv4 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv4-flows {
     description "Show AMTv4 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-amtv4-aggregate {
     description "Show aggregate for all AMT v4 control packets information";
     output {
       container ddos-protocols-information {
         uses ddos-protocols-information-block;
       }
     }
   }
   rpc get-ddos-amtv4-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-amtv6-information {
     description "Show AMT v6 control packets information";
     output {
       container ddos-protocols-information {
         uses ddos-protocols-information-block;
       }
     }
   }
   rpc get-ddos-amtv6-parameters {
     description "Show AMTv6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv6-statistics {
     description "Show AMTv6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv6-violations {
     description "Show AMTv6 traffic violations";
     output {
       container ddos-protocols-information {
         uses ddos-protocols-information-block;
       }
     }
   }
   rpc get-ddos-amtv6-flow-parameters {
     description "Show AMTv6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-amtv6-flows {
     description "Show AMTv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-amtv6-aggregate {
     description "Show aggregate for all AMT v6 control packets information";
     output {
       container ddos-protocols-information {
         uses ddos-protocols-information-block;
       }
     }
   }
   rpc get-ddos-amtv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-syslog-information {
     description "Show syslog traffic information";
     output {
       container ddos-protocols-information {
         uses ddos-protocols-information-block;
       }
     }
   }
   rpc get-ddos-syslog-parameters {
     description "Show Syslog protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-syslog-statistics {
     description "Show Syslog statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-syslog-violations {
     description "Show Syslog traffic violations";
     output {
       container ddos-protocols-information {
         uses ddos-protocols-information-block;
       }
     }
   }
   rpc get-ddos-syslog-flow-parameters {
     description "Show Syslog flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-syslog-flows {
     description "Show Syslog culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-syslog-aggregate {
     description "Show aggregate for all syslog traffic information";
     output {
       container ddos-protocols-information {
         uses ddos-protocols-information-block;
       }
     }
   }
   rpc get-ddos-syslog-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-ctrl-information {
     description "Show PIM control packets information";
     output {
       container ddos-protocols-information {
         uses ddos-protocols-information-block;
       }
     }
   }
   rpc get-ddos-pim-ctrl-parameters {
     description "Show PIM-ctrl protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-ctrl-statistics {
     description "Show PIM-ctrl statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-ctrl-violations {
     description "Show PIM-ctrl traffic violations";
     output {
       container ddos-protocols-information {
         uses ddos-protocols-information-block;
       }
     }
   }
   rpc get-ddos-pim-ctrl-flow-parameters {
     description "Show PIM-ctrl flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-ctrl-flows {
     description "Show PIM-ctrl culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-ctrl-aggregate {
     description "Show aggregate for all PIM control packets information";
     output {
       container ddos-protocols-information {
         uses ddos-protocols-information-block;
       }
     }
   }
   rpc get-ddos-pim-ctrl-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-ctrl-hello {
     description "Show PIM Control Hello Traffic information";
     output {
       container ddos-protocols-information {
         uses ddos-protocols-information-block;
       }
     }
   }
   rpc get-ddos-pim-ctrl-hello-flows {
     description "Show hello culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-ctrl-join {
     description "Show PIM Control Join Traffic information";
     output {
       container ddos-protocols-information {
         uses ddos-protocols-information-block;
       }
     }
   }
   rpc get-ddos-pim-ctrl-join-flows {
     description "Show join culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospf-hello-information {
     description "Show OSPF hello packets information";
     output {
       container ddos-protocols-information {
         uses ddos-protocols-information-block;
       }
     }
   }
   rpc get-ddos-ospf-hello-parameters {
     description "Show OSPF-hello protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-hello-statistics {
     description "Show OSPF-hello statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-hello-violations {
     description "Show OSPF-hello traffic violations";
     output {
       container ddos-protocols-information {
         uses ddos-protocols-information-block;
       }
     }
   }
   rpc get-ddos-ospf-hello-flow-parameters {
     description "Show OSPF-hello flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ospf-hello-flows {
     description "Show OSPF-hello culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ospf-hello-aggregate {
     description "Show aggregate for all OSPF hello packets information";
     output {
       container ddos-protocols-information {
         uses ddos-protocols-information-block;
       }
     }
   }
   rpc get-ddos-ospf-hello-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-data-information {
     description "Show PIM data information";
     output {
       container ddos-protocols-information {
         uses ddos-protocols-information-block;
       }
     }
   }
   rpc get-ddos-pim-data-parameters {
     description "Show PIM-data protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-data-statistics {
     description "Show PIM-data statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-data-violations {
     description "Show PIM-data traffic violations";
     output {
       container ddos-protocols-information {
         uses ddos-protocols-information-block;
       }
     }
   }
   rpc get-ddos-pim-data-flow-parameters {
     description "Show PIM-data flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pim-data-flows {
     description "Show PIM-data culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pim-data-aggregate {
     description "Show aggregate for all PIM data information";
     output {
       container ddos-protocols-information {
         uses ddos-protocols-information-block;
       }
     }
   }
   rpc get-ddos-pim-data-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fip-snooping-information {
     description "Show FIP snooping information";
     output {
       container ddos-protocols-information {
         uses ddos-protocols-information-block;
       }
     }
   }
   rpc get-ddos-fip-snooping-parameters {
     description "Show FIP-SNOOPING protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fip-snooping-statistics {
     description "Show FIP-SNOOPING statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fip-snooping-violations {
     description "Show FIP-SNOOPING traffic violations";
     output {
       container ddos-protocols-information {
         uses ddos-protocols-information-block;
       }
     }
   }
   rpc get-ddos-fip-snooping-flow-parameters {
     description "Show FIP-SNOOPING flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-fip-snooping-flows {
     description "Show FIP-SNOOPING culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-fip-snooping-aggregate {
     description "Show aggregate for all FIP snooping information";
     output {
       container ddos-protocols-information {
         uses ddos-protocols-information-block;
       }
     }
   }
   rpc get-ddos-fip-snooping-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-unknown-l2mc-information {
     description "Show Unknown layer 2 multicast information";
     output {
       container ddos-protocols-information {
         uses ddos-protocols-information-block;
       }
     }
   }
   rpc get-ddos-unknown-l2mc-parameters {
     description "Show UNKNOWN-L2mc protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-unknown-l2mc-statistics {
     description "Show UNKNOWN-L2mc statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-unknown-l2mc-violations {
     description "Show UNKNOWN-L2mc traffic violations";
     output {
       container ddos-protocols-information {
         uses ddos-protocols-information-block;
       }
     }
   }
   rpc get-ddos-unknown-l2mc-flow-parameters {
     description "Show UNKNOWN-L2mc flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-unknown-l2mc-flows {
     description "Show UNKNOWN-L2mc culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-unknown-l2mc-aggregate {
     description "Show aggregate for all Unknown layer 2 multicast information";
     output {
       container ddos-protocols-information {
         uses ddos-protocols-information-block;
       }
     }
   }
   rpc get-ddos-unknown-l2mc-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-nonucast-switch-information {
     description "Show Non unicast switched information";
     output {
       container ddos-protocols-information {
         uses ddos-protocols-information-block;
       }
     }
   }
   rpc get-ddos-nonucast-switch-parameters {
     description "Show NONUCAST-SWITCH protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-nonucast-switch-statistics {
     description "Show NONUCAST-SWITCH statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-nonucast-switch-violations {
     description "Show NONUCAST-SWITCH traffic violations";
     output {
       container ddos-protocols-information {
         uses ddos-protocols-information-block;
       }
     }
   }
   rpc get-ddos-nonucast-switch-flow-parameters {
     description "Show NONUCAST-SWITCH flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-nonucast-switch-flows {
     description "Show NONUCAST-SWITCH culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-nonucast-switch-aggregate {
     description "Show aggregate for all Non unicast switched information";
     output {
       container ddos-protocols-information {
         uses ddos-protocols-information-block;
       }
     }
   }
   rpc get-ddos-nonucast-switch-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipmcast-miss-information {
     description "Show IP multicast miss information";
     output {
       container ddos-protocols-information {
         uses ddos-protocols-information-block;
       }
     }
   }
   rpc get-ddos-ipmcast-miss-parameters {
     description "Show IPMCAST-miss protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmcast-miss-statistics {
     description "Show IPMCAST-miss statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmcast-miss-violations {
     description "Show IPMCAST-miss traffic violations";
     output {
       container ddos-protocols-information {
         uses ddos-protocols-information-block;
       }
     }
   }
   rpc get-ddos-ipmcast-miss-flow-parameters {
     description "Show IPMCAST-miss flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmcast-miss-flows {
     description "Show IPMCAST-miss culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipmcast-miss-aggregate {
     description "Show aggregate for all IP multicast miss information";
     output {
       container ddos-protocols-information {
         uses ddos-protocols-information-block;
       }
     }
   }
   rpc get-ddos-ipmcast-miss-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-urpf-fail-information {
     description "Show Unicast reverse path forwarding failure information";
     output {
       container ddos-protocols-information {
         uses ddos-protocols-information-block;
       }
     }
   }
   rpc get-ddos-urpf-fail-parameters {
     description "Show URPF-fail protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-urpf-fail-statistics {
     description "Show URPF-fail statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-urpf-fail-violations {
     description "Show URPF-fail traffic violations";
     output {
       container ddos-protocols-information {
         uses ddos-protocols-information-block;
       }
     }
   }
   rpc get-ddos-urpf-fail-flow-parameters {
     description "Show URPF-fail flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-urpf-fail-flows {
     description "Show URPF-fail culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-urpf-fail-aggregate {
     description "Show aggregate for all Unicast reverse path forwarding failure information";
     output {
       container ddos-protocols-information {
         uses ddos-protocols-information-block;
       }
     }
   }
   rpc get-ddos-urpf-fail-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3nhop-information {
     description "Show Layer 3 next hop to CPU information";
     output {
       container ddos-protocols-information {
         uses ddos-protocols-information-block;
       }
     }
   }
   rpc get-ddos-l3nhop-parameters {
     description "Show L3NHOP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3nhop-statistics {
     description "Show L3NHOP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3nhop-violations {
     description "Show L3NHOP traffic violations";
     output {
       container ddos-protocols-information {
         uses ddos-protocols-information-block;
       }
     }
   }
   rpc get-ddos-l3nhop-flow-parameters {
     description "Show L3NHOP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3nhop-flows {
     description "Show L3NHOP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3nhop-aggregate {
     description "Show aggregate for all Layer 3 next hop to CPU information";
     output {
       container ddos-protocols-information {
         uses ddos-protocols-information-block;
       }
     }
   }
   rpc get-ddos-l3nhop-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-martian-address-information {
     description "Show Martian address information";
     output {
       container ddos-protocols-information {
         uses ddos-protocols-information-block;
       }
     }
   }
   rpc get-ddos-martian-address-parameters {
     description "Show MARTIAN-address protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-martian-address-statistics {
     description "Show MARTIAN-address statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-martian-address-violations {
     description "Show MARTIAN-address traffic violations";
     output {
       container ddos-protocols-information {
         uses ddos-protocols-information-block;
       }
     }
   }
   rpc get-ddos-martian-address-flow-parameters {
     description "Show MARTIAN-address flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-martian-address-flows {
     description "Show MARTIAN-address culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-martian-address-aggregate {
     description "Show aggregate for all Martian address information";
     output {
       container ddos-protocols-information {
         uses ddos-protocols-information-block;
       }
     }
   }
   rpc get-ddos-martian-address-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3mc-sgv-hit-icl-information {
     description "Show Layer 3 multicast (*,G) hit ICL information";
     output {
       container ddos-protocols-information {
         uses ddos-protocols-information-block;
       }
     }
   }
   rpc get-ddos-l3mc-sgv-hit-icl-parameters {
     description "Show L3MC-SGV-hit-icl protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mc-sgv-hit-icl-statistics {
     description "Show L3MC-SGV-hit-icl statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mc-sgv-hit-icl-violations {
     description "Show L3MC-SGV-hit-icl traffic violations";
     output {
       container ddos-protocols-information {
         uses ddos-protocols-information-block;
       }
     }
   }
   rpc get-ddos-l3mc-sgv-hit-icl-flow-parameters {
     description "Show L3MC-SGV-hit-icl flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mc-sgv-hit-icl-flows {
     description "Show L3MC-SGV-hit-icl culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3mc-sgv-hit-icl-aggregate {
     description "Show aggregate for all Layer 3 multicast (*,G) hit ICL information";
     output {
       container ddos-protocols-information {
         uses ddos-protocols-information-block;
       }
     }
   }
   rpc get-ddos-l3mc-sgv-hit-icl-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3dest-miss-information {
     description "Show Layer 3 destination miss information";
     output {
       container ddos-protocols-information {
         uses ddos-protocols-information-block;
       }
     }
   }
   rpc get-ddos-l3dest-miss-parameters {
     description "Show L3DEST-miss protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3dest-miss-statistics {
     description "Show L3DEST-miss statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3dest-miss-violations {
     description "Show L3DEST-miss traffic violations";
     output {
       container ddos-protocols-information {
         uses ddos-protocols-information-block;
       }
     }
   }
   rpc get-ddos-l3dest-miss-flow-parameters {
     description "Show L3DEST-miss flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3dest-miss-flows {
     description "Show L3DEST-miss culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3dest-miss-aggregate {
     description "Show aggregate for all Layer 3 destination miss information";
     output {
       container ddos-protocols-information {
         uses ddos-protocols-information-block;
       }
     }
   }
   rpc get-ddos-l3dest-miss-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipmc-reserved-information {
     description "Show IP multicast reserved information";
     output {
       container ddos-protocols-information {
         uses ddos-protocols-information-block;
       }
     }
   }
   rpc get-ddos-ipmc-reserved-parameters {
     description "Show IPMC-reserved protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmc-reserved-statistics {
     description "Show IPMC-reserved statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmc-reserved-violations {
     description "Show IPMC-reserved traffic violations";
     output {
       container ddos-protocols-information {
         uses ddos-protocols-information-block;
       }
     }
   }
   rpc get-ddos-ipmc-reserved-flow-parameters {
     description "Show IPMC-reserved flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ipmc-reserved-flows {
     description "Show IPMC-reserved culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ipmc-reserved-aggregate {
     description "Show aggregate for all IP multicast reserved information";
     output {
       container ddos-protocols-information {
         uses ddos-protocols-information-block;
       }
     }
   }
   rpc get-ddos-ipmc-reserved-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-garp-reply-information {
     description "Show Gratuitous ARP reply information";
     output {
       container ddos-protocols-information {
         uses ddos-protocols-information-block;
       }
     }
   }
   rpc get-ddos-garp-reply-parameters {
     description "Show GARP-reply protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-garp-reply-statistics {
     description "Show GARP-reply statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-garp-reply-violations {
     description "Show GARP-reply traffic violations";
     output {
       container ddos-protocols-information {
         uses ddos-protocols-information-block;
       }
     }
   }
   rpc get-ddos-garp-reply-flow-parameters {
     description "Show GARP-reply flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-garp-reply-flows {
     description "Show GARP-reply culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-garp-reply-aggregate {
     description "Show aggregate for all Gratuitous ARP reply information";
     output {
       container ddos-protocols-information {
         uses ddos-protocols-information-block;
       }
     }
   }
   rpc get-ddos-garp-reply-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3mtu-fail-information {
     description "Show Layer 3 mtu failure information";
     output {
       container ddos-protocols-information {
         uses ddos-protocols-information-block;
       }
     }
   }
   rpc get-ddos-l3mtu-fail-parameters {
     description "Show L3MTU-fail protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mtu-fail-statistics {
     description "Show L3MTU-fail statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mtu-fail-violations {
     description "Show L3MTU-fail traffic violations";
     output {
       container ddos-protocols-information {
         uses ddos-protocols-information-block;
       }
     }
   }
   rpc get-ddos-l3mtu-fail-flow-parameters {
     description "Show L3MTU-fail flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-l3mtu-fail-flows {
     description "Show L3MTU-fail culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-l3mtu-fail-aggregate {
     description "Show aggregate for all Layer 3 mtu failure information";
     output {
       container ddos-protocols-information {
         uses ddos-protocols-information-block;
       }
     }
   }
   rpc get-ddos-l3mtu-fail-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-dest-information {
     description "Show Sample at egress information";
     output {
       container ddos-protocols-information {
         uses ddos-protocols-information-block;
       }
     }
   }
   rpc get-ddos-sample-dest-parameters {
     description "Show SAMPLE-dest protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-dest-statistics {
     description "Show SAMPLE-dest statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-dest-violations {
     description "Show SAMPLE-dest traffic violations";
     output {
       container ddos-protocols-information {
         uses ddos-protocols-information-block;
       }
     }
   }
   rpc get-ddos-sample-dest-flow-parameters {
     description "Show SAMPLE-dest flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-dest-flows {
     description "Show SAMPLE-dest culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-dest-aggregate {
     description "Show aggregate for all Sample at egress information";
     output {
       container ddos-protocols-information {
         uses ddos-protocols-information-block;
       }
     }
   }
   rpc get-ddos-sample-dest-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-source-information {
     description "Show Sample at ingress information";
     output {
       container ddos-protocols-information {
         uses ddos-protocols-information-block;
       }
     }
   }
   rpc get-ddos-sample-source-parameters {
     description "Show SAMPLE-source protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-source-statistics {
     description "Show SAMPLE-source statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-source-violations {
     description "Show SAMPLE-source traffic violations";
     output {
       container ddos-protocols-information {
         uses ddos-protocols-information-block;
       }
     }
   }
   rpc get-ddos-sample-source-flow-parameters {
     description "Show SAMPLE-source flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-sample-source-flows {
     description "Show SAMPLE-source culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-sample-source-aggregate {
     description "Show aggregate for all Sample at ingress information";
     output {
       container ddos-protocols-information {
         uses ddos-protocols-information-block;
       }
     }
   }
   rpc get-ddos-sample-source-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vcipc-udp-information {
     description "Show VC UDP packets information";
     output {
       container ddos-protocols-information {
         uses ddos-protocols-information-block;
       }
     }
   }
   rpc get-ddos-vcipc-udp-parameters {
     description "Show VCIPC-udp protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vcipc-udp-statistics {
     description "Show VCIPC-udp statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vcipc-udp-violations {
     description "Show VCIPC-udp traffic violations";
     output {
       container ddos-protocols-information {
         uses ddos-protocols-information-block;
       }
     }
   }
   rpc get-ddos-vcipc-udp-flow-parameters {
     description "Show VCIPC-udp flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vcipc-udp-flows {
     description "Show VCIPC-udp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vcipc-udp-aggregate {
     description "Show aggregate for all VC UDP packets information";
     output {
       container ddos-protocols-information {
         uses ddos-protocols-information-block;
       }
     }
   }
   rpc get-ddos-vcipc-udp-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vxlan-information {
     description "Show VXLAN L2/L3 packets information";
     output {
       container ddos-protocols-information {
         uses ddos-protocols-information-block;
       }
     }
   }
   rpc get-ddos-vxlan-parameters {
     description "Show VXLAN protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vxlan-statistics {
     description "Show VXLAN statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vxlan-violations {
     description "Show VXLAN traffic violations";
     output {
       container ddos-protocols-information {
         uses ddos-protocols-information-block;
       }
     }
   }
   rpc get-ddos-vxlan-flow-parameters {
     description "Show VXLAN flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-vxlan-flows {
     description "Show VXLAN culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vxlan-aggregate {
     description "Show aggregate for all VXLAN L2/L3 packets information";
     output {
       container ddos-protocols-information {
         uses ddos-protocols-information-block;
       }
     }
   }
   rpc get-ddos-vxlan-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-vxlan-bfd {
     description "Show VXLAN BFD packets information";
     output {
       container ddos-protocols-information {
         uses ddos-protocols-information-block;
       }
     }
   }
   rpc get-ddos-vxlan-bfd-flows {
     description "Show bfd culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4v6-information {
     description "Show DHCPv4/v6 traffic information";
     output {
       container ddos-protocols-information {
         uses ddos-protocols-information-block;
       }
     }
   }
   rpc get-ddos-dhcpv4v6-parameters {
     description "Show DHCPv4v6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4v6-statistics {
     description "Show DHCPv4v6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4v6-violations {
     description "Show DHCPv4v6 traffic violations";
     output {
       container ddos-protocols-information {
         uses ddos-protocols-information-block;
       }
     }
   }
   rpc get-ddos-dhcpv4v6-flow-parameters {
     description "Show DHCPv4v6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-dhcpv4v6-flows {
     description "Show DHCPv4v6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-dhcpv4v6-aggregate {
     description "Show aggregate for all DHCPv4/v6 traffic information";
     output {
       container ddos-protocols-information {
         uses ddos-protocols-information-block;
       }
     }
   }
   rpc get-ddos-dhcpv4v6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-localnh-information {
     description "Show Local nh hit ssh telnet ftp etc information";
     output {
       container ddos-protocols-information {
         uses ddos-protocols-information-block;
       }
     }
   }
   rpc get-ddos-localnh-parameters {
     description "Show LOCALNH-hit protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-localnh-statistics {
     description "Show LOCALNH-hit statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-localnh-violations {
     description "Show LOCALNH-hit traffic violations";
     output {
       container ddos-protocols-information {
         uses ddos-protocols-information-block;
       }
     }
   }
   rpc get-ddos-localnh-flow-parameters {
     description "Show LOCALNH-hit flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-localnh-flows {
     description "Show LOCALNH-hit culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-localnh-aggregate {
     description "Show aggregate for all Local nh hit ssh telnet ftp etc information";
     output {
       container ddos-protocols-information {
         uses ddos-protocols-information-block;
       }
     }
   }
   rpc get-ddos-localnh-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-8021x-information {
     description "Show 802.1X traffic information";
     output {
       container ddos-protocols-information {
         uses ddos-protocols-information-block;
       }
     }
   }
   rpc get-ddos-8021x-parameters {
     description "Show 8021X protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-8021x-statistics {
     description "Show 8021X statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-8021x-violations {
     description "Show 8021X traffic violations";
     output {
       container ddos-protocols-information {
         uses ddos-protocols-information-block;
       }
     }
   }
   rpc get-ddos-8021x-flow-parameters {
     description "Show 8021X flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-8021x-flows {
     description "Show 8021X culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-8021x-aggregate {
     description "Show aggregate for all 802.1X traffic information";
     output {
       container ddos-protocols-information {
         uses ddos-protocols-information-block;
       }
     }
   }
   rpc get-ddos-8021x-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-all-fc-enode-information {
     description "Show ALL_FC_ENODE traffic information";
     output {
       container ddos-protocols-information {
         uses ddos-protocols-information-block;
       }
     }
   }
   rpc get-ddos-all-fc-enode-parameters {
     description "Show ALL_FC_ENODE protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-all-fc-enode-statistics {
     description "Show ALL_FC_ENODE statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-all-fc-enode-violations {
     description "Show ALL_FC_ENODE traffic violations";
     output {
       container ddos-protocols-information {
         uses ddos-protocols-information-block;
       }
     }
   }
   rpc get-ddos-all-fc-enode-flow-parameters {
     description "Show ALL_FC_ENODE flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-all-fc-enode-flows {
     description "Show ALL_FC_ENODE culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-all-fc-enode-aggregate {
     description "Show aggregate for all ALL_FC_ENODE traffic information";
     output {
       container ddos-protocols-information {
         uses ddos-protocols-information-block;
       }
     }
   }
   rpc get-ddos-all-fc-enode-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcc-information {
     description "Show TCC traffic information";
     output {
       container ddos-protocols-information {
         uses ddos-protocols-information-block;
       }
     }
   }
   rpc get-ddos-tcc-parameters {
     description "Show TCC protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcc-statistics {
     description "Show TCC statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcc-violations {
     description "Show TCC traffic violations";
     output {
       container ddos-protocols-information {
         uses ddos-protocols-information-block;
       }
     }
   }
   rpc get-ddos-tcc-flow-parameters {
     description "Show TCC flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-tcc-flows {
     description "Show TCC culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcc-aggregate {
     description "Show aggregate for all TCC traffic information";
     output {
       container ddos-protocols-information {
         uses ddos-protocols-information-block;
       }
     }
   }
   rpc get-ddos-tcc-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcc-unclass {
     description "Show unclassified Unclassified TCC traffic information";
     output {
       container ddos-protocols-information {
         uses ddos-protocols-information-block;
       }
     }
   }
   rpc get-ddos-tcc-unclass-flows {
     description "Show unclassified culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcc-ethernet-tcc {
     description "Show Ethernet TCC traffic information";
     output {
       container ddos-protocols-information {
         uses ddos-protocols-information-block;
       }
     }
   }
   rpc get-ddos-tcc-ethernet-tcc-flows {
     description "Show ethernet-tcc culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-tcc-iso-tcc {
     description "Show ISO TCC traffic information";
     output {
       container ddos-protocols-information {
         uses ddos-protocols-information-block;
       }
     }
   }
   rpc get-ddos-tcc-iso-tcc-flows {
     description "Show iso-tcc culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pkt-inject-information {
     description "Show Packet Inject traffic information";
     output {
       container ddos-protocols-information {
         uses ddos-protocols-information-block;
       }
     }
   }
   rpc get-ddos-pkt-inject-parameters {
     description "Show Pkt-Inject protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pkt-inject-statistics {
     description "Show Pkt-Inject statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pkt-inject-violations {
     description "Show Pkt-Inject traffic violations";
     output {
       container ddos-protocols-information {
         uses ddos-protocols-information-block;
       }
     }
   }
   rpc get-ddos-pkt-inject-flow-parameters {
     description "Show Pkt-Inject flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pkt-inject-flows {
     description "Show Pkt-Inject culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pkt-inject-aggregate {
     description "Show aggregate for all Packet Inject traffic information";
     output {
       container ddos-protocols-information {
         uses ddos-protocols-information-block;
       }
     }
   }
   rpc get-ddos-pkt-inject-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ptpv6-information {
     description "Show PTPv6 traffic information";
     output {
       container ddos-protocols-information {
         uses ddos-protocols-information-block;
       }
     }
   }
   rpc get-ddos-ptpv6-parameters {
     description "Show PTPV6 protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptpv6-statistics {
     description "Show PTPV6 statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptpv6-violations {
     description "Show PTPV6 traffic violations";
     output {
       container ddos-protocols-information {
         uses ddos-protocols-information-block;
       }
     }
   }
   rpc get-ddos-ptpv6-flow-parameters {
     description "Show PTPV6 flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-ptpv6-flows {
     description "Show PTPV6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-ptpv6-aggregate {
     description "Show aggregate for all PTPv6 traffic information";
     output {
       container ddos-protocols-information {
         uses ddos-protocols-information-block;
       }
     }
   }
   rpc get-ddos-ptpv6-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pfcp-information {
     description "Show PFCP control traffic information";
     output {
       container ddos-protocols-information {
         uses ddos-protocols-information-block;
       }
     }
   }
   rpc get-ddos-pfcp-parameters {
     description "Show PFCP protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfcp-statistics {
     description "Show PFCP statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfcp-violations {
     description "Show PFCP traffic violations";
     output {
       container ddos-protocols-information {
         uses ddos-protocols-information-block;
       }
     }
   }
   rpc get-ddos-pfcp-flow-parameters {
     description "Show PFCP flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-pfcp-flows {
     description "Show PFCP culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-pfcp-aggregate {
     description "Show aggregate for all PFCP control traffic information";
     output {
       container ddos-protocols-information {
         uses ddos-protocols-information-block;
       }
     }
   }
   rpc get-ddos-pfcp-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gtp-path-mgmt-information {
     description "Show GTP path mgmt traffic information";
     output {
       container ddos-protocols-information {
         uses ddos-protocols-information-block;
       }
     }
   }
   rpc get-ddos-gtp-path-mgmt-parameters {
     description "Show gtp-path-mgmt protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gtp-path-mgmt-statistics {
     description "Show gtp-path-mgmt statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gtp-path-mgmt-violations {
     description "Show gtp-path-mgmt traffic violations";
     output {
       container ddos-protocols-information {
         uses ddos-protocols-information-block;
       }
     }
   }
   rpc get-ddos-gtp-path-mgmt-flow-parameters {
     description "Show gtp-path-mgmt flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-gtp-path-mgmt-flows {
     description "Show gtp-path-mgmt culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-gtp-path-mgmt-aggregate {
     description "Show aggregate for all GTP path mgmt traffic information";
     output {
       container ddos-protocols-information {
         uses ddos-protocols-information-block;
       }
     }
   }
   rpc get-ddos-gtp-path-mgmt-aggregate-flows {
     description "Show aggregate culprit flows";
     status deprecated;
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-custom-information {
     description "Show CUSTOM traffic information";
     output {
       container ddos-protocols-information {
         uses ddos-protocols-information-block;
       }
     }
   }
   rpc get-ddos-custom-parameters {
     description "Show CUSTOM protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-custom-statistics {
     description "Show CUSTOM statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-custom-violations {
     description "Show CUSTOM traffic violations";
     output {
       container ddos-protocols-information {
         uses ddos-protocols-information-block;
       }
     }
   }
   rpc get-ddos-custom-flow-parameters {
     description "Show CUSTOM flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-custom-flows {
     description "Show CUSTOM culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-custom-aggregate {
     description "Show aggregate for all CUSTOM traffic information";
     output {
       container ddos-protocols-information {
         uses ddos-protocols-information-block;
       }
     }
   }
   rpc get-ddos-custom-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-overlay-information {
     description "Show Overlay Control traffic information";
     output {
       container ddos-protocols-information {
         uses ddos-protocols-information-block;
       }
     }
   }
   rpc get-ddos-overlay-parameters {
     description "Show OVERLAY protocol parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-overlay-statistics {
     description "Show OVERLAY statistics and states";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-overlay-violations {
     description "Show OVERLAY traffic violations";
     output {
       container ddos-protocols-information {
         uses ddos-protocols-information-block;
       }
     }
   }
   rpc get-ddos-overlay-flow-parameters {
     description "Show OVERLAY flow detection parameters";
     input {
       leaf level {
         type enumeration {
           enum "brief" {
             description "Show brief output";
           }
           enum "detail" {
             description "Show detailed output";
           }
           enum "terse" {
             description "Show terse output";
           }
         }
       }
     }
     output {
       container ddos-protocols-information {
         uses ddos-protocols-information-block;
       }
     }
   }
   rpc get-ddos-overlay-flows {
     description "Show OVERLAY culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-overlay-aggregate {
     description "Show aggregate for all Overlay Control traffic information";
     output {
       container ddos-protocols-information {
         uses ddos-protocols-information-block;
       }
     }
   }
   rpc get-ddos-overlay-aggregate-flows {
     description "Show aggregate culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-overlay-arp {
     description "Show Overlay ARP traffic information";
     output {
       container ddos-protocols-information {
         uses ddos-protocols-information-block;
       }
     }
   }
   rpc get-ddos-overlay-arp-flows {
     description "Show arp culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-overlay-ndpv6 {
     description "Show Overlay NDPv6 traffic information";
     output {
       container ddos-protocols-information {
         uses ddos-protocols-information-block;
       }
     }
   }
   rpc get-ddos-overlay-ndpv6-flows {
     description "Show ndpv6 culprit flows";
     input {
       leaf fpc-slot {
         description "FPC slot number";
         type union {
           type string {
             pattern "<.*>|$.*";
           }
           type uint32;
         }
       }
       leaf level {
         type enumeration {
           enum "brief" {
             description "Show brief output";
           }
           enum "detail" {
             description "Show detailed output";
           }
           enum "summary" {
             description "Show flow information summary";
           }
         }
       }
     }
     output {
       container ddos-protocols-information {
         uses ddos-protocols-information-block;
       }
     }
   }
   rpc get-ddos-statistics-information {
     description "Show overall statistics";
     output {
       container ddos-statistics-information {
         uses ddos-statistics-information-block;
       }
     }
   }
   rpc get-ddos-version {
     description "Show version";
     output {
       container ddos-version {
         uses ddos-version-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping ddos-protocols-information-block {
     leaf total-packet-types {
       type int32;
       description "Total number of packet types";
     }
     leaf mod-packet-types {
       type int32;
       description "Number of packet types modified through user configuration";
     }
     leaf packet-types-rcvd-packets {
       type int32;
       description "Number of packet types that have received packets";
     }
     leaf packet-types-in-violation {
       type int32;
       description "Number of packet types receiving excess traffic";
     }
     leaf flows-current {
       type int32;
       description "Number of flows that are currently being tracked";
     }
     leaf flows-cumulative {
       type int32;
       description "Number of flows that the system has seen";
     }
     container ddos-protocol-group {
       leaf group-name {
         type string;
         description "Protocol group name";
       }
       container ddos-protocol {
         leaf packet-type {
           type string;
           description "Protocol packet type name";
         }
         leaf packet-type-description {
           type string;
           description "Protocol packet type description";
         }
         container ddos-basic-parameters {
           leaf policer-bandwidth {
             type int32;
             description "Policer bandwidth";
           }
           leaf policer-bandwidth-user {
             type string;
             description "User has configured the policer bandwidth";
           }
           leaf policer-burst {
             type int32;
             description "Policer burst";
           }
           leaf policer-burst-user {
             type int32;
             description "User has configured the policer burst";
           }
           leaf policer-time-recover {
             type int32;
             description "Time to return to normal state";
           }
           leaf policer-time-recover-user {
             type int32;
             description "User has configured the time to return to normal state";
           }
           leaf policer-enable {
             type string;
             description "Policer enable";
           }
           leaf policer-enable-user {
             type string;
             description "User has configured the policer enable option";
           }
           leaf policer-priority {
             type int32;
             description "Policer priority";
           }
           leaf policer-priority-user {
             type int32;
             description "User has configured the policer priority";
           }
           leaf policer-bypass-aggregate {
             type string;
             description "Bypass aggregate policer";
           }
           leaf policer-bypass-aggregate-user {
             type string;
             description "User has configured the bypass aggregate policer option";
           }
           leaf group-name {
             type string;
             description "Protocol group name";
           }
           leaf packet-type {
             type string;
             description "Protocol packet type name";
           }
           leaf policer-fpc-scaled {
             type string;
             description "Parameter scaling is configured for this FPC slot";
           }
         }
         container ddos-flow-detection {
           leaf ddos-flow-detection-enabled {
             type string;
             description "Flow detection enable";
           }
           leaf detection-mode {
             type string;
             description "Flow detection mode";
           }
           leaf detection-mode-user {
             type string;
             description "User has configured the flow detection mode";
           }
           leaf detect-time {
             type int32;
             description "The time to determine a flow is culprit";
           }
           leaf detect-time-user {
             type int32;
             description "User has configured the time to determine a flow is culprit";
           }
           leaf log-flows {
             type string;
             description "Log flow and other messages";
           }
           leaf log-flows-user {
             type string;
             description "User has configured the log flow and other messages option";
           }
           leaf recover-time {
             type int32;
             description "The time to remove a flow after its traffic is below max rate";
           }
           leaf recover-time-user {
             type int32;
             description "User has configured the time to remove a flow after its traffic is below max rate";
           }
           leaf timeout-active-flows {
             type string;
             description "Time out active flows";
           }
           leaf timeout-active-flows-user {
             type string;
             description "User has configured the time out active flows option";
           }
           leaf timeout-time {
             type int32;
             description "The time to remove a flow after it is discovered";
           }
           leaf timeout-time-user {
             type int32;
             description "User has configured the time to remove a flow after it is discovered";
           }
           container flow-aggregation-level-states {
             leaf sub-detection-mode {
               type string;
               description "Detection mode at subscriber level";
             }
             leaf sub-detection-mode-user {
               type string;
               description "User has configured the detection mode at subscriber level";
             }
             leaf sub-control-mode {
               type string;
               description "Flow control mode at subscriber level";
             }
             leaf sub-control-mode-user {
               type string;
               description "User has configured the flow control mode at subscriber level";
             }
             leaf sub-bandwidth {
               type int32;
               description "The maximum flow rate at subscriber level";
             }
             leaf sub-bandwidth-user {
               type int32;
               description "User has configured the maximum flow rate at subscriber level";
             }
             leaf ifl-detection-mode {
               type string;
               description "Detection mode at logical interface level";
             }
             leaf ifl-detection-mode-user {
               type string;
               description "User has configured the detection mode at logical interface level";
             }
             leaf ifl-control-mode {
               type string;
               description "Flow control mode at logical interface level";
             }
             leaf ifl-control-mode-user {
               type string;
               description "User has configured the flow control mode at logical interface level";
             }
             leaf ifl-bandwidth {
               type int32;
               description "The maximum flow rate at logical interface level";
             }
             leaf ifl-bandwidth-user {
               type int32;
               description "User has configured the maximum flow rate at logical interface level";
             }
             leaf ifd-detection-mode {
               type string;
               description "Detection mode at physical interface level";
             }
             leaf ifd-detection-mode-user {
               type string;
               description "User has configured the detection mode at physical interface level";
             }
             leaf ifd-control-mode {
               type string;
               description "Flow control mode at physical interface level";
             }
             leaf ifd-control-mode-user {
               type string;
               description "User has configured the flow control mode at physical interface level";
             }
             leaf ifd-bandwidth {
               type int32;
               description "The maximum flow rate at physical interface level";
             }
             leaf ifd-bandwidth-user {
               type int32;
               description "User has configured the maximum flow rate at physical interface level";
             }
           }
           leaf group-name {
             type string;
             description "Protocol group name";
           }
           leaf packet-type {
             type string;
             description "Protocol packet type name";
           }
           leaf policer-bandwidth {
             type int32;
             description "Policer bandwidth";
           }
           leaf policer-bandwidth-user {
             type string;
             description "User has configured the policer bandwidth";
           }
           leaf sub-detection-mode {
             type string;
             description "Detection mode at subscriber level";
           }
           leaf sub-control-mode {
             type string;
             description "Flow control mode at subscriber level";
           }
           leaf sub-bandwidth {
             type int32;
             description "The maximum flow rate at subscriber level";
           }
           leaf sub-level-user {
             type string;
             description "User has configured subscriber level parameters";
           }
           leaf ifl-detection-mode {
             type string;
             description "Detection mode at logical interface level";
           }
           leaf ifl-control-mode {
             type string;
             description "Flow control mode at logical interface level";
           }
           leaf ifl-bandwidth {
             type int32;
             description "The maximum flow rate at logical interface level";
           }
           leaf ifl-level-user {
             type string;
             description "User has configured logical interface level parameters";
           }
           leaf ifd-detection-mode {
             type string;
             description "Detection mode at physical interface level";
           }
           leaf ifd-control-mode {
             type string;
             description "Flow control mode at physical interface level";
           }
           leaf ifd-bandwidth {
             type int32;
             description "The maximum flow rate at physical interface level";
           }
           leaf ifd-level-user {
             type string;
             description "User has configured physical interface level parameters";
           }
         }
         list ddos-system-statistics {
           leaf fpc-violation-count-current {
             type int32;
             description "Number of FPCs receiving excess traffic";
           }
           leaf fpc-violation-count {
             type int32;
             description "Number of FPCs received excess traffic";
           }
           leaf policer-violation-start-time {
             type string;
             description "Time the policer violation was first observed";
           }
           leaf policer-violation-last-time {
             type string;
             description "Time the policer violation was last observed";
           }
           leaf policer-violation-duration {
             type string;
             description "Duration of the policer violation";
           }
           leaf policer-violation-count {
             type int32;
             description "Number of times the policer has been violated";
           }
           leaf packet-received {
             type int32;
             description "Number of packets received";
           }
           leaf packet-arrival-rate {
             type int32;
             description "Current packet arrival rate";
           }
           leaf packet-dropped {
             type int32;
             description "Number of packets dropped";
           }
           leaf packet-arrival-rate-max {
             type int32;
             description "Maximum packet arrival rate";
           }
           container ddos-flow-level-statistics {
             leaf flow-aggregation-level {
               type string;
               description "Aggregation level of the flow";
             }
             leaf flows-current {
               type int32;
               description "Number of flows that are currently being tracked";
             }
             leaf flows-cumulative {
               type int32;
               description "Number of flows that the system has seen";
             }
             leaf aggr-level-state {
               type string;
               description "The detection state of the aggregation level";
             }
           }
           leaf group-name {
             type string;
             description "Protocol group name";
           }
           leaf packet-type {
             type string;
             description "Protocol packet type name";
           }
           leaf protocol-states {
             type string;
             description "Current protocol states";
           }
         }
         list ddos-instance {
           leaf protocol-states-locale {
             type string;
             description "Location of the reported protocol states";
           }
           container ddos-instance-parameters {
             leaf policer-bandwidth {
               type int32;
               description "Policer bandwidth";
             }
             leaf policer-burst {
               type int32;
               description "Policer burst";
             }
             leaf policer-enable {
               type string;
               description "Policer enable";
             }
             leaf policer-enable-user {
               type string;
               description "User has configured the policer enable option";
             }
             leaf policer-bypass-aggregate {
               type string;
               description "Bypass aggregate policer";
             }
             leaf policer-bandwidth-scale {
               type int32;
               description "Policer bandwidth scale in percent";
             }
             leaf policer-bandwidth-scale-user {
               type string;
               description "User has configured the policer bandwidth scale";
             }
             leaf policer-burst-scale {
               type int32;
               description "Policer burst scale in percent";
             }
             leaf policer-burst-scale-user {
               type string;
               description "User has configured the policer burst scale";
             }
             leaf hostbound-queue {
               type int32;
               description "Hostbound queue for exception packets";
             }
             leaf hostbound-queue-user {
               type string;
               description "User has configured the hostbound queue";
             }
           }
           list ddos-instance-statistics {
             leaf policer-violation-start-time {
               type string;
               description "Time the policer violation was first observed";
             }
             leaf policer-violation-last-time {
               type string;
               description "Time the policer violation was last observed";
             }
             leaf policer-violation-duration {
               type string;
               description "Duration of the policer violation";
             }
             leaf policer-violation-count {
               type int32;
               description "Number of times the policer has been violated";
             }
             leaf packet-received {
               type int32;
               description "Number of packets received";
             }
             leaf packet-arrival-rate {
               type int32;
               description "Current packet arrival rate";
             }
             leaf packet-dropped {
               type int32;
               description "Number of packets dropped";
             }
             leaf packet-arrival-rate-max {
               type int32;
               description "Maximum packet arrival rate";
             }
             leaf packet-dropped-protocol {
               type int32;
               description "Number of packets dropped by individual policer(s)";
             }
             leaf packet-dropped-aggr {
               type int32;
               description "Number of packets dropped by aggregate policer";
             }
             leaf packet-dropped-flows {
               type int32;
               description "Number of packets dropped by flow suppression";
             }
             container ddos-flow-level-statistics {
               leaf flow-aggregation-level {
                 type string;
                 description "Aggregation level of the flow";
               }
               leaf flows-current {
                 type int32;
                 description "Number of flows that are currently being tracked";
               }
               leaf flows-cumulative {
                 type int32;
                 description "Number of flows that the system has seen";
               }
               leaf aggr-level-state {
                 type string;
                 description "The detection state of the aggregation level";
               }
             }
             leaf packet-dropped-others {
               type int32;
               description "Number of packets dropped by other policer(s)";
             }
           }
         }
         container ddos-culprit-flow {
           leaf group-name {
             type string;
             description "Protocol group name";
           }
           leaf packet-type {
             type string;
             description "Protocol packet type name";
           }
           leaf flow-interface {
             type string;
             description "Arriving interface of the flow";
           }
           leaf flow-source-addr {
             type string;
             description "Source address of flow";
           }
           leaf flow-aggregation-level {
             type string;
             description "Aggregation level of the flow";
           }
           leaf flow-id {
             type int32;
             description "Flow ID";
           }
           leaf flow-found-time {
             type string;
             description "The time the flow detect is detected";
           }
           leaf packet-arrival-rate {
             type int32;
             description "Current packet arrival rate";
           }
           leaf packet-received {
             type int32;
             description "Number of packets received";
           }
           leaf flow-ethertype {
             type string;
             description "Ethertype of the flow";
           }
           leaf flow-outer-vlan {
             type string;
             description "Outer vlan-id of the flow";
           }
           leaf flow-inner-vlan {
             type string;
             description "Inner vlan-id of the flow";
           }
           leaf flow-destination-addr {
             type string;
             description "Destination address of flow";
           }
           leaf flow-source-port {
             type string;
             description "Source port of flow";
           }
           leaf flow-destination-port {
             type string;
             description "Destination port of flow";
           }
           leaf vbf-flow-based {
             type string;
             description "Vbf flow based";
           }
           leaf vbf-flow-id {
             type int32;
             description "Vbf flow id";
           }
           leaf flow-icmp-type {
             type string;
             description "Icmp or Igmp type of flow";
           }
           leaf flow-icmp-code {
             type string;
             description "Icmp or Igmp code of flow";
           }
           leaf flow-last-violation {
             type string;
             description "The time the flow last violated its bandwidth";
           }
         }
         container ddos-violation-statistics {
           leaf group-name {
             type string;
             description "Protocol group name";
           }
           leaf packet-type {
             type string;
             description "Protocol packet type name";
           }
           leaf policer-bandwidth {
             type int32;
             description "Policer bandwidth";
           }
           leaf packet-arrival-rate {
             type int32;
             description "Current packet arrival rate";
           }
           leaf packet-arrival-rate-max {
             type int32;
             description "Maximum packet arrival rate";
           }
           leaf policer-violation-start-time {
             type string;
             description "Time the policer violation was first observed";
           }
           leaf protocol-states-locale {
             type string;
             description "Location of the reported protocol states";
           }
         }
       }
     }
   }
   grouping ddos-statistics-information-block {
     leaf ddos-policing-re-enabled {
       type string;
       description "Routing engine policing enable";
     }
     leaf ddos-policing-fpc-enabled {
       type string;
       description "FPC policing enable";
     }
     leaf ddos-flow-detection-enabled {
       type string;
       description "Flow detection enable";
     }
     leaf ddos-logging-enabled {
       type string;
       description "Logging enable";
     }
     leaf violation-report-rate {
       type int32;
       description "Policer violation status change report rate";
     }
     leaf flow-report-rate {
       type int32;
       description "Flow status change report rate";
     }
     leaf detection-mode {
       type string;
       description "Flow detection mode";
     }
     leaf aggr-level-detection-mode {
       type string;
       description "Aggregate level flow detection mode";
     }
     leaf aggr-level-control-mode {
       type string;
       description "Aggregate level flow control mode";
     }
     leaf packet-types-in-violation {
       type int32;
       description "Number of packet types receiving excess traffic";
     }
     leaf packet-types-seen-violation {
       type int32;
       description "Number of packet types received excess traffic";
     }
     leaf total-violations {
       type int32;
       description "Total number of policer violations";
     }
     leaf flows-current {
       type int32;
       description "Number of flows that are currently being tracked";
     }
     leaf flows-cumulative {
       type int32;
       description "Number of flows that the system has seen";
     }
   }
   grouping ddos-version-block {
     leaf total-groups {
       type string;
       description "Total number of protocol groups";
     }
     leaf total-packet-types {
       type int32;
       description "Total number of packet types";
     }
   }
 }
