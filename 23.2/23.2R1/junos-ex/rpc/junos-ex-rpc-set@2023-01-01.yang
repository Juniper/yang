/*
 * Copyright (c) 2023 Juniper Networks, Inc.
 * All rights reserved.
 */
 module junos-ex-rpc-set {
   namespace "http://yang.juniper.net/junos-ex/rpc/set";

   prefix set;

   import junos-common-types {
     prefix jt;
     revision-date 2023-01-01;
   }

   organization "Juniper Networks, Inc.";

   contact "yang-support@juniper.net";

   description "Junos RPC YANG module for set command(s)";

   revision 2023-01-01 {
     description "Junos: 23.2R1.14";
   }

   rpc set-cli-working-directory {
     description "Set working directory";
     input {
       leaf directory {
         description "Pathname of working directory";
         type string;
         mandatory true;
       }
     }
     output {
       container cli {
         uses cli-block;
       }
     }
   }
   rpc set-logical-router {
     description "Set default logical system";
     input {
       leaf logical-system {
         description "Name of logical system";
         type string {
         }
         mandatory true;
       }
       leaf tenant {
         description "Name of tenant";
         type string {
         }
       }
     }
     output {
       container cli {
         uses cli-block;
       }
     }
   }
   rpc set-tenant {
     description "Set default tenant";
     input {
       leaf tenant-name {
         description "Name of tenant";
         type string {
         }
         mandatory true;
       }
     }
     output {
       container cli {
         uses cli-block;
       }
     }
   }
   rpc set-system-connectivity-information {
     description "Set controller properties";
     output {
       choice output_c {
         case output-tag {
           leaf output {
             type string;
           }
         }
         case multichassis-tag {
           anyxml multi-routing-engine-results;
         }
       }
     }
   }
   rpc set-virtual-chassis-mode {
     description "Enable/disable virtual chassis mode";
     input {
       leaf disable {
         type enumeration {
           enum "disable" {
             description "Disable virtual chassis mode";
           }
         }
       }
       leaf local {
         description "Apply to local RE only";
         type empty;
       }
     }
     output {
       choice output_c {
         case output-tag {
           leaf output {
             type string;
           }
         }
         case multichassis-tag {
           anyxml multi-routing-engine-results;
         }
       }
     }
   }
   rpc set-rps-network {
     description "Set RPS network parameters";
     input {
       leaf member {
         description "Member of virtual chassis configuration";
         type union {
           type string {
             pattern "<.*>|$.*";
           }
           type int32;
         }
         mandatory true;
       }
       leaf ip-address {
         description "RPS IP address";
         type jt:ipv4addr;
       }
       leaf netmask {
         description "RPS netmask";
         type jt:ipv4addr;
       }
       leaf gateway {
         description "RPS gateway IP";
         type jt:ipv4addr;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping cli-block {
     leaf banner {
       type string;
     }
     leaf complete-on-space {
       type string;
     }
     leaf force {
       type empty;
     }
     leaf history-mode {
       type string;
     }
     leaf idle-timeout {
       type int32;
     }
     leaf ignore-signals {
       type string;
     }
     leaf log-level {
       type int32;
     }
     leaf log-to-stderr {
       type string;
     }
     leaf logical-system {
       type string;
     }
     leaf clear-logical-system {
       type string;
     }
     leaf tenant {
       type string;
     }
     leaf clear-tenant {
       type string;
     }
     leaf prompt {
       type string;
     }
     leaf prompt-change {
       type string;
     }
     leaf restart-on-upgrade {
       type string;
     }
     leaf screen-length {
       type int32;
     }
     leaf screen-width {
       type int32;
     }
     leaf show-cli {
       type empty;
     }
     leaf stdin-line {
       type string;
     }
     leaf terminal-type {
       type string;
     }
     leaf timestamp-format {
       type string;
     }
     leaf timestamp-disable {
       type empty;
     }
     leaf version-change {
       type empty;
     }
     leaf json-validate {
       type empty;
     }
     leaf working-directory {
       type string;
     }
     leaf reset-time-zone {
       type empty;
     }
     leaf trace-file-name {
       type string;
     }
     leaf reset-mgd-trace {
       type empty;
     }
     container display-version {
       leaf extensive {
         type empty;
       }
     }
     container history {
       leaf count {
         type int32;
       }
     }
     container monitor {
       leaf status {
         type string;
       }
       leaf stop-all {
         type empty;
       }
       container start {
         leaf source-filename {
           type string;
         }
         leaf allow-access {
           type empty;
         }
       }
       container stop {
         leaf source-filename {
           type string;
         }
       }
       container style {
         leaf header {
           type empty;
         }
         leaf none {
           type empty;
         }
         leaf prepend {
           type empty;
         }
       }
     }
     container display-xml-validate-data {
       leaf root-tag {
         type string;
       }
     }
   }
 }
