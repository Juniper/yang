/*
 * Copyright (c) 2023 Juniper Networks, Inc.
 * All rights reserved.
 */
 module junos-ex-rpc-jdaf {
   namespace "http://yang.juniper.net/junos-ex/rpc/jdaf";

   prefix jdaf;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for jdaf command(s)";

   revision 2023-01-01 {
     description "Junos: 23.2R1.14";
   }

   rpc get-jdaf-command-server-stats {
     description "Show JDAF server side statistics";
     junos:command "show jdaf service cmd statistics server";
     output {
       container jdaf-server-statistics {
         uses jdaf-server-statistics-block;
       }
     }
   }
   rpc get-jdaf-command-client-stats {
     description "Show JDAF client message statistics";
     junos:command "show jdaf service cmd statistics client";
     output {
       container jdaf-clients-statistics {
         uses jdaf-clients-statistics-block;
       }
     }
   }
   rpc get-jdaf-command-clients {
     description "Show JDAF client information";
     junos:command "show jdaf service cmd clients";
     output {
       container jdaf-clients {
         uses jdaf-clients-block;
       }
     }
   }
   rpc get-jdaf-config-server-stats {
     description "Show JDAF server side statistics";
     junos:command "show jdaf service config statistics server";
     output {
       container jdaf-server-statistics {
         uses jdaf-server-statistics-block;
       }
     }
   }
   rpc get-jdaf-config-client-stats {
     description "Show JDAF client message statistics";
     junos:command "show jdaf service config statistics client";
     output {
       container jdaf-clients-statistics {
         uses jdaf-clients-statistics-block;
       }
     }
   }
   rpc get-jdaf-config-clients {
     description "Show JDAF client information";
     junos:command "show jdaf service config clients";
     output {
       container jdaf-clients {
         uses jdaf-clients-block;
       }
     }
   }
   rpc get-jdaf-firewall-server-stats {
     description "Show JDAF server side statistics";
     junos:command "show jdaf service firewall statistics server";
     output {
       container jdaf-server-statistics {
         uses jdaf-server-statistics-block;
       }
     }
   }
   rpc get-jdaf-firewall-client-stats {
     description "Show JDAF client message statistics";
     junos:command "show jdaf service firewall statistics client";
     input {
       leaf client-id {
         description "Client id";
         junos:cli-feature "nokeyword";
         default "0";
         type union {
           type uint32;
           type string {
             pattern "<.*>|$.*";
           }
         }
       }
     }
     output {
       container jdaf-clients-statistics {
         uses jdaf-clients-statistics-block;
       }
     }
   }
   rpc get-jdaf-firewall-clients {
     description "Show JDAF client information";
     junos:command "show jdaf service firewall clients";
     output {
       container jdaf-clients {
         uses jdaf-clients-block;
       }
     }
   }
   rpc get-jdaf-interface-server-stats {
     description "Show JDAF server side statistics";
     junos:command "show jdaf service interface statistics server";
     output {
       container jdaf-server-statistics {
         uses jdaf-server-statistics-block;
       }
     }
   }
   rpc get-jdaf-interface-client-stats {
     description "Show JDAF client message statistics";
     junos:command "show jdaf service interface statistics client";
     input {
       leaf client-id {
         description "Client id";
         junos:cli-feature "nokeyword";
         default "0";
         type union {
           type uint32;
           type string {
             pattern "<.*>|$.*";
           }
         }
       }
     }
     output {
       container jdaf-clients-statistics {
         uses jdaf-clients-statistics-block;
       }
     }
   }
   rpc get-jdaf-interface-clients {
     description "Show JDAF client information";
     junos:command "show jdaf service interface clients";
     output {
       container jdaf-clients {
         uses jdaf-clients-block;
       }
     }
   }
   rpc get-jdaf-route-server-stats {
     description "Show JDAF server side statistics";
     junos:command "show jdaf service route statistics server";
     output {
       container jdaf-server-statistics {
         uses jdaf-server-statistics-block;
       }
     }
   }
   rpc get-jdaf-route-client-stats {
     description "Show JDAF client message statistics";
     junos:command "show jdaf service route statistics client";
     input {
       leaf client-id {
         description "Client id";
         junos:cli-feature "nokeyword";
         default "0";
         type union {
           type uint32;
           type string {
             pattern "<.*>|$.*";
           }
         }
       }
     }
     output {
       container jdaf-clients-statistics {
         uses jdaf-clients-statistics-block;
       }
     }
   }
   rpc get-jdaf-route-clients {
     description "Show JDAF client information";
     junos:command "show jdaf service route clients";
     output {
       container jdaf-clients {
         uses jdaf-clients-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping jdaf-server-statistics-block {
     leaf srv-conn-requests {
       type uint32;
       description "Service connection requests received";
     }
     leaf srv-conn-accepts {
       type uint32;
       description "Service connections accpeted";
     }
     leaf srv-conn-rejects {
       type uint32;
       description "Service connections rejected";
     }
     leaf srv-conn-errors {
       type uint32;
       description "Service connection errors";
     }
     list listener-statistics {
       leaf routing-instance-id {
         type uint32;
         description "Routing instance id";
       }
       leaf srv-accepts {
         type uint32;
         description "Accepts on server socket";
       }
       leaf srv-accept-errors {
         type uint32;
         description "Errors while accept on server socket";
       }
     }
   }
   grouping jdaf-clients-statistics-block {
     leaf error-msg {
       type string;
       description "Error message";
     }
     list jdaf-client-statistics {
       description "Client statistics";
       leaf client {
         type uint32;
         description "Service Client Id";
       }
       leaf rx-bytes {
         type uint32;
         description "Bytes received";
       }
       leaf tx-bytes {
         type uint32;
         description "Bytes transmitted";
       }
       leaf tx-queued {
         type uint32;
         description "Bytes queued for transmission";
       }
       leaf rx-msgs {
         type uint32;
         description "Messages received";
       }
       leaf rx-errors {
         type uint32;
         description "Errors on receive";
       }
       leaf tx-msgs {
         type uint32;
         description "Messages transmitted";
       }
       leaf tx-errors {
         type uint32;
         description "Errors on transmission";
       }
       list rpc-statistics {
         leaf name {
           type string;
           description "Message name";
         }
         leaf requests {
           type uint32;
           description "Service requests received";
         }
         leaf successes {
           type uint32;
           description "Service requests succeeded";
         }
         leaf failures {
           type uint32;
           description "Service requests failed";
         }
       }
       list notify-statistics {
         leaf name {
           type string;
           description "Message name";
         }
         leaf sent {
           type uint32;
           description "Service notifications sent";
         }
       }
     }
   }
   grouping jdaf-clients-block {
     list jdaf-client {
       description "Client information";
       leaf client {
         type uint32;
         description "Service Client Id";
       }
       leaf state {
         type string;
         description "State of the client";
       }
       leaf url {
         type string;
         description "Client URL";
       }
     }
   }
 }
