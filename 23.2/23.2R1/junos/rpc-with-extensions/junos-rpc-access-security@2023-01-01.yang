/*
 * Copyright (c) 2023 Juniper Networks, Inc.
 * All rights reserved.
 */
 module junos-rpc-access-security {
   namespace "http://yang.juniper.net/junos/rpc/access-security";

   prefix access-security;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for access-security command(s)";

   revision 2023-01-01 {
     description "Junos: 23.2R1.14";
   }

   rpc get-as-router-advertisement-statistics {
     description "Show outer advertisement guard statistics";
     junos:command "show access-security router-advertisement-guard statistics";
     output {
       container as-rag-information {
         uses as-rag-information-block;
       }
     }
   }
   rpc get-as-router-advertisement-interface {
     description "Name of interface for which to show statistics";
     junos:command "show access-security router-advertisement-guard statistics interface";
     input {
       leaf interface-name {
         description "Name of interface";
         junos:cli-feature "nokeyword";
         type union {
           type jt:interface-name;
           type string {
             pattern "<.*>|$.*";
           }
         }
         mandatory true;
       }
     }
   }
   rpc get-as-ra-state {
     description "Show Router Advertisement State Information";
     junos:command "show access-security router-advertisement-guard state";
     output {
       choice output_c {
         case output-tag {
           leaf output {
             type string;
           }
         }
         case multichassis-tag {
           anyxml multi-routing-engine-results;
         }
       }
     }
   }
   rpc get-as-router-advertisement-interface-state {
     description "Show Router Advertisement state on an interface";
     junos:command "show access-security router-advertisement-guard state interface";
     input {
       leaf interface-name {
         description "Name of interface";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc get-slaac-binding-all {
     description "Show binding information";
     junos:command "show access-security slaac-snooping binding";
     output {
       container slaac-binding-all {
         uses slaac-binding-all-block;
       }
     }
   }
   rpc get-slaac-interface-bindings {
     description "Show binding information of an interface";
     junos:command "show access-security slaac-snooping binding interface";
     input {
       leaf interface-name {
         description "Interface-name";
         junos:cli-feature "nokeyword";
         type union {
           type jt:interface-name;
           type string {
             pattern "<.*>|$.*";
           }
         }
         mandatory true;
       }
     }
     output {
       container slaac-binding-all {
         uses slaac-binding-all-block;
       }
     }
   }
   rpc get-slaac-vlan-bindings {
     description "Show vlan information";
     junos:command "show access-security slaac-snooping binding vlan";
     input {
       leaf vlan-name {
         description "Display binding information of a specified VLAN";
         junos:cli-feature "nokeyword";
         type string;
         mandatory true;
       }
       choice routing-logical {
         case routing-instance {
           leaf routing-instance {
             description "Name of routing instance";
             type string;
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       container slaac-binding-all {
         uses slaac-binding-all-block;
       }
     }
   }
   rpc get-slaac-statistics-all {
     description "Show statistics";
     junos:command "show access-security slaac-snooping statistics";
     output {
       container slaac-statistics-all {
         uses slaac-statistics-all-block;
       }
     }
   }
   rpc get-slaac-interface-statistics {
     description "Show interface statistics";
     junos:command "show access-security slaac-snooping statistics interface";
     input {
       leaf interface-name {
         description "Name of interface";
         junos:cli-feature "nokeyword";
         type union {
           type jt:interface-name;
           type string {
             pattern "<.*>|$.*";
           }
         }
         mandatory true;
       }
     }
     output {
       container slaac-statistics-all {
         uses slaac-statistics-all-block;
       }
     }
   }
   rpc get-slaac-state {
     description "Show state information";
     junos:command "show access-security slaac-snooping state";
     output {
       container slaac-state-information {
         uses slaac-state-information-block;
       }
     }
   }
   rpc get-slaac-interface-state {
     description "Show interface state";
     junos:command "show access-security slaac-snooping state interface";
     input {
       leaf interface-name {
         description "Show state on an interface";
         junos:cli-feature "nokeyword";
         type union {
           type jt:interface-name;
           type string {
             pattern "<.*>|$.*";
           }
         }
         mandatory true;
       }
     }
     output {
       container slaac-state-information {
         uses slaac-state-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping as-rag-information-block {
     container rag-summary {
       list rag-entry {
         leaf ifd-name {
           type string;
           description "Interface name on which DAI stat collected";
         }
         leaf packets {
           type uint64;
         }
         leaf pass {
           type uint64;
         }
         leaf fail {
           type uint64;
         }
       }
     }
   }
   grouping slaac-binding-all-block {
     container slaac-snooping-entries {
       list slaac-snooping-entry {
         leaf ipv6-address {
           type jt:ipv6addr;
         }
         leaf hw-address {
           type string;
         }
         leaf vlan-name {
           type string;
         }
         leaf lease-expiry {
           type int32;
         }
         leaf state {
           type string;
         }
         leaf intf-name {
           type string;
         }
       }
     }
   }
   grouping slaac-statistics-all-block {
     leaf dad-request-queued {
       type int32;
     }
     leaf confirmed-bindings {
       type int32;
     }
     leaf declined-bindings {
       type int32;
     }
     leaf conflicting-dad-entries {
       type int32;
     }
     leaf auto-dad-queued {
       type int32;
     }
     leaf auto-dad-pkt-tx {
       type int32;
     }
     leaf request-on-trusted-port {
       type int32;
     }
     leaf total-dropped {
       type int32;
     }
     leaf bad-read {
       type int32;
     }
     leaf no-cfg {
       type int32;
     }
     leaf no-vlan {
       type int32;
     }
     leaf no-ifl {
       type int32;
     }
   }
   grouping slaac-state-information-block {
     leaf slaac-intf-name {
       type string;
     }
     leaf slaac-intf-state {
       type string;
     }
   }
 }
