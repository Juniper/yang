/*
 * Copyright (c) 2023 Juniper Networks, Inc.
 * All rights reserved.
 */
 module junos-rpc-analytics {
   namespace "http://yang.juniper.net/junos/rpc/analytics";

   prefix analytics;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for analytics command(s)";

   revision 2023-01-01 {
     description "Junos: 23.2R1.14";
   }

   rpc get-analytics-information {
     description "Show Analytics information";
     junos:command "show analytics";
     output {
       container analytics {
         uses analytics-block;
       }
     }
   }
   rpc get-analytics-queue-statistics {
     description "Show queue statistics";
     junos:command "show analytics queue-statistics";
   }
   rpc get-analytics-queue-statistics-interface {
     description "Show queue-statistics for an interface";
     junos:command "show analytics queue-statistics interface";
     input {
       leaf interface-name {
         description "Interface name";
         junos:cli-feature "nokeyword";
         type string;
         mandatory true;
       }
     }
   }
   rpc get-analytics-traffic-statistics {
     description "Show traffic statistics";
     junos:command "show analytics traffic-statistics";
   }
   rpc get-analytics-traffic-statistics-interface {
     description "Show traffic-statistics for an interface";
     junos:command "show analytics traffic-statistics interface";
     input {
       leaf interface-name {
         description "Interface name";
         junos:cli-feature "nokeyword";
         type string;
         mandatory true;
       }
     }
   }
   rpc get-analytics-status {
     description "Show analytics status";
     junos:command "show analytics status";
   }
   rpc get-analytics-status-global {
     description "Show analytics global status";
     junos:command "show analytics status global";
   }
   rpc get-analytics-status-interface {
     description "Show analytics status for an interface";
     junos:command "show analytics status interface";
     input {
       leaf interface-name {
         description "Interface name";
         junos:cli-feature "nokeyword";
         type string;
         mandatory true;
       }
     }
   }
   rpc get-analytics-configuration {
     description "Show analytics configuration";
     junos:command "show analytics configuration";
   }
   rpc get-analytics-configuration-global {
     description "Show analytics global configuration";
     junos:command "show analytics configuration global";
   }
   rpc get-analytics-configuration-interface {
     description "Show analytics configuration for an interface";
     junos:command "show analytics configuration interface";
     input {
       leaf interface-name {
         description "Interface name";
         junos:cli-feature "nokeyword";
         type string;
         mandatory true;
       }
     }
   }
   rpc get-analytics-collector {
     description "Show collector status";
     junos:command "show analytics collector";
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping analytics-block {
     container analytics-current-time {
       leaf an-timeval {
         type string;
         description "Time value";
       }
     }
     container analytics-interface-summary {
       leaf an-interface-name {
         type string;
         description "Interface name";
       }
       leaf an-ts-status {
         type string;
         description "Traffic statistics status";
       }
       leaf an-qs-status {
         type string;
         description "Queue statistics status";
       }
       leaf an-depth-threshold-high {
         type string;
         description "Depth threshold high";
       }
       leaf an-depth-threshold-low {
         type string;
         description "Depth threshold low";
       }
       leaf an-latency-threshold-high {
         type string;
         description "Latency threshold high";
       }
       leaf an-latency-threshold-low {
         type string;
         description "Latency threshold low";
       }
     }
     container analytics-interface {
       leaf an-interface-name {
         type string;
         description "Interface name";
       }
       leaf an-ts-status {
         type string;
         description "Traffic statistics status";
       }
       leaf an-ts-interval {
         type uint32;
         description "Traffic statistics interval";
       }
       leaf an-qs-status {
         type string;
         description "Queue statistics status";
       }
       leaf an-qs-interval {
         type uint32;
         description "Queue statistics interval";
       }
       leaf an-depth-threshold-high {
         type string;
         description "Depth threshold high";
       }
       leaf an-depth-threshold-low {
         type string;
         description "Depth threshold low";
       }
       leaf an-latency-threshold-high {
         type string;
         description "Latency threshold high";
       }
       leaf an-latency-threshold-low {
         type string;
         description "Latency threshold low";
       }
     }
     container analytics-global {
       leaf an-ts-status {
         type string;
         description "Traffic statistics status";
       }
       leaf an-ts-interval {
         type uint32;
         description "Traffic statistics interval";
       }
       leaf an-qs-status {
         type string;
         description "Queue statistics status";
       }
       leaf an-qs-interval {
         type uint32;
         description "Queue statistics interval";
       }
       leaf an-depth-threshold-high {
         type string;
         description "Depth threshold high";
       }
       leaf an-depth-threshold-low {
         type string;
         description "Depth threshold low";
       }
       leaf an-latency-threshold-high {
         type string;
         description "Latency threshold high";
       }
       leaf an-latency-threshold-low {
         type string;
         description "Latency threshold low";
       }
     }
     container analytics-status {
     }
     container analytics-configuration {
     }
     container analytics-queue-statistics {
       leaf an-timeval {
         type string;
         description "Time value";
       }
       leaf an-interface-name {
         type string;
         description "Interface name";
       }
       leaf an-queue-depth {
         type uint32;
       }
       leaf an-latency {
         type uint32;
       }
       container analytics-queue-statistics-summary {
         leaf an-interface-name {
           type string;
           description "Interface name";
         }
         leaf an-queue-depth-1sec {
           type uint32;
         }
         leaf an-queue-depth-5sec {
           type uint32;
         }
         leaf an-queue-depth-60sec {
           type uint32;
         }
         leaf an-queue-depth-5min {
           type uint32;
         }
         leaf an-queue-depth-1hr {
           type uint32;
         }
       }
     }
     container analytics-traffic-statistics {
       leaf an-timeval {
         type string;
         description "Time value";
       }
       leaf an-interface-name {
         type string;
         description "Interface name";
       }
       leaf an-rx-total-bytes {
         type uint32;
       }
       leaf an-tx-total-bytes {
         type uint32;
       }
       leaf an-rx-total-packets {
         type uint32;
       }
       leaf an-tx-total-packets {
         type uint32;
       }
       leaf an-rx-unicast-packets {
         type uint32;
       }
       leaf an-tx-unicast-packets {
         type uint32;
       }
       leaf an-rx-multicast-packets {
         type uint32;
       }
       leaf an-tx-multicast-packets {
         type uint32;
       }
       leaf an-rx-broadcast-packets {
         type uint32;
       }
       leaf an-tx-broadcast-packets {
         type uint32;
       }
       leaf an-rx-bytes-per-second {
         type uint32;
       }
       leaf an-tx-bytes-per-second {
         type uint32;
       }
       leaf an-rx-bits-per-second {
         type uint32;
       }
       leaf an-tx-bits-per-second {
         type uint32;
       }
       leaf an-rx-packets-per-second {
         type uint32;
       }
       leaf an-tx-packets-per-second {
         type uint32;
       }
       leaf an-rx-crc-errors {
         type uint32;
       }
       leaf an-tx-crc-errors {
         type uint32;
       }
       leaf an-rx-packets-dropped {
         type uint32;
       }
       leaf an-tx-packets-dropped {
         type uint32;
       }
     }
     container analytics-collector {
       leaf an-server-address {
         type jt:ipaddr;
       }
       leaf an-server-port {
         type uint32;
       }
       leaf an-server-transport {
         type uint32;
       }
       leaf an-stream-format {
         type string;
       }
       leaf an-connection-state {
         type string;
       }
       leaf an-msg-sent {
         type uint32;
       }
     }
   }
 }
