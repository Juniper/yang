/*
 * Copyright (c) 2023 Juniper Networks, Inc.
 * All rights reserved.
 */
 module junos-es-rpc-path-computation-client {
   namespace "http://yang.juniper.net/junos-es/rpc/path-computation-client";

   prefix path-computation-client;

   import junos-common-types {
     prefix jt;
     revision-date 2023-01-01;
   }

   organization "Juniper Networks, Inc.";

   contact "yang-support@juniper.net";

   description "Junos RPC YANG module for path-computation-client command(s)";

   revision 2023-01-01 {
     description "Junos: 23.2R1.14";
   }

   rpc get-path-computation-client-statistics {
     description "Get path computation client statistics";
     input {
       leaf count {
         type enumeration {
           enum "all" {
             description "Show statistics of all available PCEs";
           }
         }
       }
       leaf verbosity_level {
         default "brief";
         type enumeration {
           enum "brief" {
             description "Display brief output (default)";
           }
           enum "detail" {
             description "Display detailed output";
           }
         }
       }
     }
     output {
       container path-computation-client-statistics {
         uses path-computation-client-statistics-block;
       }
     }
   }
   rpc get-path-computation-client-active-pce {
     description "Show information about current active PCE";
     input {
       leaf verbosity_level {
         default "brief";
         type enumeration {
           enum "brief" {
             description "Display brief output (default)";
           }
           enum "detail" {
             description "Display detailed output";
           }
         }
       }
     }
     output {
       container path-computation-client-statistics {
         uses path-computation-client-statistics-block;
       }
     }
   }
   rpc get-path-computation-client-lsp {
     description "Show information about known Labels Switched Paths";
     input {
       leaf regex {
         description "Regular expression for LSP names to match";
         type string;
       }
     }
     output {
       container path-computation-client-lsp {
         uses path-computation-client-lsp-block;
       }
     }
   }
   rpc get-path-computation-client-lsp-extensive {
     description "Show extensive information about known Label Switched Paths";
     input {
       leaf regexs {
         description "Regular expression for extensive LSP names to match";
         type string;
       }
     }
     output {
       container path-computation-client-lsp-extensive {
         uses path-computation-client-lsp-extensive-block;
       }
     }
   }
   rpc get-path-computation-client-lsp-p2mp {
     description "Show information about known P2MP Labels Switched Paths";
     input {
       leaf regex {
         description "Regular expression for P2MP LSP names to match";
         type string;
       }
     }
     output {
       container path-computation-client-lsp-p2mp {
         uses path-computation-client-lsp-p2mp-block;
       }
     }
   }
   rpc get-path-computation-client-lsp-traffic-steering {
     description "Show information about LSP traffic steering";
     output {
       container path-computation-client-lsp-traffic-steering {
         uses path-computation-client-lsp-traffic-steering-block;
       }
     }
   }
   rpc get-path-computation-client-lsp-retry-pending {
     description "Show information about LSPs for which delegation will be re-tried";
   }
   rpc get-path-computation-client-status {
     description "Show status of Path Computation Client";
     output {
       container path-computation-client-status {
         uses path-computation-client-status-block;
       }
     }
   }
   rpc get-path-computation-client-status-extensive {
     description "Show extensive status of Path Computation Client";
     output {
       container path-computation-client-status-extensive {
         uses path-computation-client-status-extensive-block;
       }
     }
   }
   rpc get-path-computation-client-objects-class {
     description "Show path computation client protocol objects values";
   }
   rpc get-path-computation-client-tlv-types {
     description "Show path computation client tlv types information";
     output {
       container path-computation-client-tlv-types {
         uses path-computation-client-tlv-types-block;
       }
     }
   }
   rpc get-path-computation-client-rfc-8231-compliance {
     description "Show path computation client rfc 8231 compliance";
     output {
       container path-computation-client-rfc-8231-compliance {
         uses path-computation-client-rfc-8231-compliance-block;
       }
     }
   }
   rpc get-path-computation-client-traffic-steering {
     description "Show information about PCE traffic steering";
     output {
       container path-computation-client-traffic-steering {
         uses path-computation-client-traffic-steering-block;
       }
     }
   }
   rpc get-path-computation-client-traffic-steering-pce {
     description "Show information of PCE traffic steering";
     input {
       leaf pce-id {
         description "PCE ID from configuration";
         type string;
         mandatory true;
       }
       leaf get-path-computation-client-traffic-steering-fs {
         description "Show information of FS-ID";
         type union {
           type uint32;
           type string {
             pattern "<.*>|$.*";
           }
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping path-computation-client-statistics-block {
     list pce-statistics-response {
       leaf pce-id {
         type string;
         description "PCE IP/NAME1";
       }
       container pce-statistics-common {
         leaf pce-ip {
           type jt:ipaddr;
           description "IP address of PCE";
         }
         leaf local-ip {
           type jt:ipaddr;
           description "Local IP address";
         }
         leaf pce-priority {
           type int32;
           description "Priority";
         }
         leaf pce-connection {
           type string;
           description "Connection state (e.g. connecting/connected, disconnected)";
         }
         leaf pce-status {
           type string;
           description "A small but friendly message";
         }
         leaf pce-session-type {
           type string;
           description "A small but friendly message";
         }
         leaf pce-session-state {
           type string;
           description "A small but friendly message";
         }
         leaf lsp-provisioning {
           type string;
           description "LSP provisioning ability";
         }
         leaf pcupdate-empty-ero-action {
           type string;
           description "Action to be taken on empty ero in pcupdate";
         }
         leaf p2mp-lsp-reporting {
           type string;
           description "P2MP LSP reporting ability";
         }
         leaf p2mp-lsp-update {
           type string;
           description "P2MP LSP updating ability";
         }
         leaf p2mp-lsp-init {
           type string;
           description "P2MP LSP initiating ability";
         }
         leaf srv6-session-cap {
           type string;
           description "PCEP session SRv6 capable";
         }
         leaf lsp-cleanup-timer {
           type uint32;
           description "Negotiated LSP cleanup timer";
         }
         leaf pce-mastership {
           type string;
           description "PCE-mastership (main or backup)";
         }
         leaf pce-traffic-steering {
           type string;
           description "PCE Traffic Steering (FlowSpec)";
         }
         leaf pce-multipath {
           type string;
           description "PCE-multipath status";
         }
         leaf pcc-multipath {
           type string;
           description "PCC-multipath status";
         }
         leaf pce-max-unknown-msgs {
           type int32;
           description "A small but friendly message";
         }
         leaf keepalives-received {
           type int32;
           description "Keepalives received total";
         }
         leaf keepalives-sent {
           type int32;
           description "Keepalives sent total";
         }
         leaf dead-timer {
           type int32;
           description "DeadTimer value (0 meaning disconnection from PCE)";
         }
         leaf active-state-current {
           type int32;
           description "Elapsed time as main PCE current session";
         }
         leaf active-state-total {
           type int32;
           description "Elapsed time as main PCE total";
         }
         leaf unknown-ratio {
           type int32;
           description "Current unknown messages per minute ratio";
         }
         leaf session-failures {
           type int32;
           description "Active state duration";
         }
         leaf corrupted-messages {
           type int32;
           description "Active state duration";
         }
         leaf delegation-timeout-set {
           type int32;
           description "Delegation timeout set";
         }
         leaf delegation-timeout {
           type int32;
           description "Delegation timeout";
         }
         leaf delegation-failures {
           type int32;
           description "Delegation failures counter";
         }
         leaf connection-active {
           type int32;
           description "Time of PCE connection active";
         }
         leaf connection-down {
           type int32;
           description "Time of PCE connection down";
         }
         leaf pcc-tls-enabled {
           type string;
           description "PCC TLS Status";
         }
         leaf pce-tls-enabled {
           type string;
           description "PCE TLS Status";
         }
         leaf session-tls-enabled {
           type string;
           description "Session TLS status";
         }
         leaf failed-computations {
           type int32;
           description "Active state duration";
         }
         leaf replies-timedout {
           type int32;
           description "Active state duration";
         }
       }
       container pce-statistics-counters {
         list pce-counter {
           leaf counter-name {
             type string;
             description "Counter name";
           }
           leaf count-total {
             type int32;
             description "Total count";
           }
           leaf count-5min {
             type int32;
             description "Last 5 minutes";
           }
           leaf count-hour {
             type int32;
             description "Last hour";
           }
         }
       }
       container pce-statistics-timers {
         list pce-timer {
           leaf timer-name {
             type string;
             description "Timer name";
           }
           leaf timer-keepalive {
             type int32;
             description "Keepalive timer";
           }
           leaf timer-dead {
             type int32;
             description "Dead timer";
           }
           leaf timer-lsp-cleanup {
             type uint32;
             description "LSP cleanup timer";
           }
         }
       }
       container pce-statistics-errors {
         list pce-error {
           leaf pce-error-name {
             type string;
           }
           list pce-error-entry {
             leaf pce-error-type {
               type int32;
             }
             leaf pce-error-value {
               type int32;
             }
             leaf pce-error-count {
               type int32;
             }
           }
         }
       }
       container pce-statistics-last-error {
         list pce-last-error {
           leaf pce-last-error-name {
             type string;
           }
           list pce-last-error-entry {
             leaf pce-error-type {
               type int32;
             }
             leaf pce-error-value {
               type int32;
             }
           }
         }
       }
       container pce-statistics-pcupdate-empty-ero-action {
         leaf stats-send-err {
           type int32;
           description "Sent err in response to Pcupdate containing empty-ero";
         }
         leaf stats-tear-down-path {
           type int32;
           description "Teared down path in response to Pcupdate containing empty-ero";
         }
         leaf stats-routing-decision {
           type int32;
           description "Path decision is taken by MPLS component in response to Pcupdate containing empty-ero";
         }
         leaf stats-routing-decision_failed {
           type int32;
           description "Path decision is taken by MPLS component in response to Pcupdate containing empty-ero, but operation failed";
         }
       }
     }
     container pccd-error-response {
       leaf pccd-error-message {
         type string;
         description "Operation error message";
       }
       leaf pccd-error-code {
         type int32;
         description "Operation error code";
       }
     }
   }
   grouping path-computation-client-lsp-block {
     list pcc-lsp-entry {
       leaf lsp-name {
         type string;
       }
       leaf lsp-status {
         type string;
       }
       leaf lsp-id {
         type int32;
       }
       leaf lsp-type {
         type string;
       }
       leaf lsp-controller {
         type string;
       }
       leaf lsp-setup-type {
         type string;
       }
       leaf template-name {
         type string;
       }
     }
   }
   grouping path-computation-client-lsp-extensive-block {
     list pcc-lsp-ext-entry {
       leaf lsp-name {
         type string;
       }
       leaf lsp-path-name {
         type string;
       }
       leaf lsp-src {
         type string;
       }
       leaf lsp-dst {
         type string;
       }
       leaf lsp-setup-type {
         type string;
       }
       leaf lsp-state {
         type string;
       }
       leaf lsp-active-path {
         type string;
       }
       leaf lsp-link {
         type string;
       }
       leaf lsp-type {
         type string;
       }
       leaf lsp-p2mp {
         type string;
       }
       leaf lsp-cspf {
         type string;
       }
       leaf lsp-ctrlr {
         type string;
       }
       leaf lsp-template {
         type string;
       }
       leaf lsp-plsp-id {
         type int32;
       }
       leaf lsp-id {
         type int32;
       }
       leaf lsp-rsvp-err {
         type int32;
       }
       leaf lsp-abw {
         type int32;
       }
       leaf lsp-rro {
         type string;
       }
       leaf lsp-pce-ero {
         type string;
       }
       leaf lsp-rpd-ero {
         type string;
       }
       leaf lsp-conf-ero {
         type string;
       }
       leaf lsp-intended-bw {
         type int32;
       }
       leaf lsp-actual-bw {
         type int32;
       }
       leaf lsp-route-metric {
         type uint32;
       }
       leaf lsp-mapped-flowspec {
         type string;
       }
       leaf lsp-local-protection {
         type string;
       }
       leaf lsp-last-recv {
         type string;
       }
       leaf lsp-last-sent {
         type string;
       }
       leaf lsp-pcu-recv {
         type string;
       }
       leaf lsp-last-err {
         type string;
       }
       leaf lsp-last-err-reason {
         type string;
       }
       container lsp-path-binding-entry {
         leaf binding-type {
           type string;
         }
         leaf binding-value {
           type uint32;
         }
       }
       container lsp-intended-metric-entry {
         leaf metric-type {
           type string;
         }
         leaf metric-bound {
           type uint32;
         }
         leaf metric-optimization {
           type string;
         }
       }
       container lsp-actual-metric-entry {
         leaf metric-type {
           type string;
         }
         leaf metric-computed-value {
           type uint32;
         }
       }
       list lsp-admin-groups {
         leaf lsp-exclude-any {
           type int32;
         }
         leaf lsp-include-any {
           type int32;
         }
         leaf lsp-include-all {
           type int32;
         }
       }
       list lsp-priority {
         leaf lsp-setup-prio {
           type int32;
         }
         leaf lsp-hold-prio {
           type int32;
         }
       }
       container lsp-association-entry {
         leaf association-type {
           type string;
         }
         leaf association-id {
           type int32;
         }
         leaf association-source {
           type string;
         }
         container srpag-association-entry {
           leaf sr-color {
             type uint32;
           }
           leaf sr-endpoint {
             type string;
           }
           leaf sr-proto-origin {
             type string;
           }
           leaf sr-originator-asn {
             type uint32;
           }
           leaf sr-originator-ip {
             type string;
           }
           leaf sr-discriminator {
             type uint32;
           }
           leaf sr-preference {
             type uint32;
           }
         }
       }
       container path-computation-client-lsp-ext-fs {
         list pcc-traffic-steering-entry {
           leaf fs-id {
             type uint32;
           }
           leaf route-distinguisher {
             type string;
           }
           leaf source-prefix {
             type string;
           }
           leaf multi-group-prefix {
             type string;
           }
           leaf fs-state {
             type string;
           }
         }
       }
     }
   }
   grouping path-computation-client-lsp-p2mp-block {
     list pcc-p2mp-lsp-section {
       leaf p2mp-name {
         type string;
       }
       container pcc-p2mp-lsp {
         list pcc-p2mp-lsp-entry {
           leaf lsp-name-p2mp {
             type string;
           }
           leaf lsp-status-p2mp {
             type string;
           }
           leaf lsp-id-p2mp {
             type int32;
           }
           leaf lsp-type-p2mp {
             type string;
           }
           leaf lsp-controller-p2mp {
             type string;
           }
           leaf lsp-setup-type-p2mp {
             type string;
           }
           leaf template-name-p2mp {
             type string;
           }
         }
       }
     }
   }
   grouping path-computation-client-lsp-traffic-steering-block {
     list pcc-lsp-traffic-steering-entry {
       leaf lsp-name {
         type string;
       }
       leaf lsp-p2mp {
         type string;
       }
       leaf lsp-plsp-id {
         type int32;
       }
       leaf pce-id {
         type string;
         description "PCE IP/NAME1";
       }
       leaf lsp-fs-id {
         type string;
       }
     }
   }
   grouping path-computation-client-status-block {
     container pcc-status-sessions {
       list pcc-status-sessions-entry {
         leaf session-name {
           type string;
         }
         leaf session-type {
           type string;
         }
         leaf session-provisioning {
           type string;
         }
         leaf session-status {
           type string;
         }
         leaf session-up {
           type int32;
         }
       }
       container pccd-error-response {
         leaf pccd-error-message {
           type string;
           description "Operation error message";
         }
         leaf pccd-error-code {
           type int32;
           description "Operation error code";
         }
       }
     }
     container pcc-status-lsp {
       list pcc-status-lsp-entry {
         leaf lsp-total {
           type uint32;
         }
         leaf lsp-static {
           type uint32;
         }
         leaf lsp-external {
           type uint32;
         }
         leaf lsp-provisioned-counter {
           type uint32;
         }
         leaf lsp-provisioned-limit {
           type uint32;
         }
         leaf lsp-orphan {
           type uint32;
         }
         leaf lsp-static-p2p {
           type uint32;
         }
         leaf lsp-static-p2mp {
           type uint32;
         }
         leaf lsp-external-p2p {
           type uint32;
         }
         leaf lsp-external-p2mp {
           type uint32;
         }
       }
       container pccd-error-response {
         leaf pccd-error-message {
           type string;
           description "Operation error message";
         }
         leaf pccd-error-code {
           type int32;
           description "Operation error code";
         }
       }
     }
     container pcc-status-pce {
       list pcc-status-pce-entry {
         leaf pce-name {
           type string;
         }
         leaf pce-delegated {
           type uint32;
         }
         leaf pce-provisioned {
           type uint32;
         }
         leaf pce-auth-keychain {
           type string;
         }
         leaf pce-auth-algorithm {
           type string;
         }
         leaf pce-auth-key {
           type string;
         }
       }
       container pccd-error-response {
         leaf pccd-error-message {
           type string;
           description "Operation error message";
         }
         leaf pccd-error-code {
           type int32;
           description "Operation error code";
         }
       }
     }
   }
   grouping path-computation-client-status-extensive-block {
     container pcc-status-sessions {
       list pcc-status-sessions-entry {
         leaf session-name {
           type string;
         }
         leaf session-type {
           type string;
         }
         leaf session-provisioning {
           type string;
         }
         leaf session-status {
           type string;
         }
         leaf session-up {
           type int32;
         }
       }
       container pccd-error-response {
         leaf pccd-error-message {
           type string;
           description "Operation error message";
         }
         leaf pccd-error-code {
           type int32;
           description "Operation error code";
         }
       }
     }
     container pcc-status-lsp-extensive {
       list pcc-status-lsp-entry-ext {
         leaf lsp-total-ext {
           type uint32;
         }
         leaf lsp-static-ext {
           type uint32;
         }
         leaf lsp-static-p2p-ext {
           type uint32;
         }
         leaf lsp-static-p2p-primary-ext {
           type uint32;
         }
         leaf lsp-static-p2p-bypass-ext {
           type uint32;
         }
         leaf lsp-static-p2mp-ext {
           type uint32;
         }
         leaf lsp-static-p2mp-trees-ext {
           type uint32;
         }
         leaf lsp-external-ext {
           type uint32;
         }
         leaf lsp-external-p2p-ext {
           type uint32;
         }
         leaf lsp-external-p2p-primary-ext {
           type uint32;
         }
         leaf lsp-external-p2p-bypass-ext {
           type uint32;
         }
         leaf lsp-external-p2mp-ext {
           type uint32;
         }
         leaf lsp-external-p2mp-trees-ext {
           type uint32;
         }
         leaf lsp-provisioned-counter-ext {
           type uint32;
         }
         leaf lsp-provisioned-limit-ext {
           type uint32;
         }
         leaf lsp-provisioned-counter-p2p-ext {
           type uint32;
         }
         leaf lsp-provisioned-counter-p2p-primary-ext {
           type uint32;
         }
         leaf lsp-provisioned-counter-p2p-bypass-ext {
           type uint32;
         }
         leaf lsp-provisioned-counter-p2mp-ext {
           type uint32;
         }
         leaf lsp-provisioned-counter-p2mp-trees-ext {
           type uint32;
         }
         leaf lsp-orphan-ext {
           type uint32;
         }
       }
       container pccd-error-response {
         leaf pccd-error-message {
           type string;
           description "Operation error message";
         }
         leaf pccd-error-code {
           type int32;
           description "Operation error code";
         }
       }
     }
     container pcc-status-pce-extensive {
       list pcc-status-pce-entry-ext {
         leaf pce-name-ext {
           type string;
         }
         leaf pce-delegated-ext {
           type uint32;
         }
         leaf pce-delegated-p2p-ext {
           type uint32;
         }
         leaf pce-delegated-p2p-primary-ext {
           type uint32;
         }
         leaf pce-delegated-p2p-bypass-ext {
           type uint32;
         }
         leaf pce-delegated-p2mp-ext {
           type uint32;
         }
         leaf pce-delegated-p2mp-trees-ext {
           type uint32;
         }
         leaf pce-provisioned-ext {
           type uint32;
         }
         leaf pce-provisioned-p2p-ext {
           type uint32;
         }
         leaf pce-provisioned-p2p-primary-ext {
           type uint32;
         }
         leaf pce-provisioned-p2p-bypass-ext {
           type uint32;
         }
         leaf pce-provisioned-p2mp-ext {
           type uint32;
         }
         leaf pce-provisioned-p2mp-trees-ext {
           type uint32;
         }
         leaf pce-auth-keychain-ext {
           type string;
         }
         leaf pce-auth-algorithm-ext {
           type string;
         }
         leaf pce-auth-key-ext {
           type string;
         }
       }
       container pccd-error-response {
         leaf pccd-error-message {
           type string;
           description "Operation error message";
         }
         leaf pccd-error-code {
           type int32;
           description "Operation error code";
         }
       }
     }
     container pcc-status-nsr-extensive {
       leaf re-mode {
         type string;
       }
       leaf conn-status {
         type string;
       }
       leaf repl-status {
         type string;
       }
     }
   }
   grouping path-computation-client-tlv-types-block {
     container pcc-tlv-types-entry {
       leaf tlv-no-path-vector {
         type uint32;
       }
       leaf tlv-overloaded-duration {
         type uint32;
       }
       leaf tlv-req-missing {
         type uint32;
       }
       leaf tlv-stateful-pce-capability {
         type uint32;
       }
       leaf tlv-lsp-symbolic-name {
         type uint32;
       }
       leaf tlv-ipv4-lsp-identifiers {
         type uint32;
       }
       leaf tlv-ipv6-lsp-identifiers {
         type uint32;
       }
       leaf tlv-lsp-update-error-code {
         type uint32;
       }
       leaf tlv-ipv4-rsvp-error-spec {
         type uint32;
       }
       leaf tlv-ipv6-rsvp-error-spec {
         type uint32;
       }
       leaf tlv-lsp-db-version {
         type uint32;
       }
       leaf tlv-node-identifier {
         type uint32;
       }
       leaf tlv-sr-pce-capability {
         type uint32;
       }
       leaf tlv-path-setup-type {
         type uint32;
       }
       leaf tlv-te-path-binding {
         type uint32;
       }
       leaf tlv-vendor-lsp-qualifier {
         type uint32;
       }
       leaf tlv-vendor-lsp-bw {
         type uint32;
       }
       leaf tlv-ipv4-p2mp-lsp-identifiers {
         type uint32;
       }
       leaf tlv-ipv6-p2mp-lsp-identifiers {
         type uint32;
       }
       leaf tlv-vendor-p2mp-tree-name {
         type uint32;
       }
       leaf tlv-lsp-cleanup {
         type uint32;
       }
       leaf tlv-vendor-local-cspf {
         type uint32;
       }
       leaf tlv-sr-candidate-path-identifier {
         type uint32;
       }
       leaf tlv-sr-preference {
         type uint32;
       }
       leaf tlv-multipath-capability {
         type uint32;
       }
       leaf tlv-path-attribute-weight {
         type uint32;
       }
       leaf tlv-path-attribute-backup {
         type uint32;
       }
       leaf tlv-path-attribute-color {
         type uint32;
       }
       leaf tlv-pce-flowspec-capability {
         type uint32;
       }
       leaf tlv-flowspec-flowfilter {
         type uint32;
       }
       leaf tlv-vendor-route-metric {
         type uint32;
       }
     }
   }
   grouping path-computation-client-rfc-8231-compliance-block {
     leaf rfc-status {
       type string;
     }
   }
   grouping path-computation-client-traffic-steering-block {
     list pcc-traffic-steering-section {
       leaf pce-id {
         type string;
         description "PCE IP/NAME1";
       }
       container pcc-traffic-steering {
         list pcc-traffic-steering-entry {
           leaf fs-id {
             type uint32;
           }
           leaf speaker-id {
             type string;
           }
           leaf afi {
             type string;
           }
           leaf flow-type {
             type string;
           }
           leaf lsp-p2mp {
             type string;
           }
           leaf lsp {
             type string;
           }
           leaf route-distinguisher {
             type string;
           }
           leaf source-prefix {
             type string;
           }
           leaf multi-group-prefix {
             type string;
           }
           leaf fs-state {
             type string;
           }
           leaf dest-prefix {
             type string;
           }
         }
       }
     }
   }
 }
