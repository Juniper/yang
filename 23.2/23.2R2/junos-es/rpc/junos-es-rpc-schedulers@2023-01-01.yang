/*
 * Copyright (c) 2024 Juniper Networks, Inc.
 * All rights reserved.
 */
 module junos-es-rpc-schedulers {
   namespace "http://yang.juniper.net/junos-es/rpc/schedulers";

   prefix schedulers;

   import junos-common-types {
     prefix jt;
     revision-date 2023-01-01;
   }

   organization "Juniper Networks, Inc.";

   contact "yang-support@juniper.net";

   description "Junos RPC YANG module for schedulers command(s)";

   revision 2023-01-01 {
     description "Junos: 23.2R2.21";
   }

   rpc get-schedulers {
     description "Show the information on one or more schedulers";
     input {
       uses command-forwarding;
       leaf scheduler-name {
         description "Name of the scheduler";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       container schedulers {
         uses schedulers-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping schedulers-block {
     list schedulers-logical-system {
       description "Logical system";
       leaf name {
         type string;
         description "Logical system name";
       }
     }
     list scheduler {
       description "Information about a scheduler";
       leaf scheduler-name {
         type string;
         description "Name of the scheduler";
       }
       leaf scheduler-state {
         type string;
         description "Operational state of the scheduler";
       }
       leaf scheduler-next-activation-date-time {
         type string;
         description "Time and date for the next activation of the scheduler";
       }
       leaf scheduler-next-deactivation-date-time {
         type string;
         description "Time and date for the next deactivation of the scheduler";
       }
       leaf scheduler-description {
         type string;
         description "Description of the scheduler";
       }
     }
   }
 }
