/*
 * Copyright (c) 2024 Juniper Networks, Inc.
 * All rights reserved.
 */
 module junos-nfx-rpc-help {
   namespace "http://yang.juniper.net/junos-nfx/rpc/help";

   prefix help;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for help command(s)";

   revision 2023-01-01 {
     description "Junos: 23.2R2.21";
   }

   rpc get-syslog-tag-information {
     description "System log error messages";
     junos:command "help syslog";
     input {
       leaf syslog-tag {
         description "System log tag or regular expression";
         junos:cli-feature "nokeyword";
         type jt:regular-expression;
       }
     }
     output {
       container syslog-tag-information-list {
         uses syslog-tag-information-list-block;
       }
     }
   }
   rpc get-syslog-facility-information {
     description "System facility messages";
     junos:command "help syslog facility";
     input {
       leaf facility-name {
         description "Facility name or regular expression";
         junos:cli-feature "nokeyword";
         type jt:regular-expression;
       }
     }
   }
   rpc get-cli-tip {
     description "Tip about using the CLI";
     junos:command "help tip cli";
     input {
       leaf number {
         junos:cli-feature "nokeyword";
         type union {
           type uint32;
           type string {
             pattern "<.*>|$.*";
           }
         }
       }
     }
     output {
       container tip {
         uses tip-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping syslog-tag-information-list-block {
     container syslog-tag-information {
       description "Syslog message help information";
       container syslog-tag {
         leaf name {
           type string;
           description "Syslog message tag name";
         }
         leaf help {
           type string;
           description "Syslog message short help information";
         }
         leaf facility {
           type string;
           description "Facility of this event";
         }
         leaf message {
           type string;
           description "Syslog message text";
         }
         leaf description {
           type string;
           description "Syslog message extended help information";
         }
         leaf type {
           type string;
           description "Syslog message type";
         }
         leaf severity {
           type string;
           description "Syslog message severity";
         }
         leaf deprecated {
           type string;
           description "Syslog message deprecated JUNOS version";
         }
         leaf-list cause {
           type string;
           description "Cause of this syslog message";
         }
         leaf-list action {
           type string;
           description "Action to be taken in response to this syslog message";
         }
       }
     }
   }
   grouping tip-block {
     leaf content {
       type string;
     }
   }
 }
