/*
 * Copyright (c) 2024 Juniper Networks, Inc.
 * All rights reserved.
 */
 module junos-nfx-rpc-evpn {
   namespace "http://yang.juniper.net/junos-nfx/rpc/evpn";

   prefix evpn;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for evpn command(s)";

   revision 2023-01-01 {
     description "Junos: 23.2R2.21";
   }

   rpc get-evpn-instance-information {
     description "Show EVPN instance information";
     junos:command "show evpn instance";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance-name {
         description "Name of EVPN instance";
         junos:cli-feature "nokeyword";
         default "all";
         type string;
       }
       leaf neighbor {
         description "Address of EVPN neighbor";
         type jt:ipaddr;
       }
       leaf esi {
         description "Ethernet segment identifier";
         type string;
       }
       leaf verbosity {
         junos:cli-feature "nokeyword";
         type enumeration {
           enum "brief" {
             description "Display brief version of output";
           }
           enum "extensive" {
             description "Display extensive version of output";
           }
           enum "designated-forwarder" {
             description "Display only designated forwarder information";
           }
           enum "backup-forwarder" {
             description "Display only backup forwarder information";
           }
           enum "esi-info" {
             description "Display only ESI information";
           }
           enum "neighbor-info" {
             description "Display only neighbor information";
           }
           enum "bridge-domains" {
             description "Display detailed bridge-domain information";
           }
         }
       }
       leaf get-evpn-instance-dci-information {
         description "Display dci information";
         type empty;
       }
     }
     output {
       container evpn-instance-information {
         uses evpn-instance-information-block;
       }
     }
   }
   rpc get-evpn-database-information {
     description "Show EVPN internal MAC database";
     junos:command "show evpn database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf mac-address {
         description "Display a specifc MAC address";
         type jt:mac-addr;
       }
       leaf instance {
         description "Display MAC address from a specific EVPN instance";
         type string;
       }
       leaf l2-domain-id {
         description "Display MAC address with a specific VLAN or VNI or ISID";
         type union {
           type string {
             pattern "<.*>|$.*";
           }
           type int32 {
             range "1 .. 16777214";
           }
         }
       }
       leaf l3-context {
         description "Display MAC address from a specific EVPN l3 Context";
         type string;
       }
       leaf esi {
         description "Ethernet segment identifier";
         type string;
       }
       choice origin-choice {
         case neighbor {
           leaf neighbor {
             description "Display MAC address learned from a specific neighbor";
             type jt:ipaddr;
           }
         }
         case interface {
           leaf interface {
             description "Display MAC address learned from a specific interface";
             type string;
           }
         }
         case origin {
           leaf origin {
             description "Display MAC address with a specific origin";
             type enumeration {
               enum "local" {
                 description "Display local MAC address";
               }
               enum "remote" {
                 description "Display remote MAC address";
               }
               enum "dci-remote" {
                 description "Display MAC addresses received from DCI";
               }
             }
           }
         }
       }
       leaf state {
         description "Display MAC address with a specific state";
         type enumeration {
           enum "default-gateway" {
             description "Display default gateway MAC address";
           }
           enum "static" {
             description "Display static MAC address";
           }
           enum "pinned" {
             description "Display pinned MAC address";
           }
           enum "duplicate" {
             description "Display duplicate MAC address";
           }
           enum "dci-adv" {
             description "Display MAC advertised to DCI";
           }
           enum "dc-adv" {
             description "Display MAC advertised to DC";
           }
         }
       }
       leaf verbosity {
         junos:cli-feature "nokeyword";
         type enumeration {
           enum "extensive" {
             description "Display extensive version of output";
           }
         }
       }
     }
     output {
       container evpn-database-information {
         uses evpn-database-information-block;
       }
     }
   }
   rpc get-evpn-p2mp-information {
     description "Show EVPN p2mp information";
     junos:command "show evpn p2mp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Display p2mp information for a specific EVPN instance";
         type string;
       }
       leaf verbosity {
         junos:cli-feature "nokeyword";
         type enumeration {
           enum "extensive" {
             description "Display extensive version of output";
           }
         }
       }
     }
     output {
       container evpn-p2mp-information {
         uses evpn-p2mp-information-block;
       }
     }
   }
   rpc get-evpn-l3-context-information {
     description "Show EVPN L3 context information";
     junos:command "show evpn l3-context";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf l3-context-name {
         description "Name of EVPN L3 context";
         junos:cli-feature "nokeyword";
         default "all";
         type string;
       }
       leaf verbosity {
         junos:cli-feature "nokeyword";
         type enumeration {
           enum "brief" {
             description "Display brief version of output";
           }
           enum "extensive" {
             description "Display extensive version of output";
           }
         }
       }
     }
     output {
       container evpn-l3-context-information {
         uses evpn-l3-context-information-block;
       }
     }
   }
   rpc get-evpn-ip-prefix-database-information {
     description "Show EVPN internal IP prefix database";
     junos:command "show evpn ip-prefix-database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf l3-context {
         description "Display IP prefix from a specific EVPN L3 context";
         type string;
       }
       leaf family {
         description "Display IP prefix with a specific address family";
         type enumeration {
           enum "inet" {
             description "Display IPv4 prefixes";
           }
           enum "inet6" {
             description "Display IPv6 prefixes";
           }
         }
       }
       leaf direction {
         description "Display IP prefix with a specific import/export direction";
         type enumeration {
           enum "imported" {
             description "Display imported EVPN IP prefixes";
           }
           enum "exported" {
             description "Display exported IP prefixes";
           }
         }
       }
       leaf prefix {
         description "Display a specifc IP prefix";
         type jt:ipprefix;
       }
       leaf ethernet-tag {
         description "Display IP prefix with a specific ethernet tag";
         type union {
           type string {
             pattern "<.*>|$.*";
           }
           type int32 {
             range "0 .. 16777214";
           }
         }
       }
       leaf gateway {
         description "Display IP prefix with a specific overlay gateway address";
         type jt:ipaddr;
       }
       leaf esi {
         description "Display IP prefix with a specific overlay ESI";
         type string;
       }
       leaf nexthop {
         description "Display IP prefix with a specific underlay nexthop";
         type jt:ipaddr;
       }
       leaf verbosity {
         junos:cli-feature "nokeyword";
         type enumeration {
           enum "extensive" {
             description "Display extensive version of output";
           }
         }
       }
     }
     output {
       container evpn-ip-prefix-database-information {
         uses evpn-ip-prefix-database-information-block;
       }
     }
   }
   rpc get-evpn-multicast-snooping-status {
     description "Show general status";
     junos:command "show evpn multicast-snooping status";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf verbosity {
         junos:cli-feature "nokeyword";
         type enumeration {
           enum "extensive" {
             description "Display extensive version of output";
           }
         }
       }
     }
   }
   rpc get-evpn-multicast-snooping-ar-nexthops-data {
     description "Show next-hops information";
     junos:command "show evpn multicast-snooping assisted-replication next-hops";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf index {
         description "Display for a specific nexthop id";
         type union {
           type uint32;
           type string {
             pattern "<.*>|$.*";
           }
         }
       }
     }
     output {
       container evpn-multicast-snooping-ar-nexthops-data {
         uses evpn-multicast-snooping-ar-nexthops-data-block;
       }
     }
   }
   rpc get-evpn-multicast-snooping-ar-mh-peers-data {
     description "Show multi-homed peers";
     junos:command "show evpn multicast-snooping assisted-replication multihomed-peers";
     input {
       leaf instance {
         description "Display for a specific EVPN instance";
         type string;
       }
       leaf verbosity {
         junos:cli-feature "nokeyword";
         type enumeration {
           enum "extensive" {
             description "Display extensive version of output";
           }
         }
       }
     }
     output {
       container evpn-multicast-snooping-ar-mh-peers-data {
         uses evpn-multicast-snooping-ar-mh-peers-data-block;
       }
     }
   }
   rpc get-evpn-multicast-snooping-ar-replicators-data {
     description "Show replicators";
     junos:command "show evpn multicast-snooping assisted-replication replicators";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
     }
     output {
       container evpn-multicast-snooping-ar-replicators-data {
         uses evpn-multicast-snooping-ar-replicators-data-block;
       }
     }
   }
   rpc get-evpn-multicast-next-hops-information {
     description "Show EVPN multicast-snooping nexthops table";
     junos:command "show evpn multicast-snooping next-hops";
     input {
       leaf verbosity_level {
         junos:cli-feature "nokeyword";
         default "brief";
         type enumeration {
           enum "terse" {
             description "Display terse output";
           }
           enum "brief" {
             description "Display brief output (default)";
           }
           enum "detail" {
             description "Display detailed output";
           }
         }
       }
       leaf identifier {
         description "ID of next hop";
         junos:cli-feature "nokeyword";
         type union {
           type uint32;
           type string {
             pattern "<.*>|$.*";
           }
         }
       }
     }
     output {
       container multicast-next-hops-information {
         uses multicast-next-hops-information-block;
       }
     }
   }
   rpc get-evpn-igmp-snooping-proxy-information {
     description "Show EVPN igmp snooping proxy";
     junos:command "show evpn igmp-snooping proxy";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf group {
         description "Group address";
         type jt:ipaddr;
       }
       leaf verbosity {
         junos:cli-feature "nokeyword";
         type enumeration {
           enum "extensive" {
             description "Display extensive version of output";
           }
         }
       }
     }
     output {
       container evpn-igmp-snooping-information {
         uses evpn-igmp-snooping-information-block;
       }
     }
   }
   rpc get-evpn-igmp-snooping-database-information {
     description "Show EVPN igmp snooping database";
     junos:command "show evpn igmp-snooping database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf esi {
         description "Ethernet segment identifier";
         type string;
       }
       leaf group {
         description "Group address";
         type jt:ipaddr;
       }
       leaf interface {
         description "Display for a specific interface";
         type string;
       }
       leaf verbosity {
         junos:cli-feature "nokeyword";
         type enumeration {
           enum "extensive" {
             description "Display extensive version of output";
           }
         }
       }
     }
     output {
       container evpn-igmp-snooping-information {
         uses evpn-igmp-snooping-information-block;
       }
     }
   }
   rpc get-evpn-mld-snooping-proxy-information {
     description "Show EVPN mld snooping proxy";
     junos:command "show evpn mld-snooping proxy";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf group {
         description "Group address";
         type jt:ipaddr;
       }
       leaf verbosity {
         junos:cli-feature "nokeyword";
         type enumeration {
           enum "extensive" {
             description "Display extensive version of output";
           }
         }
       }
     }
     output {
       container evpn-mld-snooping-information {
         uses evpn-mld-snooping-information-block;
       }
     }
   }
   rpc get-evpn-mld-snooping-database-information {
     description "Show EVPN mld snooping database";
     junos:command "show evpn mld-snooping database";
     input {
       leaf instance {
         description "Display for a specific EVPN instance";
         type string;
       }
       leaf l2-domain-id {
         description "Display for a specific VLAN or VNI or ISID";
         type union {
           type string {
             pattern "<.*>|$.*";
           }
           type int32 {
             range "1 .. 16777214";
           }
         }
       }
       leaf esi {
         description "Ethernet segment identifier";
         type string;
       }
       leaf group {
         description "Group address";
         type jt:ipaddr;
       }
       leaf interface {
         description "Display for a specific interface";
         type string;
       }
       leaf verbosity {
         junos:cli-feature "nokeyword";
         type enumeration {
           enum "extensive" {
             description "Display extensive version of output";
           }
         }
       }
     }
     output {
       container evpn-mld-snooping-information {
         uses evpn-mld-snooping-information-block;
       }
     }
   }
   rpc get-evpn-oism-information {
     description "Show EVPN OISM information";
     junos:command "show evpn oism";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf l3-context {
         description "Name of specific EVPN L3 context";
         type string;
       }
       leaf verbosity {
         junos:cli-feature "nokeyword";
         type enumeration {
           enum "brief" {
             description "Display brief version of output";
           }
           enum "extensive" {
             description "Display extensive version of output";
           }
         }
       }
     }
     output {
       container evpn-oism-information {
         uses evpn-oism-information-block;
       }
     }
   }
   rpc get-evpn-oism-spmsi-ad-information {
     description "Show EVPN OISM spmsi-ad";
     junos:command "show evpn oism spmsi-ad";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf group {
         description "Group address";
         type jt:ipaddr;
       }
       leaf source {
         description "Source address";
         type jt:ipaddr;
       }
       leaf l3-context {
         description "Name of specific EVPN L3 context";
         type string;
       }
       leaf verbosity {
         junos:cli-feature "nokeyword";
         type enumeration {
           enum "extensive" {
             description "Display extensive version of output";
           }
         }
       }
     }
     output {
       container evpn-oism-spmsi-ad-information {
         uses evpn-oism-spmsi-ad-information-block;
       }
     }
   }
   rpc get-evpn-vpws-information {
     description "Show EVPN VPWS instance information";
     junos:command "show evpn vpws-instance";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance-name {
         description "Name of EVPN VPWS instance";
         junos:cli-feature "nokeyword";
         default "all";
         type string;
       }
     }
     output {
       container evpn-vpws-information {
         uses evpn-vpws-information-block;
       }
     }
   }
   rpc get-evpn-mac-ip-table {
     description "Show IP table for EVPN instances";
     junos:command "show evpn mac-ip-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf address {
         description "MAC address";
         junos:cli-feature "nokeyword";
         default "all";
         type jt:mac-addr;
       }
       leaf ip-addr {
         description "IP address";
         type jt:ipaddr;
       }
       leaf show-choice {
         junos:cli-feature "nokeyword";
         default "brief";
         type enumeration {
           enum "detail" {
             description "Display detailed output";
           }
           enum "brief" {
             description "Display brief output";
           }
           enum "extensive" {
             description "Display extensive output";
           }
           enum "count" {
             description "Display count only";
           }
           enum "summary" {
             description "Display summary output";
           }
           enum "sync-check" {
             description "Sync check";
           }
         }
       }
     }
     output {
       container l2ald-rtb-mac-ip-db {
         uses l2ald-rtb-mac-ip-db-block;
       }
     }
   }
   rpc get-evpn-mac-ip-table-kernel {
     description "Entries present in kernel";
     junos:command "show evpn mac-ip-table kernel";
     input {
       leaf verbosity {
         junos:cli-feature "nokeyword";
         default "brief";
         type enumeration {
           enum "detail" {
             description "Display detailed output";
           }
           enum "brief" {
             description "Display brief output";
           }
           enum "extensive" {
             description "Display extensive output";
           }
           enum "summary" {
             description "Display summary output";
           }
         }
       }
     }
     output {
       container l2ald-rtb-mac-ip-kernel-db {
         uses l2ald-rtb-mac-ip-kernel-db-block;
       }
     }
   }
   rpc get-evpn-mac-ip-table-kernel-diff {
     description "Entries not present in both l2ald and kernel";
     junos:command "show evpn mac-ip-table kernel differences";
     input {
       leaf bd-id {
         description "Display IP address under particular bd-id";
         type string;
       }
     }
     output {
       container l2ald-rtb-mac-ip-kernel-db {
         uses l2ald-rtb-mac-ip-kernel-db-block;
       }
     }
   }
   rpc get-evpn-mac-ip-table-kernel-ipv4 {
     description "IPv4 entries present in kernel";
     junos:command "show evpn mac-ip-table kernel ipv4";
     input {
       leaf bd-id {
         description "Display IP address under particular bd-id";
         type string;
       }
       leaf ipv4-addr {
         description "Display kernel information for ip";
         junos:cli-feature "nokeyword";
         default "all";
         type jt:ipv4addr;
       }
       leaf verbosity {
         junos:cli-feature "nokeyword";
         default "brief";
         type enumeration {
           enum "detail" {
             description "Display detailed output";
           }
           enum "brief" {
             description "Display brief output";
           }
           enum "extensive" {
             description "Display extensive output";
           }
           enum "summary" {
             description "Display summary output";
           }
         }
       }
     }
     output {
       container l2ald-rtb-mac-ip-kernel-db {
         uses l2ald-rtb-mac-ip-kernel-db-block;
       }
     }
   }
   rpc get-evpn-mac-ip-table-kernel-ipv6 {
     description "IPv6 entries present in kernel";
     junos:command "show evpn mac-ip-table kernel ipv6";
     input {
       leaf bd-id {
         description "Display IP address under particular bd-id";
         type string;
       }
       leaf ipv6-addr {
         description "Display kernel information for ip";
         junos:cli-feature "nokeyword";
         default "all";
         type jt:ipv6addr;
       }
       leaf verbosity {
         junos:cli-feature "nokeyword";
         default "brief";
         type enumeration {
           enum "detail" {
             description "Display detailed output";
           }
           enum "brief" {
             description "Display brief output";
           }
           enum "extensive" {
             description "Display extensive output";
           }
           enum "summary" {
             description "Display summary output";
           }
         }
       }
     }
     output {
       container l2ald-rtb-mac-ip-kernel-db {
         uses l2ald-rtb-mac-ip-kernel-db-block;
       }
     }
   }
   rpc get-evpn-mac-ip-table-dest-route {
     description "Destination Route entries present in kernel";
     junos:command "show evpn mac-ip-table destination-route";
     output {
       container l2ald-rtb-mac-ip-kernel-db {
         uses l2ald-rtb-mac-ip-kernel-db-block;
       }
     }
   }
   rpc get-evpn-mac-ip-table-dest-route-diff {
     description "Destination Route Entries not present in both l2ald and kernel";
     junos:command "show evpn mac-ip-table destination-route differences";
     input {
       leaf bd-id {
         description "Display IP address under particular bd-id";
         type string;
       }
     }
     output {
       container l2ald-rtb-mac-ip-kernel-db {
         uses l2ald-rtb-mac-ip-kernel-db-block;
       }
     }
   }
   rpc get-evpn-mac-table {
     description "Show media access control table";
     junos:command "show evpn mac-table";
     input {
       leaf instance {
         description "Display information for a specified vpls";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Display MAC address learned on a specified VLAN";
         type string;
       }
       leaf isid {
         description "Display Information for specified ISID or all ISID(s)";
         type string;
       }
       leaf address {
         description "MAC address";
         junos:cli-feature "nokeyword";
         default "all";
         type jt:mac-addr;
       }
       leaf show-choice {
         junos:cli-feature "nokeyword";
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "sync-check" {
             description "Sync check";
           }
           enum "summary" {
             description "Display summary output";
           }
         }
       }
     }
     output {
       container l2ald-rtb-macdb {
         uses l2ald-rtb-macdb-block;
       }
     }
   }
   rpc get-evpn-interface-mac-table {
     description "Display MAC table for a specified interface";
     junos:command "show evpn mac-table interface";
     input {
       choice interface-choice {
         case interface-name {
           leaf interface-name {
             description "Name of interface for which to display table";
             junos:cli-feature "nokeyword";
             type string;
           }
         }
         case all {
           leaf all {
             description "Display MAC table for all the interfaces";
             type empty;
           }
         }
       }
       leaf show-choice {
         junos:cli-feature "nokeyword";
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "sync-check" {
             description "Sync check";
           }
           enum "summary" {
             description "Display summary output";
           }
         }
       }
     }
     output {
       container l2ald-interface-macdb {
         uses l2ald-interface-macdb-block;
       }
     }
   }
   rpc get-evpn-flood-information {
     description "Show EVPN flooding information";
     junos:command "show evpn flood";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf verbosity {
         junos:cli-feature "nokeyword";
         default "detail";
         type enumeration {
           enum "detail" {
             description "Display detailed output";
           }
           enum "brief" {
             description "Display brief output";
           }
           enum "extensive" {
             description "Display extensive output";
           }
         }
       }
     }
     output {
       container l2ald-vpls-flood-instance {
         uses l2ald-vpls-flood-instance-block;
       }
     }
   }
   rpc get-evpn-ce-flood-route-information {
     description "Show customer edge flood route";
     junos:command "show evpn flood route ce-flood";
     input {
       leaf interface {
         description "Interface for which to show CE flood route";
         type union {
           type jt:interface-unit;
           type string {
             pattern "<.*>|$.*";
           }
         }
         mandatory true;
       }
     }
     output {
       container l2ald-vpls-flood-route-information {
         uses l2ald-vpls-flood-route-information-block;
       }
     }
   }
   rpc get-evpn-all-flood-route-information {
     description "Show route for flooding traffic from customer edge router";
     junos:command "show evpn flood route all-flood";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         uses l2ald-vpls-flood-route-information-block;
       }
     }
   }
   rpc get-evpn-all-ce-flood-route-information {
     description "Show route for flooding traffic to all CE routers";
     junos:command "show evpn flood route all-ce-flood";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         uses l2ald-vpls-flood-route-information-block;
       }
     }
   }
   rpc get-evpn-re-flood-route-information {
     description "Show route for Routing Engine flooding to all interfaces";
     junos:command "show evpn flood route re-flood";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         uses l2ald-vpls-flood-route-information-block;
       }
     }
   }
   rpc get-evpn-mlp-flood-route-information {
     description "Show route for flooding traffic to MAC learning chips";
     junos:command "show evpn flood route mlp-flood";
     input {
       leaf logical-system {
         description "Name of logical system";
         type string {
           junos:posix-pattern "^[a-zA-Z0-9_-]{1,63}$";
           junos:pattern-message "Logical-system name is a string consisting of up to 63 letters, numbers, dashes and underscores";
         }
       }
       leaf instance {
         description "Display information for a specified vpls";
         type string;
         mandatory true;
       }
     }
     output {
       container l2ald-vpls-flood-route-information {
         uses l2ald-vpls-flood-route-information-block;
       }
     }
   }
   rpc get-evpn-alt-root-flood-route-information {
     description "Show STP alt-root flooding route used for interface";
     junos:command "show evpn flood route alt-root-flood";
     input {
       leaf interface {
         description "Interface for which to show alternate-root flooding route";
         type union {
           type jt:interface-unit;
           type string {
             pattern "<.*>|$.*";
           }
         }
         mandatory true;
       }
     }
     output {
       container l2ald-vpls-flood-route-information {
         uses l2ald-vpls-flood-route-information-block;
       }
     }
   }
   rpc get-evpn-event-queue-information {
     description "Show queue of pending EVPN flood events";
     junos:command "show evpn flood event-queue";
     output {
       container l2ald-vpls-flood-event-queue {
         uses l2ald-vpls-flood-event-queue-block;
       }
     }
   }
   rpc get-evpn-arp-table {
     description "Show ARP entries associated with MACs learned";
     junos:command "show evpn arp-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         junos:cli-feature "nokeyword";
         default "all";
         type jt:mac-addr;
       }
       leaf show-choice {
         junos:cli-feature "nokeyword";
         default "brief";
         type enumeration {
           enum "detail" {
             description "Display detailed output";
           }
           enum "brief" {
             description "Display brief output";
           }
           enum "extensive" {
             description "Display extensive output";
           }
           enum "count" {
             description "Display count only";
           }
         }
       }
     }
     output {
       container l2rtb-evpn-arp-db {
         uses l2rtb-evpn-arp-db-block;
       }
     }
   }
   rpc get-evpn-nd-table {
     description "Show ND entries associated with MACs learned";
     junos:command "show evpn nd-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         junos:cli-feature "nokeyword";
         default "all";
         type jt:mac-addr;
       }
       leaf show-choice {
         junos:cli-feature "nokeyword";
         default "brief";
         type enumeration {
           enum "detail" {
             description "Display detailed output";
           }
           enum "brief" {
             description "Display brief output";
           }
           enum "extensive" {
             description "Display extensive output";
           }
           enum "count" {
             description "Display count only";
           }
         }
       }
     }
     output {
       container l2rtb-evpn-nd-db {
         uses l2rtb-evpn-nd-db-block;
       }
     }
   }
   rpc get-evpn-peer-gateway-mac {
     description "Show MAC addresses installed as gateway MACs";
     junos:command "show evpn peer-gateway-macs";
     input {
       leaf instance {
         description "Display information for a specified instance";
         default "all";
         type string;
       }
       leaf address {
         description "MAC address";
         junos:cli-feature "nokeyword";
         default "all";
         type jt:mac-addr;
       }
     }
     output {
       container l2rtb-peer-gateway-macdb {
         uses l2rtb-peer-gateway-macdb-block;
       }
     }
   }
   rpc get-evpn-statistics-information {
     description "Show EVPN statistics";
     junos:command "show evpn statistics";
     input {
       leaf instance {
         description "Name of EVPN instance";
         type string;
         mandatory true;
       }
     }
     output {
       container evpn-statistics-information {
         uses evpn-statistics-information-block;
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping evpn-instance-information-block {
     container evpn-instance {
       leaf evpn-instance-name {
         type string;
       }
       leaf route-distinguisher {
         type string;
       }
       leaf evpn-encap-type {
         type string;
       }
       leaf evpn-instance-vlan-id {
         type string;
       }
       leaf evpn-instance-pbb-evpn-core {
         type string;
       }
       leaf evpn-instance-pbb-optimize-multicast {
         type string;
       }
       leaf evpn-instance-control-word {
         type string;
       }
       leaf evpn-instance-flow-label {
         type string;
       }
       leaf evpn-instance-flow-label-static {
         type string;
       }
       leaf evpn-service-interface-type {
         type string;
       }
       leaf evpn-instance-mac-label {
         type string;
       }
       leaf evpn-instance-mc-label {
         type string;
       }
       leaf evpn-etree-leaf-label {
         type string;
       }
       leaf evpn-instance-df-preference {
         type string;
       }
       leaf duplicate-mac-detection-threshold {
         type int32;
       }
       leaf duplicate-mac-detection-window {
         type int32;
       }
       leaf duplicate-mac-auto-recovery-time {
         type int32;
       }
       leaf num-local-macs {
         type int32;
       }
       leaf num-remote-macs {
         type int32;
       }
       leaf local-interfaces {
         type int32;
       }
       leaf local-interfaces-up {
         type int32;
       }
       leaf num-protect-interfaces {
         type int32;
       }
       leaf irb-interfaces {
         type int32;
       }
       leaf irb-interfaces-up {
         type int32;
       }
       leaf num-bridge-domains {
         type int32;
       }
       leaf num-bundle-bridge-domains {
         type int32;
       }
       leaf evpn-num-neighbors {
         type int32;
       }
       leaf evpn-num-esi {
         type int32;
       }
       leaf evpn-router-id {
         type jt:ipaddr;
       }
       leaf evpn-source-vtep-ipaddr {
         type jt:ipaddr;
       }
       leaf evpn-migration {
         type string;
       }
       leaf evpn-smet-forwarding {
         type string;
       }
       leaf esi-df-election-algorithm {
         type string;
       }
       leaf esi-granularity {
         type string;
       }
       leaf esi-lacp-oos-on-ndf {
         type string;
       }
       container mac-database-status-table {
         leaf local-macs {
           type int32;
         }
         leaf remote-macs {
           type int32;
         }
         leaf local-mac-ips {
           type int32;
         }
         leaf remote-mac-ips {
           type int32;
         }
         leaf local-default-gateway-macs {
           type int32;
         }
         leaf remote-default-gateway-macs {
           type int32;
         }
       }
       container evpn-interconn-info {
         leaf route-distinguisher {
           type string;
         }
         leaf interconn-vrf-import {
           type string;
         }
         leaf interconn-vrf-export {
           type string;
         }
         leaf interconn-vrf-import-target {
           type string;
         }
         leaf interconn-vrf-export-target {
           type string;
         }
         leaf evpn-interconn-mac-label {
           type string;
         }
         leaf evpn-interconn-mc-label {
           type string;
         }
       }
       container evpn-interconn-route-stats-table {
         leaf evpn-interconn-num-local-ad-routes {
           type int32;
         }
         leaf evpn-interconn-num-local-im-routes {
           type int32;
         }
         leaf evpn-interconn-num-local-mac-routes {
           type int32;
         }
         leaf evpn-interconn-num-local-mac-ip-routes {
           type int32;
         }
         leaf evpn-interconn-num-local-es-routes {
           type int32;
         }
         leaf evpn-interconn-num-local-sg-proxy-routes {
           type int32;
         }
       }
       container evpn-interface-status-table {
         list evpn-interface {
           leaf evpn-interface-name {
             type string;
           }
           leaf evpn-interface-esi {
             type string;
           }
           leaf evpn-interface-mode {
             type string;
           }
           leaf evpn-interface-status {
             type string;
           }
           leaf evpn-interface-etree-role {
             type string;
           }
         }
       }
       container irb-interface-status-table {
         list irb-interface {
           leaf irb-interface-name {
             type string;
           }
           leaf irb-interface-vlan-id {
             type string;
           }
           leaf irb-interface-vni-id {
             type string;
           }
           leaf irb-interface-status {
             type string;
           }
           leaf irb-interface-l3-context {
             type string;
           }
         }
       }
       container evpn-protect-interface-status-table {
         list evpn-protect-interface {
           leaf evpn-primary-interface-name {
             type string;
           }
           leaf evpn-protect-interface-name {
             type string;
           }
           leaf evpn-protect-interface-status {
             type string;
           }
         }
       }
       container bridge-domain-status-table {
         list bridge-domain {
           leaf vlan-id {
             type int32;
           }
           leaf domain-id {
             type int32;
           }
           leaf interfaces {
             type int32;
           }
           leaf interfaces-up {
             type int32;
           }
           leaf-list irb-interface {
             type string;
           }
           leaf mode {
             type string;
           }
           leaf mac-sync-status {
             type string;
           }
           leaf sg-sync-status {
             type string;
           }
           leaf v6-sg-sync-status {
             type string;
           }
         }
       }
       container bridge-domain-status-table-detailed {
         list bridge-domain-detailed {
           leaf vlan-id {
             type int32;
           }
           leaf domain-id {
             type int32;
           }
           leaf trans-domain-id {
             type int32;
           }
           leaf inclusive-multicast-label {
             type int32;
           }
           leaf bd-mac-label {
             type int32;
           }
           leaf inclusive-multicast-core-nh {
             type int32;
           }
           leaf v6-inclusive-multicast-core-nh {
             type int32;
           }
         }
       }
       container bundle-bridge-domain-status-table {
         list bundle-bridge-domain {
           leaf domain-name {
             type string;
           }
           leaf num-isids {
             type int32;
           }
           leaf mode {
             type string;
           }
           leaf mac-sync-status {
             type string;
           }
         }
       }
       list evpn-neighbor {
         leaf evpn-neighbor-address {
           type jt:ipaddr;
         }
         container evpn-neighbor-route-information {
           leaf evpn-neighbor-address {
             type jt:ipaddr;
           }
           leaf evpn-num-mac-routes {
             type int32;
           }
           leaf evpn-num-mac-ip-routes {
             type int32;
           }
           leaf evpn-num-ethernet-autodiscovery-routes {
             type int32;
           }
           leaf evpn-num-inclusive-multicast-routes {
             type int32;
           }
           leaf evpn-num-ethernet-segment-routes {
             type int32;
           }
           leaf evpn-peer-leaf-label {
             type int32;
           }
           leaf evpn-peer-dci {
             type string;
           }
           leaf evpn-flow-label {
             type string;
           }
         }
       }
       list evpn-esi {
         leaf evpn-esi-value {
           type string;
         }
         leaf evpn-interconn-esi {
           type string;
         }
         leaf evpn-esi-status {
           type string;
         }
         leaf evpn-esi-min-isid {
           type int32;
         }
         leaf evpn-esi-mac-label {
           type int32;
         }
         leaf evpn-esi-aliasing-label {
           type int32;
         }
         leaf evpn-esi-split-horizon-label {
           type int32;
         }
         container evpn-esi-local-intf-information {
           leaf evpn-esi-local-intf-name {
             type string;
           }
           leaf evpn-esi-local-intf-status {
             type string;
           }
         }
         container evpn-esi-event-history-information {
           list evpn-esi-event-history-database {
             leaf evpn-esi-event-entry {
               type string;
             }
           }
         }
         container evpn-esi-remote-pe-information {
           leaf evpn-esi-num-remote-pe {
             type int32;
           }
           list evpn-esi-remote-pe {
             leaf evpn-esi-remote-pe-ipaddr {
               type jt:ipaddr;
             }
             leaf evpn-esi-remote-mac-label {
               type int32;
             }
             leaf evpn-esi-remote-aliasing-label {
               type int32;
             }
             leaf evpn-esi-remote-pe-mode {
               type string;
             }
           }
         }
         container evpn-esi-df-information {
           leaf esi-df-election-algorithm {
             type string;
           }
           leaf esi-granularity {
             type string;
           }
           leaf esi-lacp-oos-on-ndf {
             type string;
           }
           leaf esi-designated-forwarder {
             type string;
           }
           leaf esi-df-preference {
             type int32;
           }
           leaf esi-df-no-preempt {
             type string;
           }
           leaf-list esi-backup-forwarder {
             type string;
           }
           leaf-list esi-backup-df-preference {
             type int32;
           }
           leaf-list esi-backup-df-no-preempt {
             type string;
           }
           leaf esi-last-df-update-timestamp {
             type string;
           }
         }
         list evpn-esi-bd-remote-pe-information {
           leaf evpn-esi-bd-vlan {
             type int32;
           }
           leaf evpn-esi-bd-status {
             type string;
           }
           leaf evpn-esi-bd-num-remote-pe {
             type int32;
           }
           list evpn-esi-bd-remote-pe {
             leaf evpn-esi-bd-remote-pe-ipaddr {
               type jt:ipaddr;
             }
             leaf evpn-esi-bd-remote-mac-label {
               type int32;
             }
             leaf evpn-esi-bd-remote-aliasing-label {
               type int32;
             }
             leaf evpn-esi-bd-remote-pe-mode {
               type string;
             }
           }
         }
       }
     }
   }
   grouping evpn-database-information-block {
     list evpn-database-instance {
       leaf instance-name {
         type string;
       }
       list mac-entry {
         leaf vlan-id {
           type int32;
         }
         leaf vni-id {
           type int32;
         }
         leaf isid-val {
           type int32;
         }
         leaf mac-address {
           type jt:mac-addr;
         }
         leaf active-source {
           type string;
         }
         leaf active-source-timestamp {
           type string;
         }
         leaf ip-address {
           type jt:ipaddr;
         }
         container mobility-history {
           list mobility-event {
             leaf event-time {
               type string;
             }
             leaf event-type {
               type string;
             }
             leaf event-source {
               type string;
             }
             leaf event-seq-num {
               type int32;
             }
           }
         }
         list mac-source {
           leaf source-name {
             type string;
           }
           leaf source-rank {
             type string;
           }
           leaf source-status {
             type string;
           }
           leaf source-local-origin {
             type string;
           }
           leaf source-remote-origin {
             type string;
           }
           leaf source-remote-mac-label {
             type int32;
           }
           leaf source-local-mac-label {
             type int32;
           }
           leaf source-remote-state {
             type string;
           }
           leaf source-mobility-seq-num {
             type int32;
           }
           leaf source-mobility-min-origin-address {
             type jt:ipaddr;
           }
           leaf source-timestamp {
             type string;
           }
           leaf source-timestamp-value {
             type int32;
           }
           leaf source-state {
             type string;
           }
           leaf source-mac-adv-route-status {
             type string;
           }
           leaf interconn-adv-route-status {
             type string;
           }
           list mac-ip-information {
             leaf address {
               type jt:ipaddr;
             }
             leaf mac-ip-flags {
               type string;
             }
             leaf l3-route {
               type string;
             }
             leaf l3-context {
               type string;
             }
             leaf-list irb-interface {
               type string;
             }
             leaf interconn-adv-route-status {
               type string;
             }
             list mac-ip-origin {
               leaf ip-local-origin {
                 type string;
               }
               leaf ip-remote-origin {
                 type jt:ipaddr;
               }
               leaf ip-remote-state {
                 type string;
               }
             }
             list mac-ip-peer-symm-route {
               leaf symm-remote-pe {
                 type jt:ipaddr;
               }
               leaf symm-l3-route {
                 type string;
               }
               list mac-ip-peer-symm-route-l3-context {
                 leaf symm-l3-context {
                   type string;
                 }
                 leaf symm-rt-status {
                   type string;
                 }
                 leaf reject-reason {
                   type string;
                 }
               }
             }
           }
         }
         container history-db {
           leaf history-db-heading {
             type string;
           }
           leaf history-db-maximum-size {
             type int32;
           }
           leaf history-db-current-size {
             type int32;
           }
           container history-db-entries {
             leaf history-db-entries-heading {
               type string;
             }
             list history-db-entry {
               leaf history-db-entry-timestamp {
                 type string;
               }
               leaf history-db-entry-event {
                 type string;
               }
             }
           }
         }
         leaf mac-state-value {
           type int32;
         }
         leaf mac-state {
           type string;
         }
         leaf duplicate-mac-auto-recovery-timer {
           type string;
         }
         leaf nexthop-id {
           type string;
         }
       }
     }
   }
   grouping evpn-p2mp-information-block {
     list evpn-p2mp-instance {
       leaf evpn-instance-name {
         type string;
       }
       list evpn-p2mp-nh-table {
         leaf evpn-p2mp-nh-l2-domain {
           type int32;
         }
         leaf evpn-p2mp-nh-id {
           type int32;
         }
         leaf evpn-p2mp-nh-leaf-id {
           type int32;
         }
         list evpn-p2mp-nh-esi-list {
           leaf evpn-p2mp-nh-esi {
             type string;
           }
           leaf evpn-p2mp-nh-sh {
             type int32;
           }
         }
         leaf evpn-p2mp-nh-tunnel {
           type string;
         }
         leaf evpn-p2mp-nh-pmsi {
           type string;
           description "P-multicast service interface";
         }
       }
       container evpn-p2mp-peer-table {
         list evpn-p2mp-peer {
           leaf evpn-p2mp-peer-addr {
             type jt:ipaddr;
           }
           leaf evpn-p2mp-peer-l2-domain {
             type int32;
           }
           leaf evpn-p2mp-peer-transport-label {
             type int32;
           }
           leaf evpn-p2mp-peer-transport-label-backup {
             type int32;
           }
           leaf evpn-p2mp-peer-pmsi {
             type string;
             description "P-multicast service interface";
           }
         }
       }
     }
   }
   grouping evpn-l3-context-information-block {
     container evpn-l3-context {
       leaf context-name {
         type string;
       }
       leaf context-type {
         type string;
         description "Type";
       }
       leaf context-advertisement-mode {
         type string;
       }
       leaf context-gateway-interface {
         type string;
       }
       leaf context-router-mac {
         type string;
       }
       leaf context-encapsulation {
         type string;
       }
       leaf context-label {
         type int32;
       }
       leaf context-vni {
         type int32;
       }
       leaf context-import-policy {
         type string;
       }
       leaf context-export-policy {
         type string;
       }
       leaf route-distinguisher {
         type string;
       }
       leaf context-multicast-routing-mode {
         type string;
       }
       leaf context-flags {
         type int32;
       }
       leaf context-flags-descriptions {
         type string;
       }
       leaf context-change-flags {
         type int32;
       }
       leaf context-change-flags-descriptions {
         type string;
       }
       leaf context-composite-nexthop-support {
         type string;
       }
       leaf context-reference-count {
         type int32;
       }
       container context-overlay-gateway {
         leaf gateway-family {
           type string;
         }
         leaf gateway-address {
           type jt:ipaddr;
         }
       }
       container context-source-vtep {
         leaf vtep-family {
           type string;
         }
         leaf vtep-address {
           type jt:ipaddr;
         }
       }
     }
   }
   grouping evpn-ip-prefix-database-information-block {
     list evpn-pfxdb-l3-context {
       leaf context-name {
         type string;
       }
       list evpn-pfxdb-ip-table {
         leaf table-description {
           type string;
         }
         list evpn-pfxdb-ip-entry {
           leaf entry-prefix {
             type jt:ipprefix;
           }
           leaf entry-evpn-route-status {
             type string;
           }
           leaf entry-evpn-route-error {
             type string;
           }
           leaf entry-change-flags {
             type int32;
           }
           leaf entry-change-flags-descriptions {
             type string;
           }
           leaf entry-advertisement-mode {
             type string;
           }
           leaf entry-encap {
             type string;
           }
           leaf entry-vni {
             type int32;
           }
           leaf entry-label {
             type int32;
           }
           leaf entry-overlay-gateway-address {
             type jt:ipaddr;
           }
           leaf entry-router-mac {
             type string;
           }
         }
       }
       list evpn-pfxdb-evpn-ip-table {
         leaf table-description {
           type string;
         }
         list evpn-pfxdb-evpn-ip-entry {
           leaf entry-prefix {
             type jt:ipprefix;
           }
           leaf entry-etag {
             type int32;
           }
           container evpn-pfxdb-evpn-ip-adv {
             leaf route-distinguisher {
               type string;
             }
             leaf adv-vni {
               type int32;
             }
             leaf adv-label {
               type int32;
             }
             leaf adv-router-mac {
               type string;
             }
             leaf adv-bgp-nexthop {
               type jt:ipaddr;
             }
             leaf adv-overlay-gateway-address {
               type jt:ipaddr;
             }
             leaf adv-esi {
               type string;
             }
             leaf adv-ip-route-status {
               type string;
             }
             leaf adv-ip-route-error {
               type string;
             }
             leaf adv-gbp-tag {
               type int32;
             }
           }
           leaf entry-change-flags {
             type int32;
           }
           leaf entry-change-flags-descriptions {
             type string;
           }
         }
         container evpn-pfxdb-evpn-ip-adv {
           leaf route-distinguisher {
             type string;
           }
           leaf adv-vni {
             type int32;
           }
           leaf adv-label {
             type int32;
           }
           leaf adv-router-mac {
             type string;
           }
           leaf adv-bgp-nexthop {
             type jt:ipaddr;
           }
           leaf adv-overlay-gateway-address {
             type jt:ipaddr;
           }
           leaf adv-esi {
             type string;
           }
           leaf adv-ip-route-status {
             type string;
           }
           leaf adv-ip-route-error {
             type string;
           }
           leaf adv-gbp-tag {
             type int32;
           }
         }
       }
     }
   }
   grouping evpn-multicast-snooping-ar-nexthops-data-block {
     list evpn-multicast-snooping-ar-nexthops-per-instance {
       leaf evpn-instance-name {
         type string;
       }
       leaf evpn-ar-role {
         type string;
       }
       list evpn-multicast-snooping-ar-nexthops-per-domain {
         leaf vni-id {
           type int32;
         }
         leaf evpn-ar-load-balance-nexthop-index {
           type int32;
         }
         leaf load-balance-to {
           type empty;
         }
         list evpn-ar-load-balance-nexthops-member {
           leaf evpn-neighbor-nexthop-index {
             type int32;
           }
           leaf evpn-neighbor-interface {
             type string;
           }
           leaf evpn-ar-ip {
             type jt:ipaddr;
           }
           leaf designated-node {
             type empty;
           }
         }
       }
     }
   }
   grouping evpn-multicast-snooping-ar-mh-peers-data-block {
     list evpn-multicast-snooping-ar-mh-peers-per-instance {
       leaf evpn-instance-name {
         type string;
       }
       leaf evpn-ar-role {
         type string;
       }
       list evpn-ar-mh-peer {
         leaf evpn-neighbor-address {
           type jt:ipaddr;
         }
         leaf evpn-neighbor-nexthop-index {
           type int32;
         }
         leaf evpn-neighbor-interface {
           type string;
         }
         list evpn-local-multihomed-esi-table {
           leaf evpn-interface-esi {
             type string;
           }
         }
       }
     }
   }
   grouping evpn-multicast-snooping-ar-replicators-data-block {
     list evpn-multicast-snooping-ar-replicators-per-instance {
       leaf evpn-instance-name {
         type string;
       }
       leaf evpn-ar-role {
         type string;
       }
       list evpn-multicast-snooping-ar-replicators-per-domain {
         leaf vni-id {
           type int32;
         }
         leaf evpn-operational-replication-mode {
           type string;
         }
         list evpn-ar-replicator {
           leaf evpn-neighbor-address {
             type jt:ipaddr;
           }
           leaf evpn-neighbor-nexthop-index {
             type int32;
           }
           leaf evpn-neighbor-interface {
             type string;
           }
           leaf evpn-replication-mode {
             type string;
           }
         }
       }
     }
   }
   grouping multicast-next-hops-information-block {
     list next-hops-family {
       leaf address-family {
         type string;
       }
       list iflist-next-hop {
         leaf next-hop-id {
           type uint32;
         }
         leaf next-hop-ref-count {
           type uint32;
         }
         leaf next-hop-kernel-ref-count {
           type uint32;
         }
         leaf next-hop-addr {
           type uint32;
         }
         leaf rpf-next-hop-id {
           type uint32;
         }
         list next-hop-downstream-interface {
           leaf interface-name {
             type string;
             description "Name of interface";
           }
           leaf interface-index {
             type int32;
           }
           leaf interface-nh-index {
             type uint32;
             description "Logical interface nexthop index";
           }
         }
         leaf next-hop-downstream-interface-count {
           type uint32;
         }
       }
     }
   }
   grouping evpn-igmp-snooping-information-block {
     list evpn-igmp-snooping-database-instance {
       leaf instance-name {
         type string;
       }
       leaf vlan-id {
         type int32;
       }
       leaf vni-id {
         type int32;
       }
       list sg-entry {
         leaf grp-ip {
           type jt:ipprefix;
         }
         leaf src-ip {
           type jt:ipprefix;
         }
         leaf access-oif-count {
           type int32;
         }
         list sg-esi {
           leaf esi-intf-name {
             type string;
           }
           leaf esi-name {
             type string;
           }
           leaf esi-local-count {
             type string;
           }
           leaf esi-peer-count {
             type string;
           }
         }
       }
     }
     list evpn-igmp-snooping-proxy-instance {
       leaf instance-name {
         type string;
       }
       leaf vlan-id {
         type int32;
       }
       leaf vni-id {
         type int32;
       }
       list sg-proxy {
         leaf proxy-grp-ip {
           type jt:ipprefix;
         }
         leaf proxy-src-ip {
           type jt:ipprefix;
         }
         leaf interconn-adv-route-status {
           type string;
         }
         leaf proxy-grp-local-count {
           type string;
         }
         leaf proxy-grp-remote-count {
           type string;
         }
         leaf proxy-grp-smet-corenh {
           type int32;
         }
         leaf proxy-grp-smet-flood {
           type int32;
         }
       }
     }
   }
   grouping evpn-mld-snooping-information-block {
     list evpn-mld-snooping-database-instance {
       leaf instance-name {
         type string;
       }
       leaf vlan-id {
         type int32;
       }
       leaf vni-id {
         type int32;
       }
       list sg-entry {
         leaf grp-ip {
           type jt:ipprefix;
         }
         leaf src-ip {
           type jt:ipprefix;
         }
         leaf access-oif-count {
           type int32;
         }
         list sg-esi {
           leaf esi-intf-name {
             type string;
           }
           leaf esi-name {
             type string;
           }
           leaf esi-local-count {
             type string;
           }
           leaf esi-peer-count {
             type string;
           }
         }
       }
     }
     list evpn-mld-snooping-proxy-instance {
       leaf instance-name {
         type string;
       }
       leaf vlan-id {
         type int32;
       }
       leaf vni-id {
         type int32;
       }
       list sg-proxy {
         leaf proxy-grp-ip {
           type jt:ipprefix;
         }
         leaf proxy-src-ip {
           type jt:ipprefix;
         }
         leaf interconn-adv-route-status {
           type string;
         }
         leaf proxy-grp-local-count {
           type string;
         }
         leaf proxy-grp-remote-count {
           type string;
         }
         leaf proxy-grp-smet-corenh {
           type int32;
         }
         leaf proxy-grp-smet-flood {
           type int32;
         }
       }
     }
   }
   grouping evpn-oism-information-block {
     container evpn-oism {
       leaf oism-context-name {
         type string;
       }
       leaf oism-sbd-interface {
         type string;
       }
       leaf oism-mode {
         type string;
       }
     }
   }
   grouping evpn-oism-spmsi-ad-information-block {
     list evpn-oism-spmsi-ad-instance {
       leaf instance-name {
         type string;
       }
       leaf vlan-id {
         type int32;
       }
       leaf vni-id {
         type int32;
       }
       list sg-spmsi-ad {
         leaf spmsi-ad-grp-ip {
           type jt:ipprefix;
         }
         leaf spmsi-ad-src-ip {
           type jt:ipprefix;
         }
         leaf spmsi-ad-grp-local-count {
           type string;
         }
         leaf spmsi-ad-grp-remote-count {
           type string;
         }
       }
     }
   }
   grouping evpn-vpws-information-block {
     container evpn-vpws-instance {
       leaf evpn-vpws-instance-name {
         type string;
       }
       leaf evpn-vpws-instance-type {
         type string;
       }
       leaf evpn-vpws-instance-encap-type {
         type string;
       }
       leaf route-distinguisher {
         type string;
       }
       leaf local-interfaces {
         type int32;
       }
       leaf local-interfaces-up {
         type int32;
       }
       leaf num-protect-interfaces {
         type int32;
       }
       container evpn-vpws-interface-status-table {
         list evpn-vpws-interface {
           leaf evpn-vpws-interface-name {
             type string;
           }
           leaf evpn-vpws-interface-esi {
             type string;
           }
           leaf evpn-vpws-interface-mode {
             type string;
           }
           leaf evpn-vpws-interface-role {
             type string;
           }
           leaf evpn-vpws-interface-status {
             type string;
           }
           leaf evpn-vpws-control-word {
             type string;
           }
           leaf evpn-vpws-flow-label-transmit {
             type string;
           }
           leaf evpn-vpws-flow-label-receive {
             type string;
           }
           container evpn-vpws-service-id-local-status-table {
             list evpn-vpws-sid-local {
               leaf evpn-vpws-sid-local-value {
                 type int32;
               }
               leaf evpn-vpws-sid-advertised-label {
                 type int32;
               }
               leaf evpn-vpws-sid-advertised-end-dx2-sid {
                 type jt:ipv6addr;
               }
               leaf evpn-vpws-sid-local-interface-name {
                 type string;
               }
               leaf evpn-vpws-sid-remote-interface-name {
                 type string;
               }
               leaf evpn-vpws-sid-local-interface-status {
                 type string;
               }
               container evpn-vpws-sid-pe-status-table {
                 list evpn-vpws-sid-pe-info {
                   leaf evpn-vpws-sid-pe-ipaddr {
                     type jt:ipaddr;
                   }
                   leaf evpn-vpws-sid-interface-esi {
                     type string;
                   }
                   leaf evpn-vpws-sid-pe-label {
                     type int32;
                   }
                   leaf evpn-vpws-sid-pe-end-dx2-sid {
                     type jt:ipv6addr;
                   }
                   leaf evpn-vpws-sid-pe-mode {
                     type string;
                   }
                   leaf evpn-vpws-sid-pe-role {
                     type string;
                   }
                   leaf evpn-vpws-sid-pe-ts {
                     type string;
                   }
                   leaf evpn-vpws-sid-pe-status {
                     type string;
                   }
                 }
               }
             }
           }
           container evpn-vpws-service-id-remote-status-table {
             list evpn-vpws-sid-remote {
               leaf evpn-vpws-sid-remote-value {
                 type int32;
               }
               leaf evpn-vpws-sid-local-interface-name {
                 type string;
               }
               leaf evpn-vpws-sid-local-interface-status {
                 type string;
               }
               leaf evpn-vpws-sid-remote-interface-name {
                 type string;
               }
               container evpn-vpws-sid-pe-status-table {
                 list evpn-vpws-sid-pe-info {
                   leaf evpn-vpws-sid-pe-ipaddr {
                     type jt:ipaddr;
                   }
                   leaf evpn-vpws-sid-interface-esi {
                     type string;
                   }
                   leaf evpn-vpws-sid-pe-label {
                     type int32;
                   }
                   leaf evpn-vpws-sid-pe-end-dx2-sid {
                     type jt:ipv6addr;
                   }
                   leaf evpn-vpws-sid-pe-mode {
                     type string;
                   }
                   leaf evpn-vpws-sid-pe-role {
                     type string;
                   }
                   leaf evpn-vpws-sid-pe-ts {
                     type string;
                   }
                   leaf evpn-vpws-sid-pe-status {
                     type string;
                   }
                 }
               }
             }
           }
         }
       }
       container evpn-protect-interface-status-table {
         list evpn-protect-interface {
           leaf evpn-primary-interface-name {
             type string;
           }
           leaf evpn-protect-interface-name {
             type string;
           }
           leaf evpn-protect-interface-status {
             type string;
           }
         }
       }
       container evpn-vpws-esi-info-status-table {
         list evpn-vpws-esi-info {
           leaf evpn-vpws-esi-val {
             type string;
           }
           leaf evpn-vpws-num-pes {
             type int32;
           }
           list evpn-vpws-esi-pe-status-table {
             container evpn-vpws-esi-pe-info {
               leaf evpn-vpws-esi-pe-ipaddr {
                 type jt:ipaddr;
               }
               leaf-list evpn-vpws-esi-advertised-sid {
                 type int32;
               }
             }
           }
         }
       }
       list evpn-vpws-esi-df-table {
         leaf evpn-esi-value {
           type string;
         }
         leaf esi-df-election-algorithm {
           type string;
         }
         leaf esi-granularity {
           type string;
         }
         leaf esi-lacp-oos-on-ndf {
           type string;
         }
         leaf evpn-vpws-esi-df-min-sid {
           type int32;
         }
         leaf evpn-vpws-esi-df-primary-pe {
           type string;
         }
         leaf evpn-vpws-esi-df-primary-pe-preference {
           type string;
         }
         leaf evpn-vpws-esi-df-primary-pe-no-preempt {
           type string;
         }
         leaf evpn-vpws-esi-df-backup-pe {
           type string;
         }
         leaf evpn-vpws-esi-df-backup-pe-preference {
           type string;
         }
         leaf evpn-vpws-esi-df-backup-pe-no-preempt {
           type string;
         }
         leaf evpn-vpws-esi-df-other-pe {
           type string;
         }
         leaf evpn-vpws-esi-df-other-pe-preference {
           type string;
         }
         leaf evpn-vpws-esi-df-other-pe-no-preempt {
           type string;
         }
         leaf evpn-vpws-esi-df-timestamp {
           type string;
         }
       }
       container evpn-vpws-service-id-local-status-table {
         list evpn-vpws-sid-local {
           leaf evpn-vpws-sid-local-value {
             type int32;
           }
           leaf evpn-vpws-sid-advertised-label {
             type int32;
           }
           leaf evpn-vpws-sid-advertised-end-dx2-sid {
             type jt:ipv6addr;
           }
           leaf evpn-vpws-sid-local-interface-name {
             type string;
           }
           leaf evpn-vpws-sid-remote-interface-name {
             type string;
           }
           leaf evpn-vpws-sid-local-interface-status {
             type string;
           }
           container evpn-vpws-sid-pe-status-table {
             list evpn-vpws-sid-pe-info {
               leaf evpn-vpws-sid-pe-ipaddr {
                 type jt:ipaddr;
               }
               leaf evpn-vpws-sid-interface-esi {
                 type string;
               }
               leaf evpn-vpws-sid-pe-label {
                 type int32;
               }
               leaf evpn-vpws-sid-pe-end-dx2-sid {
                 type jt:ipv6addr;
               }
               leaf evpn-vpws-sid-pe-mode {
                 type string;
               }
               leaf evpn-vpws-sid-pe-role {
                 type string;
               }
               leaf evpn-vpws-sid-pe-ts {
                 type string;
               }
               leaf evpn-vpws-sid-pe-status {
                 type string;
               }
             }
           }
         }
       }
       container evpn-vpws-sid-pe-status-table {
         list evpn-vpws-sid-pe-info {
           leaf evpn-vpws-sid-pe-ipaddr {
             type jt:ipaddr;
           }
           leaf evpn-vpws-sid-interface-esi {
             type string;
           }
           leaf evpn-vpws-sid-pe-label {
             type int32;
           }
           leaf evpn-vpws-sid-pe-end-dx2-sid {
             type jt:ipv6addr;
           }
           leaf evpn-vpws-sid-pe-mode {
             type string;
           }
           leaf evpn-vpws-sid-pe-role {
             type string;
           }
           leaf evpn-vpws-sid-pe-ts {
             type string;
           }
           leaf evpn-vpws-sid-pe-status {
             type string;
           }
         }
       }
       container evpn-vpws-service-id-remote-status-table {
         list evpn-vpws-sid-remote {
           leaf evpn-vpws-sid-remote-value {
             type int32;
           }
           leaf evpn-vpws-sid-local-interface-name {
             type string;
           }
           leaf evpn-vpws-sid-local-interface-status {
             type string;
           }
           leaf evpn-vpws-sid-remote-interface-name {
             type string;
           }
           container evpn-vpws-sid-pe-status-table {
             list evpn-vpws-sid-pe-info {
               leaf evpn-vpws-sid-pe-ipaddr {
                 type jt:ipaddr;
               }
               leaf evpn-vpws-sid-interface-esi {
                 type string;
               }
               leaf evpn-vpws-sid-pe-label {
                 type int32;
               }
               leaf evpn-vpws-sid-pe-end-dx2-sid {
                 type jt:ipv6addr;
               }
               leaf evpn-vpws-sid-pe-mode {
                 type string;
               }
               leaf evpn-vpws-sid-pe-role {
                 type string;
               }
               leaf evpn-vpws-sid-pe-ts {
                 type string;
               }
               leaf evpn-vpws-sid-pe-status {
                 type string;
               }
             }
           }
         }
       }
     }
   }
   grouping l2ald-rtb-mac-ip-db-block {
     leaf l2ald-rtb-mac-ip-db-name {
       type string;
       description "Bridging MAC database for a routing instance";
     }
     list l2ald-mac-ip-entry {
       leaf l2-mac-ip-logical-system {
         type string;
         description "Name of logical system in which this MAC address was learned";
       }
       leaf l2-mac-ip-routing-instance {
         type string;
         description "Routing instance in which the MAC address was learned";
       }
       leaf l2-mac-ip-bridging-domain {
         type string;
         description "Bridging domain in which the MAC address was learned";
       }
       leaf l2-ip-address {
         type jt:ipaddr;
         description "IP address learned from another source";
       }
       leaf l2-mac-address {
         type jt:mac-addr;
         description "Media access control address learned from another source";
       }
       leaf l2-mac-ip-flags {
         type string;
         description "MAC IP flags";
       }
       leaf l2-mac-ip-gbptag {
         type int32;
         description "GBP tag value";
       }
       leaf l2-mac-logical-interface {
         type string;
         description "Name of logical interface on which MAC address was learned";
       }
       leaf l2-active-source {
         type string;
         description "Remote VXLAN tunnel endpoint ip address or ESI value";
       }
       leaf l2-mac-ip-state {
         type string;
         description "MAC IP state";
       }
       leaf l2-mac-ip-rpd-flags {
         type string;
         description "MAC IP RPD flags";
       }
       leaf l2-mac-ip-local-learn-mask {
         type string;
         description "Local learn mask";
       }
       leaf l2-mac-ip-remote-learn-mask {
         type string;
         description "Remote learn mask";
       }
       leaf l2-mac-ip-remote-proxy-learn-mask {
         type string;
         description "Remote Proxy learn mask";
       }
       leaf l2-mac-ip-time-info {
         type string;
         description "MAC IP Time info";
       }
     }
   }
   grouping l2ald-rtb-mac-ip-kernel-db-block {
     list l2ald-mac-ip-kernel-entry {
       leaf l2-mac-ip-bd-id {
         type int32;
         description "Bridge-domain id";
       }
       leaf l2-ip-address {
         type jt:ipaddr;
         description "IP address learned from another source";
       }
       leaf l2-mac-address {
         type jt:mac-addr;
         description "Media access control address learned from another source";
       }
       leaf l2-mac-logical-interface {
         type string;
         description "Name of logical interface on which MAC address was learned";
       }
       leaf l2-mac-ip-flags {
         type string;
         description "MAC IP flags";
       }
       leaf l2-mac-ip-state {
         type string;
         description "MAC IP state";
       }
       leaf l2-mac-pseudo-interface {
         type string;
         description "Pseudo vtep interface";
       }
       leaf l2-mac-ip-rpd-flags {
         type string;
         description "MAC IP RPD flags";
       }
       leaf l2-mac-ip-local-learn-mask {
         type string;
         description "Local learn mask";
       }
       leaf l2-mac-ip-remote-learn-mask {
         type string;
         description "Remote learn mask";
       }
       leaf l2-mac-ip-remote-proxy-learn-mask {
         type string;
         description "Remote Proxy learn mask";
       }
       leaf l2-mac-ip-time-info {
         type string;
         description "MAC IP Time info";
       }
     }
   }
   grouping l2ald-rtb-macdb-block {
     leaf l2ald-macdb-rtb-name {
       type string;
       description "Bridging MAC database for a routing instance";
     }
     list l2ald-mac-entry {
       leaf l2-mac-address {
         type jt:mac-addr;
         description "Media access control address learned from another source";
       }
       leaf l2-mac-logical-interface {
         type string;
         description "Name of logical interface on which MAC address was learned";
       }
       leaf l2-mac-logical-system {
         type string;
         description "Name of logical system in which this MAC address was learned";
       }
       leaf l2-mac-routing-instance {
         type string;
         description "Routing instance in which the MAC address was learned";
       }
       leaf l2-mac-bridging-domain {
         type string;
         description "Bridging domain in which the MAC address was learned";
       }
       leaf l2-mac-flags {
         type string;
         description "Forwarding entry flags associated with MACs displayed in short form";
       }
       leaf l2-mac-fwd-next-hop {
         type uint32;
         description "Forwarding next hop for Control MAC to be routed to";
       }
       leaf l2-mac-property {
         type string;
         description "Property of MAC route";
       }
       leaf l2-active-source {
         type string;
         description "Remote VXLAN tunnel endpoint ip address or ESI value";
       }
       leaf l2-mac-pvlan-port-role {
         type string;
         description "The PVLAN port role for interface associated with these MAC addresses";
       }
       leaf l2-mac-pvlan-vlan-id {
         type string;
         description "The PVLAN vlan ID associated with these MAC addresses";
       }
       leaf l2-mac-interface-device {
         type string;
         description "Name of interface device on which MAC address was learned";
       }
       leaf l2-mac-rtr-id {
         type uint32;
         description "Remote Rourter ID for Control MAC to be routed to";
       }
       leaf l2-mac-vlan {
         type uint32;
         description "VLAN ID of the routing instance in which the MAC address was learned";
       }
       leaf l2-mac-stp-index {
         type uint32;
         description "Spanning Tree Protocol (STP) index of the logical interface in which the MAC address was learned";
       }
       leaf l2-mac-ifl-generation {
         type uint32;
         description "Creation time of the logical interface when this MAC address was learned";
       }
       leaf l2-mac-entry-age {
         type string;
         description "Age of the mac entry";
       }
       leaf l2-bridge-vlan {
         type string;
         description "Vlan for the bridging domain";
       }
       leaf l2-bridge-isid {
         type uint32;
         description "ISID for the bridging domain";
       }
       leaf l2-remote-beb-mac-address {
         type jt:mac-addr;
         description "Media access control address of remote backbone edge bridge (BEB)";
       }
       leaf l2-mac-elp-nh {
         type uint32;
         description "ELP NH Id of the MAC address";
       }
       leaf l2-mac-base-logical-interface {
         type string;
         description "Name of logical interface on which MAC address was learnt first";
       }
       leaf l2-mac-entry-flags {
         type string;
         description "Forwarding entry flags associated with these MAC addresses";
       }
       leaf l2-mac-epoch {
         type uint32;
         description "Spanning Tree Protocol (STP) epoch number when MAC address was learned";
       }
       leaf l2-mac-sequence-number {
         type uint32;
         description "Sequence number assigned to this MAC address";
       }
       leaf l2-mac-learn-mask {
         type string;
         description "Mask of Packet Forwarding Engines where this MAC address was learned";
       }
       leaf l2-mac-mcae-id {
         type uint32;
         description "MCAE ID of the mac entry";
       }
       leaf l2-mac-mcae-ifl-unit {
         type uint32;
         description "MCAE IFL unit of the mac entry";
       }
       leaf l2-mac-svc-id {
         type uint32;
         description "MCAE SVC ID of the mac entry";
       }
       leaf l2-mac-rg-id {
         type uint32;
         description "RG ID of the mac entry";
       }
       leaf l2-mac-rtm-op {
         type uint32;
         description "MCAE mac operation of the mac entry";
       }
       leaf l2-mac-time-info {
         type string;
         description "Mac learning time";
       }
       container l2ald-mac-source-address-statistics {
         leaf packet-count {
           type uint64;
           description "Packet count";
         }
         leaf byte-count {
           type uint64;
           description "Byte count";
         }
       }
       container l2ald-mac-destination-address-statistics {
         leaf packet-count {
           type uint64;
           description "Packet count";
         }
         leaf byte-count {
           type uint64;
           description "Byte count";
         }
       }
       leaf l2-remote-vtep-address {
         type string;
         description "Remote VXLAN tunnel endpoint ip address";
       }
     }
   }
   grouping l2ald-interface-macdb-block {
     leaf l2ald-macdb-if-name {
       type string;
     }
     list l2ald-mac-entry {
       leaf l2-mac-address {
         type jt:mac-addr;
         description "Media access control address learned from another source";
       }
       leaf l2-mac-logical-interface {
         type string;
         description "Name of logical interface on which MAC address was learned";
       }
       leaf l2-mac-logical-system {
         type string;
         description "Name of logical system in which this MAC address was learned";
       }
       leaf l2-mac-routing-instance {
         type string;
         description "Routing instance in which the MAC address was learned";
       }
       leaf l2-mac-bridging-domain {
         type string;
         description "Bridging domain in which the MAC address was learned";
       }
       leaf l2-mac-flags {
         type string;
         description "Forwarding entry flags associated with MACs displayed in short form";
       }
       leaf l2-mac-fwd-next-hop {
         type uint32;
         description "Forwarding next hop for Control MAC to be routed to";
       }
       leaf l2-mac-property {
         type string;
         description "Property of MAC route";
       }
       leaf l2-active-source {
         type string;
         description "Remote VXLAN tunnel endpoint ip address or ESI value";
       }
       leaf l2-mac-pvlan-port-role {
         type string;
         description "The PVLAN port role for interface associated with these MAC addresses";
       }
       leaf l2-mac-pvlan-vlan-id {
         type string;
         description "The PVLAN vlan ID associated with these MAC addresses";
       }
       leaf l2-mac-interface-device {
         type string;
         description "Name of interface device on which MAC address was learned";
       }
       leaf l2-mac-rtr-id {
         type uint32;
         description "Remote Rourter ID for Control MAC to be routed to";
       }
       leaf l2-mac-vlan {
         type uint32;
         description "VLAN ID of the routing instance in which the MAC address was learned";
       }
       leaf l2-mac-stp-index {
         type uint32;
         description "Spanning Tree Protocol (STP) index of the logical interface in which the MAC address was learned";
       }
       leaf l2-mac-ifl-generation {
         type uint32;
         description "Creation time of the logical interface when this MAC address was learned";
       }
       leaf l2-mac-entry-age {
         type string;
         description "Age of the mac entry";
       }
       leaf l2-bridge-vlan {
         type string;
         description "Vlan for the bridging domain";
       }
       leaf l2-bridge-isid {
         type uint32;
         description "ISID for the bridging domain";
       }
       leaf l2-remote-beb-mac-address {
         type jt:mac-addr;
         description "Media access control address of remote backbone edge bridge (BEB)";
       }
       leaf l2-mac-elp-nh {
         type uint32;
         description "ELP NH Id of the MAC address";
       }
       leaf l2-mac-base-logical-interface {
         type string;
         description "Name of logical interface on which MAC address was learnt first";
       }
       leaf l2-mac-entry-flags {
         type string;
         description "Forwarding entry flags associated with these MAC addresses";
       }
       leaf l2-mac-epoch {
         type uint32;
         description "Spanning Tree Protocol (STP) epoch number when MAC address was learned";
       }
       leaf l2-mac-sequence-number {
         type uint32;
         description "Sequence number assigned to this MAC address";
       }
       leaf l2-mac-learn-mask {
         type string;
         description "Mask of Packet Forwarding Engines where this MAC address was learned";
       }
       leaf l2-mac-mcae-id {
         type uint32;
         description "MCAE ID of the mac entry";
       }
       leaf l2-mac-mcae-ifl-unit {
         type uint32;
         description "MCAE IFL unit of the mac entry";
       }
       leaf l2-mac-svc-id {
         type uint32;
         description "MCAE SVC ID of the mac entry";
       }
       leaf l2-mac-rg-id {
         type uint32;
         description "RG ID of the mac entry";
       }
       leaf l2-mac-rtm-op {
         type uint32;
         description "MCAE mac operation of the mac entry";
       }
       leaf l2-mac-time-info {
         type string;
         description "Mac learning time";
       }
       container l2ald-mac-source-address-statistics {
         leaf packet-count {
           type uint64;
           description "Packet count";
         }
         leaf byte-count {
           type uint64;
           description "Byte count";
         }
       }
       container l2ald-mac-destination-address-statistics {
         leaf packet-count {
           type uint64;
           description "Packet count";
         }
         leaf byte-count {
           type uint64;
           description "Byte count";
         }
       }
       leaf l2-remote-vtep-address {
         type string;
         description "Remote VXLAN tunnel endpoint ip address";
       }
     }
   }
   grouping l2ald-vpls-flood-instance-block {
     list l2ald-vpls-lr-information {
       list logical-system-info {
         leaf logical-system-name {
           type string;
           description "Logical System";
         }
       }
       list l2ald-vpls-flood-instance-information {
         leaf instance-name {
           type string;
         }
         leaf num-active-ce-iffs {
           type int32;
         }
         leaf num-active-ve-iffs {
           type int32;
         }
         leaf bridging-domain {
           type string;
         }
         list flood-route {
           leaf route-prefix {
             type string;
           }
           leaf route-type {
             type string;
           }
           leaf owner {
             type string;
           }
           leaf nhtype {
             type string;
           }
           leaf nhindex {
             type int32;
           }
           list flood-nh-components {
             leaf interface-name {
               type string;
               description "Bridging media access control address interface";
             }
             leaf interface-type {
               type string;
             }
             leaf nhtype {
               type string;
             }
             leaf nhindex {
               type int32;
             }
             leaf interface-esi {
               type string;
               description "ESI";
             }
             leaf nh-guid {
               type uint64;
             }
             leaf remote-vtep-address {
               type string;
               description "Remote VXLAN tunnel endpoint IP address";
             }
             leaf shared-rvtep-interface-name {
               type string;
             }
           }
           list flood-nh-group {
             leaf flood-nh-group-name {
               type string;
             }
             leaf flood-nh-group-type {
               type string;
             }
             leaf nhtype {
               type string;
             }
             leaf nhindex {
               type int32;
             }
             leaf flood-group-composite-function {
               type string;
             }
             list flood-nh-components {
               leaf interface-name {
                 type string;
                 description "Bridging media access control address interface";
               }
               leaf interface-type {
                 type string;
               }
               leaf nhtype {
                 type string;
               }
               leaf nhindex {
                 type int32;
               }
               leaf interface-esi {
                 type string;
                 description "ESI";
               }
               leaf nh-guid {
                 type uint64;
               }
               leaf remote-vtep-address {
                 type string;
                 description "Remote VXLAN tunnel endpoint IP address";
               }
               leaf shared-rvtep-interface-name {
                 type string;
               }
             }
             list flood-nh-p2mp-components {
               leaf component-nhindex {
                 type int32;
               }
             }
             list flood-nh-evpn-core-components {
               leaf component-nhindex {
                 type int32;
               }
               leaf peer {
                 type string;
               }
               leaf nh-type {
                 type string;
               }
               leaf interface-esi {
                 type string;
                 description "ESI";
               }
             }
             leaf nh-guid {
               type uint64;
             }
           }
           leaf route-flood-group-name {
             type string;
           }
           leaf route-flood-group-index {
             type int32;
           }
           leaf df-indirect-index {
             type int32;
           }
           leaf df-composite-index {
             type int32;
           }
           leaf ndf-indirect-index {
             type int32;
           }
           leaf ndf-composite-index {
             type int32;
           }
           leaf make-before-break {
             type string;
           }
           leaf make-before-break-state {
             type string;
           }
           list flood-nh-evpn-core-components {
             leaf component-nhindex {
               type int32;
             }
             leaf peer {
               type string;
             }
             leaf nh-type {
               type string;
             }
             leaf interface-esi {
               type string;
               description "ESI";
             }
           }
           list flood-nh-p2mp-components {
             leaf component-nhindex {
               type int32;
             }
           }
           leaf nh-guid {
             type uint64;
           }
         }
         leaf bridge-domain-name {
           type string;
           description "Name of the bridging domain";
         }
         leaf bridge-domain-evpn-extension {
           type string;
           description "EVPN extension for the BD";
         }
       }
     }
   }
   grouping l2ald-vpls-flood-route-information-block {
     list flood-route {
       leaf route-prefix {
         type string;
       }
       leaf route-type {
         type string;
       }
       leaf owner {
         type string;
       }
       leaf nhtype {
         type string;
       }
       leaf nhindex {
         type int32;
       }
       list flood-nh-components {
         leaf interface-name {
           type string;
           description "Bridging media access control address interface";
         }
         leaf interface-type {
           type string;
         }
         leaf nhtype {
           type string;
         }
         leaf nhindex {
           type int32;
         }
         leaf interface-esi {
           type string;
           description "ESI";
         }
         leaf nh-guid {
           type uint64;
         }
         leaf remote-vtep-address {
           type string;
           description "Remote VXLAN tunnel endpoint IP address";
         }
         leaf shared-rvtep-interface-name {
           type string;
         }
       }
       list flood-nh-group {
         leaf flood-nh-group-name {
           type string;
         }
         leaf flood-nh-group-type {
           type string;
         }
         leaf nhtype {
           type string;
         }
         leaf nhindex {
           type int32;
         }
         leaf flood-group-composite-function {
           type string;
         }
         list flood-nh-components {
           leaf interface-name {
             type string;
             description "Bridging media access control address interface";
           }
           leaf interface-type {
             type string;
           }
           leaf nhtype {
             type string;
           }
           leaf nhindex {
             type int32;
           }
           leaf interface-esi {
             type string;
             description "ESI";
           }
           leaf nh-guid {
             type uint64;
           }
           leaf remote-vtep-address {
             type string;
             description "Remote VXLAN tunnel endpoint IP address";
           }
           leaf shared-rvtep-interface-name {
             type string;
           }
         }
         list flood-nh-p2mp-components {
           leaf component-nhindex {
             type int32;
           }
         }
         list flood-nh-evpn-core-components {
           leaf component-nhindex {
             type int32;
           }
           leaf peer {
             type string;
           }
           leaf nh-type {
             type string;
           }
           leaf interface-esi {
             type string;
             description "ESI";
           }
         }
         leaf nh-guid {
           type uint64;
         }
       }
       leaf route-flood-group-name {
         type string;
       }
       leaf route-flood-group-index {
         type int32;
       }
       leaf df-indirect-index {
         type int32;
       }
       leaf df-composite-index {
         type int32;
       }
       leaf ndf-indirect-index {
         type int32;
       }
       leaf ndf-composite-index {
         type int32;
       }
       leaf make-before-break {
         type string;
       }
       leaf make-before-break-state {
         type string;
       }
       list flood-nh-evpn-core-components {
         leaf component-nhindex {
           type int32;
         }
         leaf peer {
           type string;
         }
         leaf nh-type {
           type string;
         }
         leaf interface-esi {
           type string;
           description "ESI";
         }
       }
       list flood-nh-p2mp-components {
         leaf component-nhindex {
           type int32;
         }
       }
       leaf nh-guid {
         type uint64;
       }
     }
   }
   grouping l2ald-vpls-flood-event-queue-block {
     container l2ald-vpls-flood-next-event {
       list l2ald-vpls-flood-event-info {
         leaf event-name {
           type string;
         }
         leaf event-owner {
           type string;
         }
         leaf event-type {
           type string;
         }
         leaf event-op {
           type string;
         }
         leaf event-error {
           type string;
         }
       }
     }
     container l2ald-vpls-flood-event-list {
       list l2ald-vpls-flood-event-info {
         leaf event-name {
           type string;
         }
         leaf event-owner {
           type string;
         }
         leaf event-type {
           type string;
         }
         leaf event-op {
           type string;
         }
         leaf event-error {
           type string;
         }
       }
     }
   }
   grouping l2rtb-evpn-arp-db-block {
     leaf l2rtb-evpn-arp-db-rtb-name {
       type string;
       description "Bridging MAC INET database for a routing instance";
     }
     list l2rtb-evpn-arp-entry {
       leaf l2-evpn-arp-inet-address {
         type jt:ipaddr;
         description "INET addresses learned via ARP";
       }
       leaf l2-mac-address {
         type jt:mac-addr;
         description "Media access control address learned from another source";
       }
       leaf l2-mac-logical-interface {
         type string;
         description "Name of logical interface on which MAC address was learned";
       }
       leaf l2-mac-routing-instance {
         type string;
         description "Routing instance in which the MAC address was learned";
       }
       leaf l2-mac-bridging-domain {
         type string;
         description "Bridging domain in which the MAC address was learned";
       }
       leaf l2-mac-interface-device {
         type string;
         description "Name of interface device on which MAC address was learned";
       }
       container l2ald-mac-destination-address-statistics {
         leaf packet-count {
           type uint64;
           description "Packet count";
         }
         leaf byte-count {
           type uint64;
           description "Byte count";
         }
       }
       container l2ald-mac-source-address-statistics {
         leaf packet-count {
           type uint64;
           description "Packet count";
         }
         leaf byte-count {
           type uint64;
           description "Byte count";
         }
       }
     }
   }
   grouping l2rtb-evpn-nd-db-block {
     leaf l2rtb-evpn-nd-db-rtb-name {
       type string;
       description "Bridging MAC INET6 database for a routing instance";
     }
     list l2rtb-evpn-nd-entry {
       leaf l2-evpn-nd-inet6-address {
         type jt:ipv6addr;
         description "INET6 addresses learned via NDP";
       }
       leaf l2-mac-address {
         type jt:mac-addr;
         description "Media access control address learned from another source";
       }
       leaf l2-mac-logical-interface {
         type string;
         description "Name of logical interface on which MAC address was learned";
       }
       leaf l2-mac-routing-instance {
         type string;
         description "Routing instance in which the MAC address was learned";
       }
       leaf l2-mac-bridging-domain {
         type string;
         description "Bridging domain in which the MAC address was learned";
       }
       leaf l2-mac-interface-device {
         type string;
         description "Name of interface device on which MAC address was learned";
       }
       container l2ald-mac-destination-address-statistics {
         leaf packet-count {
           type uint64;
           description "Packet count";
         }
         leaf byte-count {
           type uint64;
           description "Byte count";
         }
       }
       container l2ald-mac-source-address-statistics {
         leaf packet-count {
           type uint64;
           description "Packet count";
         }
         leaf byte-count {
           type uint64;
           description "Byte count";
         }
       }
     }
   }
   grouping l2rtb-peer-gateway-macdb-block {
     list l2rtb-peer-gateway-mac-entry {
       leaf l2-gateway-mac-routing-instance {
         type string;
         description "Routing instance in which the GW MAC address is installed";
       }
       leaf l2-gateway-mac-bridge-domain {
         type string;
         description "Bridging domain in which the GW MAC address is installed";
       }
       leaf l2-gateway-mac-bridge-vlan {
         type string;
         description "Vlan for the bridging domain";
       }
       leaf l2-gateway-mac-address {
         type jt:mac-addr;
         description "MAC address Installed as gateway (route-able) MAC";
       }
     }
   }
   grouping evpn-statistics-information-block {
     leaf instance-name {
       type string;
     }
     list interface-statistics {
       leaf l2bd-vlan-id {
         type string;
         description "Bridge domain VLAN";
       }
       leaf vn-id {
         type uint32;
         description "VXLAN identifier";
       }
       leaf remote-pe {
         type jt:ipaddr;
       }
       leaf broadcast-packets {
         type uint64;
         description "Broadcast packets";
       }
       leaf broadcast-bytes {
         type uint64;
         description "Broadcast bytes";
       }
       leaf multicast-packets {
         type uint64;
         description "Multicast packets";
       }
       leaf multicast-bytes {
         type uint64;
         description "Multicast bytes";
       }
       leaf flooded-packets {
         type uint64;
         description "Flooded packets";
       }
       leaf flooded-bytes {
         type uint64;
         description "Flooded bytes";
       }
       leaf unicast-packets {
         type uint64;
         description "Unicast packets";
       }
       leaf unicast-bytes {
         type uint64;
         description "Unicast bytes";
       }
       leaf data-vlan-mlp-drop-count {
         type int32;
         description "Number of mac learning packets dropped in data vlan";
       }
       leaf num-mac-count {
         type int32;
         description "Number of addresses learned on the interface";
       }
       leaf mac-limit {
         type int32;
         description "Limit of number of addresses learned on interface";
       }
       list interface {
         leaf interface-name {
           type string;
           description "Bridging media access control address interface";
         }
         leaf local-interface-index {
           type int32;
         }
         leaf interface-flags {
           type int32;
         }
       }
     }
     container instance {
       leaf instance-name {
         type string;
       }
       leaf instance-display-error {
         type string;
       }
       leaf edge-protection {
         type string;
       }
       leaf edge-protector {
         type string;
       }
       list reference-site {
         leaf automatic-site-name {
           type string;
           description "VPLS automatic site name";
         }
         leaf automatic-site-id-status {
           type string;
           description "VPLS automatic site identifier status";
         }
         leaf automatic-site-claim-id {
           type int32;
           description "Claim site identifier";
         }
         leaf automatic-site-collisions {
           type int32;
           description "Number of collisions";
         }
         leaf automatic-site-timer-status {
           type string;
           description "VPLS automatic site timer status";
         }
         leaf vpls-signaling-protocol-identifier {
           type string;
         }
         leaf local-site-id {
           type string;
         }
         leaf source-attachment-id {
           type string;
           description "Local source attachment identifier";
         }
         leaf vpls-id {
           type int32;
           description "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         leaf target-attachment-id {
           type string;
           description "Remote target attachment identifier";
         }
         list mesh-group-interfaces {
           leaf mesh-group-name {
             type string;
             description "Name of mesh-group";
           }
           leaf mesh-group-state {
             type string;
             description "Mesh-group state";
           }
           leaf mesh-group-id {
             type int32;
             description "Mesh-group Identifier";
           }
           list interface {
             leaf interface-name {
               type string;
               description "Name of interface";
             }
             leaf interface-description {
               type string;
             }
             leaf interface-flags-description {
               type string;
             }
             leaf interface-flags {
               type int32;
             }
           }
         }
         list interface {
           leaf interface-name {
             type string;
             description "Name of interface";
           }
           leaf interface-id {
             type int32;
           }
           leaf interface-description {
             type string;
           }
           leaf interface-flags-description {
             type string;
           }
           leaf interface-flags {
             type int32;
           }
         }
         list label-block {
           leaf-list label-block.heading {
             type string;
           }
           leaf label-block-base {
             type int32;
           }
           leaf label-block-offset {
             type int32;
           }
           leaf label-block-size {
             type int32;
           }
           leaf label-block-range {
             type int32;
           }
           leaf label-block-preference {
             type int32;
           }
           leaf label-block-status-vector {
             type string;
           }
         }
         list connection {
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type int32;
           }
           leaf remote-pw-status-code {
             type int32;
           }
           leaf connection-protection {
             type string;
           }
           leaf mesh-group-name {
             type string;
             description "Name of mesh-group";
           }
           leaf vc-flow-label-transmit {
             type string;
           }
           leaf vc-flow-label-receive {
             type string;
           }
           leaf auto-sensed {
             type empty;
             description "Auto-sensed";
           }
           container local-interface {
             leaf interface-name {
               type string;
               description "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description "Name of interface";
             }
             leaf interface-status {
               type string;
             }
             leaf interface-encapsulation {
               type string;
             }
           }
           container connection-bandwidth {
             leaf connection-bandwidth.heading {
               type string;
               description "Bandwidth of a layer 2 connection";
             }
             leaf bandwidth {
               type int32;
             }
             leaf class-type {
               type int32;
             }
             leaf class-bandwidth {
               type int32;
             }
           }
           container vpls-rsvp-te-p2mp-lsp-information {
             leaf vpls-ingress-p2mp-branch-lsp-name {
               type string;
               description "Name of ingress point-to-multipoint branch LSP";
             }
             leaf vpls-ingress-p2mp-branch-lsp-state {
               type string;
               description "State of ingress point-to-multipoint branch LSP";
             }
             leaf vpls-egress-p2mp-branch-lsp-name {
               type string;
               description "Name of egress point-to-multipoint branch LSP";
             }
             leaf vpls-egress-p2mp-branch-lsp-state {
               type string;
               description "State of egress point-to-multipoint branch LSP";
             }
           }
           container spe-info {
             leaf spe-info.heading {
               type string;
             }
             leaf local-ip-addr {
               type jt:ipaddr;
             }
             leaf remote-ip-addr {
               type jt:ipaddr;
             }
             leaf pw-status {
               type string;
             }
           }
           container history {
             leaf history.category-heading {
               type string;
             }
             leaf history.heading {
               type string;
             }
             container history-element {
               leaf log-time-stamp {
                 type string;
               }
               leaf log-event {
                 type string;
               }
               leaf changed-entity {
                 type string;
               }
             }
           }
         }
         list mesh-group-connection {
           leaf mesh-group-name {
             type string;
             description "Name of mesh-group";
           }
           list connection {
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type int32;
             }
             leaf remote-pw-status-code {
               type int32;
             }
             leaf connection-protection {
               type string;
             }
             leaf mesh-group-name {
               type string;
               description "Name of mesh-group";
             }
             leaf vc-flow-label-transmit {
               type string;
             }
             leaf vc-flow-label-receive {
               type string;
             }
             leaf auto-sensed {
               type empty;
               description "Auto-sensed";
             }
             container local-interface {
               leaf interface-name {
                 type string;
                 description "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description "Name of interface";
               }
               leaf interface-status {
                 type string;
               }
               leaf interface-encapsulation {
                 type string;
               }
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
             container vpls-rsvp-te-p2mp-lsp-information {
               leaf vpls-ingress-p2mp-branch-lsp-name {
                 type string;
                 description "Name of ingress point-to-multipoint branch LSP";
               }
               leaf vpls-ingress-p2mp-branch-lsp-state {
                 type string;
                 description "State of ingress point-to-multipoint branch LSP";
               }
               leaf vpls-egress-p2mp-branch-lsp-name {
                 type string;
                 description "Name of egress point-to-multipoint branch LSP";
               }
               leaf vpls-egress-p2mp-branch-lsp-state {
                 type string;
                 description "State of egress point-to-multipoint branch LSP";
               }
             }
             container history {
               leaf history.category-heading {
                 type string;
               }
               leaf history.heading {
                 type string;
               }
               container history-element {
                 leaf log-time-stamp {
                   type string;
                 }
                 leaf log-event {
                   type string;
                 }
                 leaf changed-entity {
                   type string;
                 }
               }
             }
           }
         }
         container automatic-site-timers {
           leaf automatic-site-timers.heading {
             type string;
           }
           leaf automatic-site-startup-wait-time {
             type string;
           }
           leaf automatic-site-new-site-wait-time {
             type string;
           }
           leaf automatic-site-collision-detect-time {
             type string;
           }
           leaf automatic-site-reclaim-wait-time {
             type string;
           }
         }
         container connections-summary {
           leaf vc-up-count {
             type int32;
           }
           leaf vc-down-count {
             type int32;
           }
         }
       }
       list ldp-vpls-reference-site {
         leaf vpls-signaling-protocol-identifier {
           type string;
         }
         leaf local-site-id {
           type string;
         }
         leaf vpls-id {
           type int32;
           description "VPLS instance identifier";
         }
         leaf l2vpn-id {
           type string;
         }
         leaf local-id {
           type jt:ipaddr;
         }
         leaf num-local-interfaces {
           type int32;
         }
         leaf num-local-interfaces-up {
           type int32;
         }
         leaf irb-present {
           type string;
         }
         leaf mesh-group-count {
           type int32;
         }
         leaf mesh-group-up-count {
           type int32;
         }
         leaf remote-site-id {
           type string;
         }
         list mesh-group-interfaces {
           leaf mesh-group-name {
             type string;
             description "Name of mesh-group";
           }
           leaf mesh-group-state {
             type string;
             description "Mesh-group state";
           }
           leaf mesh-group-id {
             type int32;
             description "Mesh-group Identifier";
           }
           list interface {
             leaf interface-name {
               type string;
               description "Name of interface";
             }
             leaf interface-description {
               type string;
             }
             leaf interface-flags-description {
               type string;
             }
             leaf interface-flags {
               type int32;
             }
           }
         }
         list interface {
           leaf interface-name {
             type string;
             description "Name of interface";
           }
           leaf interface-id {
             type int32;
           }
           leaf interface-description {
             type string;
           }
           leaf interface-flags-description {
             type string;
           }
           leaf interface-flags {
             type int32;
           }
         }
         list connection {
           leaf-list connection.heading {
             type string;
           }
           leaf connection-id {
             type string;
           }
           leaf connection-type {
             type string;
           }
           leaf connection-status {
             type string;
           }
           leaf last-change {
             type string;
           }
           leaf up-transitions {
             type int32;
           }
           leaf remote-pe {
             type jt:ipaddr;
           }
           leaf control-word {
             type string;
           }
           leaf control-word-type {
             type string;
           }
           leaf interface-encapsulation {
             type string;
           }
           leaf inbound-label {
             type string;
           }
           leaf outbound-label {
             type string;
           }
           leaf pw-status-tlv {
             type string;
           }
           leaf local-pw-status-code {
             type int32;
           }
           leaf remote-pw-status-code {
             type int32;
           }
           leaf connection-protection {
             type string;
           }
           leaf mesh-group-name {
             type string;
             description "Name of mesh-group";
           }
           leaf vc-flow-label-transmit {
             type string;
           }
           leaf vc-flow-label-receive {
             type string;
           }
           leaf auto-sensed {
             type empty;
             description "Auto-sensed";
           }
           container local-interface {
             leaf interface-name {
               type string;
               description "Name of interface";
             }
             leaf interface-status {
               type string;
             }
             leaf interface-encapsulation {
               type string;
             }
             leaf working-status {
               type string;
             }
             leaf profile-name {
               type string;
             }
             leaf profile-varset-name {
               type string;
             }
             leaf interface-description {
               type string;
             }
           }
           container remote-interface {
             leaf interface-name {
               type string;
               description "Name of interface";
             }
             leaf interface-status {
               type string;
             }
             leaf interface-encapsulation {
               type string;
             }
           }
           container connection-bandwidth {
             leaf connection-bandwidth.heading {
               type string;
               description "Bandwidth of a layer 2 connection";
             }
             leaf bandwidth {
               type int32;
             }
             leaf class-type {
               type int32;
             }
             leaf class-bandwidth {
               type int32;
             }
           }
           container vpls-rsvp-te-p2mp-lsp-information {
             leaf vpls-ingress-p2mp-branch-lsp-name {
               type string;
               description "Name of ingress point-to-multipoint branch LSP";
             }
             leaf vpls-ingress-p2mp-branch-lsp-state {
               type string;
               description "State of ingress point-to-multipoint branch LSP";
             }
             leaf vpls-egress-p2mp-branch-lsp-name {
               type string;
               description "Name of egress point-to-multipoint branch LSP";
             }
             leaf vpls-egress-p2mp-branch-lsp-state {
               type string;
               description "State of egress point-to-multipoint branch LSP";
             }
           }
           container history {
             leaf history.category-heading {
               type string;
             }
             leaf history.heading {
               type string;
             }
             container history-element {
               leaf log-time-stamp {
                 type string;
               }
               leaf log-event {
                 type string;
               }
               leaf changed-entity {
                 type string;
               }
             }
           }
         }
         list mesh-group-connection {
           leaf mesh-group-name {
             type string;
             description "Name of mesh-group";
           }
           list connection {
             leaf-list connection.heading {
               type string;
             }
             leaf connection-id {
               type string;
             }
             leaf connection-type {
               type string;
             }
             leaf connection-status {
               type string;
             }
             leaf last-change {
               type string;
             }
             leaf up-transitions {
               type int32;
             }
             leaf remote-pe {
               type jt:ipaddr;
             }
             leaf control-word {
               type string;
             }
             leaf control-word-type {
               type string;
             }
             leaf interface-encapsulation {
               type string;
             }
             leaf inbound-label {
               type string;
             }
             leaf outbound-label {
               type string;
             }
             leaf pw-status-tlv {
               type string;
             }
             leaf local-pw-status-code {
               type int32;
             }
             leaf remote-pw-status-code {
               type int32;
             }
             leaf connection-protection {
               type string;
             }
             leaf mesh-group-name {
               type string;
               description "Name of mesh-group";
             }
             leaf vc-flow-label-transmit {
               type string;
             }
             leaf vc-flow-label-receive {
               type string;
             }
             leaf auto-sensed {
               type empty;
               description "Auto-sensed";
             }
             container local-interface {
               leaf interface-name {
                 type string;
                 description "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container remote-interface {
               leaf interface-name {
                 type string;
                 description "Name of interface";
               }
               leaf interface-status {
                 type string;
               }
               leaf interface-encapsulation {
                 type string;
               }
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
             container vpls-rsvp-te-p2mp-lsp-information {
               leaf vpls-ingress-p2mp-branch-lsp-name {
                 type string;
                 description "Name of ingress point-to-multipoint branch LSP";
               }
               leaf vpls-ingress-p2mp-branch-lsp-state {
                 type string;
                 description "State of ingress point-to-multipoint branch LSP";
               }
               leaf vpls-egress-p2mp-branch-lsp-name {
                 type string;
                 description "Name of egress point-to-multipoint branch LSP";
               }
               leaf vpls-egress-p2mp-branch-lsp-state {
                 type string;
                 description "State of egress point-to-multipoint branch LSP";
               }
             }
             container history {
               leaf history.category-heading {
                 type string;
               }
               leaf history.heading {
                 type string;
               }
               container history-element {
                 leaf log-time-stamp {
                   type string;
                 }
                 leaf log-event {
                   type string;
                 }
                 leaf changed-entity {
                   type string;
                 }
               }
             }
           }
         }
         container connections-summary {
           leaf vc-up-count {
             type int32;
           }
           leaf vc-down-count {
             type int32;
           }
         }
       }
       container vpls-protocol-state {
         leaf vpls-signaling-protocol-identifier {
           type string;
         }
         leaf num-local-interfaces {
           type int32;
         }
         leaf num-local-interfaces-up {
           type int32;
         }
         leaf irb-present {
           type string;
         }
         leaf mesh-group-count {
           type int32;
         }
         leaf mesh-group-up-count {
           type int32;
         }
         list mesh-group-interfaces {
           list interface {
             leaf interface-name {
               type string;
               description "Name of interface";
             }
             leaf interface-flags {
               type int32;
             }
           }
         }
         list interface {
           leaf interface-name {
             type string;
             description "Name of interface";
           }
           leaf interface-flags {
             type int32;
           }
         }
         list mesh-group-connection {
           leaf mesh-group-name {
             type string;
             description "Name of mesh-group";
           }
           list connection {
             leaf-list connection.heading {
               type string;
             }
             leaf remote-pe {
               type jt:ipaddr;
             }
             leaf l2vpn-local-site-id {
               type int32;
               description "Local site identifier";
             }
             leaf l2vpn-remote-site-id {
               type int32;
               description "Remote site identifier";
             }
             leaf connection-status {
               type string;
             }
             leaf last-change {
               type string;
             }
             leaf inbound-label {
               type string;
             }
             leaf outbound-label {
               type string;
             }
             container local-interface {
               leaf interface-name {
                 type string;
                 description "Name of interface";
               }
               leaf interface-status {
                 type string;
               }
               leaf interface-encapsulation {
                 type string;
               }
               leaf working-status {
                 type string;
               }
               leaf profile-name {
                 type string;
               }
               leaf profile-varset-name {
                 type string;
               }
               leaf interface-description {
                 type string;
               }
             }
             container connection-bandwidth {
               leaf connection-bandwidth.heading {
                 type string;
                 description "Bandwidth of a layer 2 connection";
               }
               leaf bandwidth {
                 type int32;
               }
               leaf class-type {
                 type int32;
               }
               leaf class-bandwidth {
                 type int32;
               }
             }
             container vpls-rsvp-te-p2mp-lsp-information {
               leaf vpls-ingress-p2mp-branch-lsp-name {
                 type string;
                 description "Name of ingress point-to-multipoint branch LSP";
               }
               leaf vpls-ingress-p2mp-branch-lsp-state {
                 type string;
                 description "State of ingress point-to-multipoint branch LSP";
               }
               leaf vpls-egress-p2mp-branch-lsp-name {
                 type string;
                 description "Name of egress point-to-multipoint branch LSP";
               }
               leaf vpls-egress-p2mp-branch-lsp-state {
                 type string;
                 description "State of egress point-to-multipoint branch LSP";
               }
             }
             container history {
               leaf history.category-heading {
                 type string;
               }
               leaf history.heading {
                 type string;
               }
               container history-element {
                 leaf log-time-stamp {
                   type string;
                 }
                 leaf log-event {
                   type string;
                 }
                 leaf changed-entity {
                   type string;
                 }
               }
             }
           }
           container connections-summary {
             leaf vc-up-count {
               type int32;
             }
             leaf vc-down-count {
               type int32;
             }
           }
         }
         list reference-site {
           leaf automatic-site-name {
             type string;
             description "VPLS automatic site name";
           }
           leaf automatic-site-id-status {
             type string;
             description "VPLS automatic site identifier status";
           }
           leaf automatic-site-claim-id {
             type int32;
             description "Claim site identifier";
           }
           leaf automatic-site-collisions {
             type int32;
             description "Number of collisions";
           }
           leaf automatic-site-timer-status {
             type string;
             description "VPLS automatic site timer status";
           }
           leaf vpls-signaling-protocol-identifier {
             type string;
           }
           leaf local-site-id {
             type string;
           }
           leaf source-attachment-id {
             type string;
             description "Local source attachment identifier";
           }
           leaf vpls-id {
             type int32;
             description "VPLS instance identifier";
           }
           leaf l2vpn-id {
             type string;
           }
           leaf local-id {
             type jt:ipaddr;
           }
           leaf num-local-interfaces {
             type int32;
           }
           leaf num-local-interfaces-up {
             type int32;
           }
           leaf irb-present {
             type string;
           }
           leaf mesh-group-count {
             type int32;
           }
           leaf mesh-group-up-count {
             type int32;
           }
           leaf remote-site-id {
             type string;
           }
           leaf target-attachment-id {
             type string;
             description "Remote target attachment identifier";
           }
           list mesh-group-interfaces {
             leaf mesh-group-name {
               type string;
               description "Name of mesh-group";
             }
             leaf mesh-group-state {
               type string;
               description "Mesh-group state";
             }
             leaf mesh-group-id {
               type int32;
               description "Mesh-group Identifier";
             }
             list interface {
               leaf interface-name {
                 type string;
                 description "Name of interface";
               }
               leaf interface-description {
                 type string;
               }
               leaf interface-flags-description {
                 type string;
               }
               leaf interface-flags {
                 type int32;
               }
             }
           }
           list interface {
             leaf interface-name {
               type string;
               description "Name of interface";
             }
             leaf interface-id {
               type int32;
             }
             leaf interface-description {
               type string;
             }
             leaf interface-flags-description {
               type string;
             }
             leaf interface-flags {
               type int32;
             }
           }
           list connection {
             container history {
             }
           }
           list mesh-group-connection {
             list connection {
               container history {
               }
             }
           }
         }
       }
       container vpls-rsvp-te-ingress-p2mp-lsp {
         leaf vpls-ingress-p2mp-lsp-name {
           type string;
           description "Name of ingress point-to-multipoint LSP";
         }
         leaf vpls-rsvp-te-p2mp-flood-nexthop-id {
           type int32;
           description "Identifier for VPLS RSVP traffic-engineering ingress flood next hop";
         }
       }
       container multihome {
         leaf multihome.heading {
           type string;
         }
         list multihome-site {
           leaf multihome-site-name {
             type string;
             description "Name of site";
           }
           leaf multihome-site-id {
             type int32;
             description "Site Identifier";
           }
           leaf multihome-site-preference {
             type int32;
             description "Site Preference";
           }
           leaf multihome-site-state {
             type string;
             description "Site state";
           }
           leaf multihome-num-interfaces {
             type int32;
           }
           leaf multihome-num-interfaces-up {
             type int32;
           }
           list interface {
             leaf interface-name {
               type string;
               description "Name of interface";
             }
             leaf interface-id {
               type int32;
             }
             leaf interface-description {
               type string;
             }
             leaf interface-flags-description {
               type string;
             }
             leaf interface-flags {
               type int32;
             }
           }
           container remote-advertisements {
             leaf remote-advertisements.heading {
               type string;
             }
             list remote-adv {
               leaf remote-adv-addr {
                 type string;
               }
               leaf remote-adv-preference {
                 type int32;
                 description "Remote PE preference";
               }
               leaf remote-adv-ctrl-flag {
                 type int32;
                 description "Remote PE Control flags";
               }
               leaf remote-adv-ctrl-flag-description {
                 type string;
                 description "Control flags description";
               }
             }
           }
         }
       }
       container history {
         leaf history.category-heading {
           type string;
         }
         leaf history.heading {
           type string;
         }
         container history-element {
           leaf log-time-stamp {
             type string;
           }
           leaf log-event {
             type string;
           }
           leaf changed-entity {
             type string;
           }
         }
       }
     }
   }
 }
