/*
 * Copyright (c) 2024 Juniper Networks, Inc.
 * All rights reserved.
 */
 module junos-rpc-storm-control {
   namespace "http://yang.juniper.net/junos/rpc/storm-control";

   prefix storm-control;

   import junos-common-types {
     prefix jt;
     revision-date 2023-01-01;
   }

   organization "Juniper Networks, Inc.";

   contact "yang-support@juniper.net";

   description "Junos RPC YANG module for storm-control command(s)";

   revision 2023-01-01 {
     description "Junos: 23.2R2.21";
   }

   rpc get-l2ng-storm-control-profiles-information {
     description "Show stormcontrol profile names and ids";
     output {
       container l2ng-storm-control-profiles-information {
         uses l2ng-storm-control-profiles-information-block;
       }
     }
   }
   rpc get-l2ng-storm-control-interface-information {
     description "Show stormcontrol information of the interface";
     input {
       leaf verbosity {
         default "brief";
         type enumeration {
           enum "detail" {
             description "Display detailed output";
           }
           enum "brief" {
             description "Display brief output";
           }
           enum "extensive" {
             description "Display extensive output";
           }
         }
       }
     }
     output {
       container l2ng-storm-control-interface-information {
         uses l2ng-storm-control-interface-information-block;
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping l2ng-storm-control-profiles-information-block {
     list l2ng-storm-control-profile-entry {
       leaf l2ng-profile-id {
         type uint32;
         description "Stormcontrol profile Id";
       }
       leaf l2ng-profile-name1 {
         type string;
         description "Stormcontrol profile name";
       }
     }
   }
   grouping l2ng-storm-control-interface-information-block {
     list l2ng-storm-control-interface-entry {
       leaf l2ng-storm-control-interface-name {
         type string;
         description "Interface Name";
       }
       leaf l2ng-storm-in-effect {
         type string;
         description "Storm is in effect";
       }
       leaf l2ng-storm-time-to-recover {
         type string;
         description "Time left to bringup the port";
       }
       leaf l2ng-storm-control-profile-name {
         type string;
         description "Stormcontrol profile name";
       }
       leaf l2ng-storm-control-ifl-level-support {
         type string;
         description "IFL levle stormcontrol enabled";
       }
       leaf l2ng-storm-control-profile-action {
         type string;
         description "Stormcontrol profile action: drop or shutdown";
       }
       leaf l2ng-last-storm-hit-time {
         type string;
         description "Timestamp of recent storm hit";
       }
       leaf l2ng-last-storm-clear-time {
         type string;
         description "Timestamp of recent storm clear";
       }
     }
   }
 }
