/*
 * Copyright (c) 2024 Juniper Networks, Inc.
 * All rights reserved.
 */
 module junos-ex-rpc-clear {
   namespace "http://yang.juniper.net/junos-ex/rpc/clear";

   prefix clear;

   import junos-common-ddl-extensions {
     prefix junos;
     revision-date 2023-01-01;
   }

   import junos-common-types {
     prefix jt;
     revision-date 2023-01-01;
   }

   organization "Juniper Networks, Inc.";

   contact "yang-support@juniper.net";

   description "Junos RPC YANG module for clear command(s)";

   revision 2023-01-01 {
     description "Junos: 23.2R2.21";
   }

   rpc clear-cli-logical-system {
     description "Clear logical system association";
     junos:command "clear cli logical-system";
     output {
       choice output_c {
         case output-tag {
           leaf output {
             type string;
           }
         }
         case multichassis-tag {
           anyxml multi-routing-engine-results;
         }
       }
     }
   }
   rpc clear-cli-tenant {
     description "Clear teannt association";
     junos:command "clear cli tenant";
     output {
       choice output_c {
         case output-tag {
           leaf output {
             type string;
           }
         }
         case multichassis-tag {
           anyxml multi-routing-engine-results;
         }
       }
     }
   }
   rpc clear-cli-satellite {
     description "Clear satellite association";
     junos:command "clear cli satellite";
     output {
       choice output_c {
         case output-tag {
           leaf output {
             type string;
           }
         }
         case multichassis-tag {
           anyxml multi-routing-engine-results;
         }
       }
     }
   }
   rpc clear-system-commit {
     description "Clear all pending commit requests";
     junos:command "clear system commit";
     input {
       leaf prepared {
         description "Clear prepared commit";
         type empty;
       }
     }
     output {
       choice output_c {
         case output-tag {
           leaf output {
             type string;
           }
         }
         case multichassis-tag {
           anyxml multi-routing-engine-results;
         }
       }
     }
   }
   rpc clear-pending-commit-sync-jobs {
     description "Clear pending commit synchronize jobs";
     junos:command "clear system commit synchronize-server pending-jobs";
     output {
       choice output_c {
         case output-tag {
           leaf output {
             type string;
           }
         }
         case multichassis-tag {
           anyxml multi-routing-engine-results;
         }
       }
     }
   }
   rpc clear-system-login-lockout {
     description "Clear login locks on user accounts";
     junos:command "clear system login lockout";
     input {
       choice lockout-choice {
         case all {
           leaf all {
             description "Clear login locks on all user acounts";
             type empty;
           }
         }
         case user {
           leaf user {
             description "Name of user";
             type string;
           }
         }
       }
     }
     output {
       container clear-system-login-lockout {
         uses clear-system-login-lockout-block;
       }
     }
   }
   rpc clear-boot-media {
     description "Clear permanent boot media settings";
     junos:command "clear system boot-media";
     input {
       leaf media {
         description "Media to be cleared from boot device list";
         junos:cli-feature "nokeyword";
         type enumeration {
           enum "external" {
             description "Disable booting from external USB device";
           }
         }
         mandatory true;
       }
     }
     output {
       choice output_c {
         case output-tag {
           leaf output {
             type string;
           }
         }
         case multichassis-tag {
           anyxml multi-routing-engine-results;
         }
       }
     }
   }
   rpc clear-reboot {
     description "Clear all pending halt or reboot requests";
     junos:command "clear system reboot";
     input {
       uses command-forwarding;
       leaf both-routing-engines {
         description "Clear halt or reboot on both Routing Engines";
         type empty;
       }
     }
     output {
       container clear-reboot-status {
         uses clear-reboot-status-block;
       }
     }
   }
   rpc clear-dhcp-binding-information {
     description "Clear DHCP client binding information";
     junos:command "clear system services dhcp binding";
     input {
       uses command-forwarding;
       leaf address {
         description "Address of DHCP client binding";
         junos:cli-feature "nokeyword";
         type jt:ipaddr;
       }
     }
     output {
       choice output_c {
         case output-tag {
           leaf output {
             type string;
           }
         }
         case multichassis-tag {
           anyxml multi-routing-engine-results;
         }
       }
     }
   }
   rpc clear-dhcp-conflict-information {
     description "Clear DHCP address conflict";
     junos:command "clear system services dhcp conflict";
     input {
       uses command-forwarding;
       leaf address {
         description "DHCP conflict address";
         junos:cli-feature "nokeyword";
         type jt:ipaddr;
       }
     }
     output {
       choice output_c {
         case output-tag {
           leaf output {
             type string;
           }
         }
         case multichassis-tag {
           anyxml multi-routing-engine-results;
         }
       }
     }
   }
   rpc clear-dhcp-statistics-information {
     description "Clear DHCP statistics";
     junos:command "clear system services dhcp statistics";
     input {
       uses command-forwarding;
     }
     output {
       choice output_c {
         case output-tag {
           leaf output {
             type string;
           }
         }
         case multichassis-tag {
           anyxml multi-routing-engine-results;
         }
       }
     }
   }
   rpc clear-subscriber-management-statistics {
     description "Clear subscriber management statistics";
     junos:command "clear system subscriber-management statistics";
     output {
       container bbe-smgd-generic-command {
         uses bbe-smgd-generic-command-block;
       }
     }
   }
   rpc clear-subscriber-management-arp {
     description "Clear subscriber management arp information";
     junos:command "clear system subscriber-management arp";
     output {
       container bbe-smgd-generic-command {
         uses bbe-smgd-generic-command-block;
       }
     }
   }
   rpc clear-subscriber-management-arp-interface {
     description "Name of interface";
     junos:command "clear system subscriber-management arp interface";
     input {
       leaf interface-name {
         description "Name of interface";
         junos:cli-feature "nokeyword";
         type string;
         mandatory true;
       }
     }
   }
   rpc clear-subscriber-management-arp-address {
     description "Ipv4 address";
     junos:command "clear system subscriber-management arp address";
     input {
       leaf ip-address {
         description "Ipv4 address";
         junos:cli-feature "nokeyword";
         type jt:ipv4addr;
         mandatory true;
       }
     }
   }
   rpc clear-subscriber-management-ipv6-neighbors {
     description "Clear subscriber management ipv6 neighbors information";
     junos:command "clear system subscriber-management ipv6-neighbors";
     output {
       container bbe-smgd-generic-command {
         uses bbe-smgd-generic-command-block;
       }
     }
   }
   rpc clear-subscriber-management-ipv6-neighbor-interface {
     description "Name of interface";
     junos:command "clear system subscriber-management ipv6-neighbors interface";
     input {
       leaf interface-name {
         description "Name of interface";
         junos:cli-feature "nokeyword";
         type string;
         mandatory true;
       }
     }
   }
   rpc clear-subscriber-management-ipv6-neighbor-address {
     description "Ipv6 address";
     junos:command "clear system subscriber-management ipv6-neighbors address";
     input {
       leaf interface-name {
         description "Ipv6 address";
         junos:cli-feature "nokeyword";
         type jt:ipv6addr;
         mandatory true;
       }
     }
   }
   rpc clear-security-alarm-information {
     description "Clear (acknowledge) security alarms";
     junos:command "clear security alarms";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf all {
         description "Clear (acknowledge) all security alarms";
         type empty;
       }
     }
     output {
       container clear-security-alarm-results {
         uses clear-security-alarm-results-block;
       }
     }
   }
   rpc clear-security-log-information {
     description "Clear auditable security logs";
     junos:command "clear security log";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         junos:cli-feature "nokeyword";
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf all {
         description "Clear all security log entries";
         type empty;
       }
     }
   }
   rpc clear-pki-certificate-request {
     description "Clear router certificate request";
     junos:command "clear security pki certificate-request";
     input {
       uses command-forwarding;
       choice daemon-select {
         case logical-system {
         }
       }
       choice certificate-request-choice {
         case certificate-id {
           leaf certificate-id {
             description "Certificate identifier";
             type string {
               length "1 .. 32";
               junos:posix-pattern "![/%. ]";
               junos:pattern-message "Must not contain \'/\', %, \'.\' or a space";
             }
           }
         }
         case all {
           leaf all {
             description "Clear all certificate requests";
             type empty;
           }
         }
       }
     }
     output {
       choice output_c {
         case output-tag {
           leaf output {
             type string;
           }
         }
         case multichassis-tag {
           anyxml multi-routing-engine-results;
         }
       }
     }
   }
   rpc clear-pki-ca-certificate {
     description "Clear CA/RA certificate";
     junos:command "clear security pki ca-certificate";
     input {
       uses command-forwarding;
       choice daemon-select {
         case logical-system {
         }
       }
       choice ca-choice {
         case ca-profile {
           leaf ca-profile {
             description "Certificate authority profile";
             type string {
               length "1 .. 32";
               junos:posix-pattern "![/%. ]";
               junos:pattern-message "Must not contain \'/\', %, \'.\' or a space";
             }
           }
         }
         case ca-profile-group {
           leaf ca-profile-group {
             description "Clear CA profile group";
             type string {
               length "1 .. 32";
               junos:posix-pattern "![/%. ]";
               junos:pattern-message "Must not contain \'/\', %, \'.\' or a space";
             }
           }
         }
         case all {
           leaf all {
             description "Clear all CA certificates";
             type empty;
           }
         }
       }
     }
     output {
       choice output_c {
         case output-tag {
           leaf output {
             type string;
           }
         }
         case multichassis-tag {
           anyxml multi-routing-engine-results;
         }
       }
     }
   }
   rpc clear-node-local-certificate-request {
     description "Clear router certificate request";
     junos:command "clear security pki node-local certificate-request";
     input {
       uses command-forwarding;
       choice daemon-select {
         case logical-system {
         }
       }
       choice certificate-request-choice {
         case certificate-id {
           leaf certificate-id {
             description "Certificate identifier";
             type string {
               length "1 .. 32";
               junos:posix-pattern "![/%. ]";
               junos:pattern-message "Must not contain \'/\', %, \'.\' or a space";
             }
           }
         }
         case all {
           leaf all {
             description "Clear all certificate requests";
             type empty;
           }
         }
       }
     }
     output {
       choice output_c {
         case output-tag {
           leaf output {
             type string;
           }
         }
         case multichassis-tag {
           anyxml multi-routing-engine-results;
         }
       }
     }
   }
   rpc clear-node-local-local-certificate {
     description "Clear local certificate";
     junos:command "clear security pki node-local local-certificate";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain \'/\', %, \'.\' or a space";
             }
           }
         }
         case system-generated {
           leaf system-generated {
             description "Clear autogenerated self-signed certificate";
             type empty;
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-node-local-key-pair {
     description "Clear key pair";
     junos:command "clear security pki node-local key-pair";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain \'/\', %, \'.\' or a space";
             }
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-acme-account-request {
     description "Clear ACME account";
     junos:command "clear security pki acme account";
     input {
       uses command-forwarding;
       choice daemon-select {
         case logical-system {
         }
       }
       leaf ca-profile {
         description "Certificate authority profile";
         type string {
           length "1 .. 32";
           junos:posix-pattern "![/%. ]";
           junos:pattern-message "Must not contain \'/\', %, \'.\' or a space";
         }
         mandatory true;
       }
       leaf acme-key-id {
         description "Key identifier";
         type string {
           length "1 .. 32";
           junos:posix-pattern "![/%. ]";
           junos:pattern-message "Must not contain \'/\', %, \'.\' or a space";
         }
       }
     }
     output {
       choice output_c {
         case output-tag {
           leaf output {
             type string;
           }
         }
         case multichassis-tag {
           anyxml multi-routing-engine-results;
         }
       }
     }
   }
   rpc clear-pki-key-pair {
     description "Clear key pair";
     junos:command "clear security pki key-pair";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain \'/\', %, \'.\' or a space";
             }
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-local-certificate {
     description "Clear local certificate";
     junos:command "clear security pki local-certificate";
     input {
       uses command-forwarding;
       choice daemon-select {
         case logical-system {
         }
       }
       choice certificate-choice {
         case certificate-id {
           leaf certificate-id {
             description "Certificate identifier";
             type string {
               length "1 .. 32";
               junos:posix-pattern "![/%. ]";
               junos:pattern-message "Must not contain \'/\', %, \'.\' or a space";
             }
           }
         }
         case system-generated {
           leaf system-generated {
             description "Clear autogenerated self-signed certificate";
             type empty;
           }
         }
         case all {
           leaf all {
             description "Clear all local certificates";
             type empty;
           }
         }
       }
     }
     output {
       choice output_c {
         case output-tag {
           leaf output {
             type string;
           }
         }
         case multichassis-tag {
           anyxml multi-routing-engine-results;
         }
       }
     }
   }
   rpc clear-pki-crl {
     description "Clear certificate revocation list";
     junos:command "clear security pki crl";
     input {
       uses command-forwarding;
       choice daemon-select {
         case logical-system {
         }
       }
       choice ca-choice {
         case ca-profile {
           leaf ca-profile {
             description "Certificate authority profile";
             type string {
               length "1 .. 32";
               junos:posix-pattern "![/%. ]";
               junos:pattern-message "Must not contain \'/\', %, \'.\' or a space";
             }
           }
         }
         case all {
           leaf all {
             description "Clear all CRLs";
             type empty;
           }
         }
       }
     }
     output {
       choice output_c {
         case output-tag {
           leaf output {
             type string;
           }
         }
         case multichassis-tag {
           anyxml multi-routing-engine-results;
         }
       }
     }
   }
   rpc clear-pki-statistics {
     description "Clear PKI related statistics";
     junos:command "clear security pki statistics";
     input {
       uses command-forwarding;
     }
     output {
       choice output_c {
         case output-tag {
           leaf output {
             type string;
           }
         }
         case multichassis-tag {
           anyxml multi-routing-engine-results;
         }
       }
     }
   }
   rpc clear-gvpn-ipsec-security-association {
     description "Clear IPSec dynamic security associations";
     junos:command "clear security group-vpn member ipsec security-associations";
     input {
       uses command-forwarding;
       leaf index {
         description "Index of security association";
         type union {
           type string {
             pattern "<.*>|$.*";
           }
           type uint32 {
             range "10001 .. 20000";
           }
         }
       }
       leaf group-id {
         description "Group VPN identification number";
         type union {
           type string {
             pattern "<.*>|$.*";
           }
           type uint32 {
             range "1 .. 4294967295";
           }
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-gvpn-ipsec-security-association-statistics {
     description "Clear IPSec security associations statistics";
     junos:command "clear security group-vpn member ipsec security-associations statistics";
     input {
       leaf group-id {
         description "Group VPN identification number";
         type union {
           type string {
             pattern "<.*>|$.*";
           }
           type uint32 {
             range "1 .. 4294967295";
           }
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-gvpn-ipsec-statistics {
     description "Clear Group VPN IPSec statistics";
     junos:command "clear security group-vpn member ipsec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf index {
         description "Index of security association";
         type union {
           type string {
             pattern "<.*>|$.*";
           }
           type uint32 {
             range "10001 .. 20000";
           }
         }
       }
     }
     output {
       choice output_c {
         case output-tag {
           leaf output {
             type string;
           }
         }
         case multichassis-tag {
           anyxml multi-routing-engine-results;
         }
       }
     }
   }
   rpc clear-group-vpn-ike-security-associations {
     description "Clear group VPN IKE security associations";
     junos:command "clear security group-vpn member ike security-associations";
     input {
       uses command-forwarding;
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
       leaf peer-address {
         description "IP address of the peer";
         junos:cli-feature "nokeyword";
         type jt:ipaddr;
       }
       leaf index {
         description "Index of security association";
         default "0";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-gvpn-group-information {
     description "Clear IPSec Group VPN";
     junos:command "clear security group-vpn member group";
     input {
       uses command-forwarding;
       leaf group-id {
         description "Group VPN identification number";
         type union {
           type string {
             pattern "<.*>|$.*";
           }
           type uint32 {
             range "1 .. 4294967295";
           }
         }
       }
       leaf vpn {
         description "Group VPN Name";
         type string {
           length "1 .. 32";
         }
       }
       leaf service-set {
         description "Service set name";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-mka-statistics {
     description "Clear MKA statistics information";
     junos:command "clear security mka statistics";
     output {
       container mka-statistics {
         uses mka-statistics-block;
       }
     }
   }
   rpc clear-mka-interface-statistics {
     description "Clear MKA statistics information on this interface";
     junos:command "clear security mka statistics interface";
     input {
       choice interface-choice {
         case interface-name {
           leaf interface-name {
             description "Name of interface";
             junos:cli-feature "nokeyword";
             type union {
               type jt:interface-name;
               type string {
                 pattern "<.*>|$.*";
               }
             }
           }
         }
         case all {
           leaf all {
             description "Clear mka statistics of all interfaces";
             junos:cli-feature "nokeyword";
             type string;
           }
         }
       }
     }
     output {
       container mka-statistics {
         uses mka-statistics-block;
       }
     }
   }
   rpc clear-log {
     description "Clear contents of log file";
     junos:command "clear log";
     input {
       leaf filename {
         description "Name of log file";
         junos:cli-feature "nokeyword";
         type string {
           junos:posix-pattern "![ =;|(){}]";
           junos:pattern-message "Must not contain any special characters";
         }
         mandatory true;
       }
       leaf all {
         description "Also delete all archive (.gz) files for specified file";
         type empty;
       }
       leaf tenant {
         description "Name of tenant";
         type string {
           junos:posix-pattern "^[a-zA-Z0-9-]{1,63}$";
           junos:pattern-message "Tenant name is a string consisting of up to 63 letters, numbers and dashes";
         }
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case multichassis-tag {
           anyxml multi-routing-engine-results;
         }
       }
     }
   }
   rpc clear-log-sset {
     description "Name of service-set";
     junos:command "clear log service-set";
     input {
       leaf filename {
         description "Name of log file";
         junos:cli-feature "nokeyword";
         type string {
           junos:posix-pattern "![ =;|(){}]";
           junos:pattern-message "Must not contain any special characters [ =;|(){}]";
         }
         mandatory true;
       }
     }
     output {
       choice output_c {
         case output-tag {
           leaf output {
             type string;
           }
         }
         case multichassis-tag {
           anyxml multi-routing-engine-results;
         }
       }
     }
   }
   rpc clear-log-pics {
     description "Name of interface";
     junos:command "clear log interface";
     input {
       leaf filename {
         description "Name of log file";
         junos:cli-feature "nokeyword";
         type string {
           junos:posix-pattern "![ =;|(){}]";
           junos:pattern-message "Must not contain any special characters [ =;|(){}]";
         }
         mandatory true;
       }
     }
     output {
       choice output_c {
         case output-tag {
           leaf output {
             type string;
           }
         }
         case multichassis-tag {
           anyxml multi-routing-engine-results;
         }
       }
     }
   }
   rpc clear-request-response-clients {
     description "Clear client sessions";
     junos:command "clear extension-service request-response clients";
     input {
       leaf client-id {
         description "Client ID of session to be terminated";
         type string;
         mandatory true;
       }
     }
     output {
       container clear-request-response-client-information {
         uses clear-request-response-client-information-block;
       }
     }
   }
   rpc clear-rfc2544-information {
     description "Clear rfc2544 information";
     junos:command "clear services rpm rfc2544-benchmarking";
     output {
       choice output_c {
         case output-tag {
           leaf output {
             type string;
           }
         }
         case multichassis-tag {
           anyxml multi-routing-engine-results;
         }
       }
     }
   }
   rpc clear-active-tests-information {
     description "Clear rfc2544 active tests";
     junos:command "clear services rpm rfc2544-benchmarking active-tests";
     input {
       leaf test-id {
         description "Test id";
         junos:cli-feature "nokeyword";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-aborted-tests-information {
     description "Clear rfc2544 aborted tests";
     junos:command "clear services rpm rfc2544-benchmarking aborted-tests";
     input {
       leaf test-id {
         description "Test id";
         junos:cli-feature "nokeyword";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-completed-tests-information {
     description "Clear rfc2544 completed tests";
     junos:command "clear services rpm rfc2544-benchmarking completed-tests";
     input {
       leaf test-id {
         description "Test id";
         junos:cli-feature "nokeyword";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-services-ipsec-vpn-security-associations {
     description "Clear IPSec dynamic security associations";
     junos:command "clear services ipsec-vpn ipsec security-associations";
     input {
       leaf service-set {
         description "Name of service set";
         junos:cli-feature "nokeyword";
         type string {
           junos:posix-pattern "^[A-Za-z0-9][_0-9A-Za-z-]{0,62}$";
           junos:pattern-message "Must be a string beginning with a number or letter and consisting of no more than 63 total letters, numbers, dashes and underscores.";
         }
       }
       leaf tunnel-index {
         description "Tunnel index";
         type union {
           type uint32;
           type string {
             pattern "<.*>|$.*";
           }
         }
       }
       leaf remote-gateway {
         description "Peer address to use as filter";
         type jt:ipaddr;
       }
     }
     output {
       choice output_c {
         case output-tag {
           leaf output {
             type string;
           }
         }
         case multichassis-tag {
           anyxml multi-routing-engine-results;
         }
       }
     }
   }
   rpc clear-ipsec-vpn-statistics {
     description "Clear IPSec statistics";
     junos:command "clear services ipsec-vpn ipsec statistics";
     input {
       leaf remote-gateway {
         description "Peer address to use as filter";
         type string;
       }
       leaf service-set {
         description "Name of service set";
         type string;
       }
     }
     output {
       choice output_c {
         case output-tag {
           leaf output {
             type string;
           }
         }
         case multichassis-tag {
           anyxml multi-routing-engine-results;
         }
       }
     }
   }
   rpc clear-services-ike-security-associations {
     description "Clear IKE security associations";
     junos:command "clear services ipsec-vpn ike security-associations";
     input {
       leaf peer-address {
         description "Name of security association";
         junos:cli-feature "nokeyword";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-services-ike-statistics {
     description "Clear IKE security associations statistics";
     junos:command "clear services ipsec-vpn ike statistics";
     input {
       leaf peer-address {
         description "Name of security association";
         junos:cli-feature "nokeyword";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-ipsec-certificates-service-set {
     description "Clear certificates for one or all service sets";
     junos:command "clear services ipsec-vpn certificates service-set";
     input {
       choice specific-or-all-service-set {
         case service-set {
           leaf service-set {
             description "Name of service set for which to clear certificates";
             junos:cli-feature "nokeyword";
             type string {
               junos:posix-pattern "^[A-Za-z0-9][_0-9A-Za-z-]{0,62}$";
               junos:pattern-message "Must be a string beginning with a number or letter and consisting of no more than 63 total letters, numbers, dashes and underscores.";
             }
           }
         }
         case all {
           leaf all {
             description "Clear all local and remote certificates";
             type empty;
           }
         }
       }
       leaf certificate-cache-entry {
         description "Certificate entry present in the cache";
         type union {
           type int32;
           type string {
             pattern "<.*>|$.*";
           }
         }
       }
     }
     output {
       choice output_c {
         case output-tag {
           leaf output {
             type string;
           }
         }
         case multichassis-tag {
           anyxml multi-routing-engine-results;
         }
       }
     }
   }
   rpc clear-service-accounting-information {
     description "Clear service accouting information";
     junos:command "clear services accounting";
     output {
       choice output_c {
         case output-tag {
           leaf output {
             type string;
           }
         }
         case multichassis-tag {
           anyxml multi-routing-engine-results;
         }
       }
     }
   }
   rpc clear-service-accounting-statistics {
     description "Clear all statistics";
     junos:command "clear services accounting statistics";
     output {
       choice output_c {
         case output-tag {
           leaf output {
             type string;
           }
         }
         case multichassis-tag {
           anyxml multi-routing-engine-results;
         }
       }
     }
   }
   rpc clear-service-accouting-flow {
     description "Clear service accouting flows";
     junos:command "clear services accounting flow";
     output {
       choice output_c {
         case output-tag {
           leaf output {
             type string;
           }
         }
         case multichassis-tag {
           anyxml multi-routing-engine-results;
         }
       }
     }
   }
   rpc clear-service-video-monitoring-information {
     description "Clear video monitoring service related counters";
     junos:command "clear services video-monitoring";
     output {
       choice output_c {
         case output-tag {
           leaf output {
             type string;
           }
         }
         case multichassis-tag {
           anyxml multi-routing-engine-results;
         }
       }
     }
   }
   rpc clear-service-video-monitoring-mdi-information {
     description "Clear video monitoring mdi counters";
     junos:command "clear services video-monitoring mdi";
     output {
       choice output_c {
         case output-tag {
           leaf output {
             type string;
           }
         }
         case multichassis-tag {
           anyxml multi-routing-engine-results;
         }
       }
     }
   }
   rpc clear-service-video-monitoring-mdi-statistics {
     description "Clear all statistics";
     junos:command "clear services video-monitoring mdi statistics";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-service-video-monitoring-mdi-errors {
     description "Clear all error counters";
     junos:command "clear services video-monitoring mdi errors";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-service-video-monitoring-mdi-alarm-information {
     description "Clear video monitoring mdi alarm counters";
     junos:command "clear services video-monitoring mdi alarm";
     output {
       choice output_c {
         case output-tag {
           leaf output {
             type string;
           }
         }
         case multichassis-tag {
           anyxml multi-routing-engine-results;
         }
       }
     }
   }
   rpc clear-services-video-monitoring-mdi-alarm-statistics {
     description "Clear all statistics";
     junos:command "clear services video-monitoring mdi alarm stats";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-services-video-monitoring-mdi-alarm-errors {
     description "Clear all errors";
     junos:command "clear services video-monitoring mdi alarm errors";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc clear-service-msp-flow-table-information {
     description "Remove established flows from flow table";
     junos:command "clear services flows";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       container service-msp-flow-drain-information {
         uses service-msp-flow-drain-information-block;
       }
     }
   }
   rpc clear-service-msp-session-table-information {
     description "Remove established sessions from sessions table";
     junos:command "clear services sessions";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       container service-msp-sess-drain-information {
         uses service-msp-sess-drain-information-block;
       }
     }
   }
   rpc clear-service-msp-session-analysis-information {
     description "Clear service session analysis counter statistics";
     junos:command "clear services sessions analysis";
     input {
       leaf interface {
         description "Name of extension provider interface";
         type string;
       }
     }
     output {
       container service-session-analysis-information {
         uses service-session-analysis-information-block;
       }
     }
   }
   rpc clear-service-msp-subscriber-analyis-counters-information {
     description "Remove established subscriber analysis counters";
     junos:command "clear services subscriber";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       container msp-service-subs-analysis-information {
         uses msp-service-subs-analysis-information-block;
       }
     }
   }
   rpc clear-service-subscriber-analysis-information {
     description "Clear service subscribers counter statistics";
     junos:command "clear services subscriber analysis";
     input {
       leaf interface {
         description "Name of extension provider interface";
         type string;
       }
     }
     output {
       container msp-service-subs-analysis-information {
         uses msp-service-subs-analysis-information-block;
       }
     }
   }
   rpc clear-service-pcp-epoch {
     description "Clear pcp epoch information";
     junos:command "clear services pcp epoch";
     input {
       leaf interface {
         description "Name of adaptive services interface";
         type string;
       }
       leaf server-name {
         description "Server name";
         type string;
       }
     }
     output {
       container service-pcp-epoch-information {
         uses service-pcp-epoch-information-block;
       }
     }
   }
   rpc clear-service-pcp-statistics {
     description "Clear PCP statistics";
     junos:command "clear services pcp statistics";
     input {
       leaf interface {
         description "Name of adaptive services interface";
         type string;
       }
     }
   }
   rpc clear-dhcp-service-statistics-information {
     description "Clear DHCP service statistics";
     junos:command "clear dhcp statistics";
     input {
       leaf interface {
         description "Name of interface";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-dhcp-relay-binding-information {
     description "Clear DHCP client binding information";
     junos:command "clear dhcp relay binding";
     input {
       choice binding-clear-choice {
         case address {
           leaf address {
             description "IP address or MAC address or Session Id of DHCP client binding";
             junos:cli-feature "nokeyword";
             type string;
           }
         }
         case interfaces-wildcard {
           leaf interfaces-wildcard {
             description "Interfaces to clear bindings on (can be '*' wildcard)";
             junos:cli-feature "nokeyword";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             junos:cli-feature "nokeyword";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       leaf bridge-domain {
         description "Name of bridge domain";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-interface-bindings {
     description "Name of interface on which to clear bindings";
     junos:command "clear dhcp relay binding interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-dhcp-relay-statistics-information {
     description "Clear DHCP statistics";
     junos:command "clear dhcp relay statistics";
     input {
       leaf routing-instance {
         description "Name of routing instance";
         type string;
       }
       leaf bridge-domain {
         description "Name of bridge domain";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-leasequery-statistics {
     description "Clear DHCP relay leasequery statistics";
     junos:command "clear dhcp relay statistics leasequery";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-bulk-leasequery-conn-statistics {
     description "Clear DHCP relay bulk leasequery conn statistics";
     junos:command "clear dhcp relay statistics bulk-leasequery-connections";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-lockout-entries-information {
     description "Clear DHCP lockout entries";
     junos:command "clear dhcp relay lockout-entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-alq-information-statistics-peer {
     description "Clear active-leasequery peer statistics";
     junos:command "clear dhcp relay active-leasequery statistics peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-relay-alq-info-statistics-interface {
     description "Clear active-leasequery interface statistics";
     junos:command "clear dhcp relay active-leasequery statistics interface";
     input {
       leaf interface-name {
         description "Active-leasequery interface name";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-binding-information {
     description "Clear DHCP client binding information";
     junos:command "clear dhcp server binding";
     input {
       choice binding-clear-choice {
         case address {
           leaf address {
             description "IP address or MAC address or Session Id of DHCP client binding";
             junos:cli-feature "nokeyword";
             type string;
           }
         }
         case interfaces-wildcard {
           leaf interfaces-wildcard {
             description "Interfaces to clear bindings on (can be '*' wildcard)";
             junos:cli-feature "nokeyword";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             junos:cli-feature "nokeyword";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-binding-interface {
     description "Name of interface on which to clear bindings";
     junos:command "clear dhcp server binding interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-server-statistics-information {
     description "Clear DHCP server statistics";
     junos:command "clear dhcp server statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-bulk-leasequery-statistics {
     description "Show DHCP server bulk leasequeery statistics";
     junos:command "clear dhcp server statistics bulk-leasequery-connections";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-lockout-entries-information {
     description "Clear DHCP lockout entries";
     junos:command "clear dhcp server lockout-entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-alq-info-statistics-peer {
     description "Clear active-leasequery peer statistics";
     junos:command "clear dhcp server active-leasequery statistics peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-server-alq-info-statistics-interface {
     description "Clear active-leasequery interface statistics";
     junos:command "clear dhcp server active-leasequery statistics interface";
     input {
       leaf interface-name {
         description "Active-leasequery interface name";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-client-binding-information {
     description "Clear DHCP client binding information";
     junos:command "clear dhcp client binding";
     input {
       choice binding-clear-choice {
         case interface {
           leaf interface {
             description "Name of interface";
             type string;
           }
         }
         case all {
           leaf all {
             description "Clear all bindings";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-client-statistics-information {
     description "Clear DHCP client statistics";
     junos:command "clear dhcp client statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-proxy-client-statistics-information {
     description "Clear DHCP client statistics";
     junos:command "clear dhcp proxy-client statistics";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-service-statistics-information {
     description "Clear DHCPv6 service statistics";
     junos:command "clear dhcpv6 statistics";
     input {
       leaf interface {
         description "Name of interface";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-dhcpv6-relay-binding-information {
     description "Clear DHCPv6 client binding information";
     junos:command "clear dhcpv6 relay binding";
     input {
       choice binding-clear-choice {
         case address {
           leaf address {
             description "IPv6 Prefix, session-id or CID of DHCPv6 client binding";
             junos:cli-feature "nokeyword";
             type string;
           }
         }
         case interfaces-wildcard {
           leaf interfaces-wildcard {
             description "Interfaces to clear bindings on (can be '*' wildcard)";
             junos:cli-feature "nokeyword";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             junos:cli-feature "nokeyword";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-binding-interface {
     description "Name of interface on which to clear bindings";
     junos:command "clear dhcpv6 relay binding interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-dhcpv6-relay-statistics-information {
     description "Clear DHCPv6 relay statistics";
     junos:command "clear dhcpv6 relay statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-leasequery-statistics {
     description "Clear DHCP relay leasequery statistics";
     junos:command "clear dhcpv6 relay statistics leasequery";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-bulk-leasequery-conn-statistics {
     description "Clear DHCP relay bulk leasequery conn statistics";
     junos:command "clear dhcpv6 relay statistics bulk-leasequery-connections";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-lockout-entries-information {
     description "Clear DHCP lockout entries";
     junos:command "clear dhcpv6 relay lockout-entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-alq-info-statistics-peer {
     description "Clear active-leasequery peer statistics";
     junos:command "clear dhcpv6 relay active-leasequery statistics peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-relay-alq-info-statistics-interface {
     description "Clear active-leasequery interface statistics";
     junos:command "clear dhcpv6 relay active-leasequery statistics interface";
     input {
       leaf interface-name {
         description "Active-leasequery interface name";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-binding-information {
     description "Clear DHCPv6 client binding information";
     junos:command "clear dhcpv6 server binding";
     input {
       choice binding-clear-choice {
         case address {
           leaf address {
             description "IPv6 Prefix, session-id or CID of DHCPv6 client binding";
             junos:cli-feature "nokeyword";
             type string;
           }
         }
         case interfaces-wildcard {
           leaf interfaces-wildcard {
             description "Interfaces to clear bindings on (can be '*' wildcard)";
             junos:cli-feature "nokeyword";
             type string {
               junos:posix-pattern "^( (((ge-)|(mge-)|(xe-)|(et-))( [[:digit:]]+(-([[:digit:]]+))+(-([[:digit:]]+)?)?)?) | (ae))+$";
               junos:pattern-message "Must be an interface wildcard string";
             }
           }
         }
         case interfaces-vlan {
           leaf interfaces-vlan {
             description "Interface VLAN-ID/SVLAN-ID on which to clear bindings";
             junos:cli-feature "nokeyword";
             type string {
               junos:posix-pattern "^(( (((ge-)|(mge-)|(xe-)|(et-))( [[:digit:]]+(-([[:digit:]]+))+(-([[:digit:]]+)?)?)?) | (ae))(/:)([[:digit:]]+(-[[:digit:]]+))?)+$";
               junos:pattern-message "Must be an interface:VLAN string";
             }
           }
         }
         case all {
           leaf all {
             description "Clear all bindings";
             type empty;
           }
         }
       }
       leaf routing-instance {
         description "Name of routing instance";
         type string;
       }
       choice force_choice {
         case dual-stack {
           leaf dual-stack {
             description "Clear dual stack bindings";
             type empty;
           }
         }
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-binding-interface {
     description "Name of interface on which to clear bindings";
     junos:command "clear dhcpv6 server binding interface";
     input {
       leaf interface-name {
         description "Name of interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-dhcpv6-server-statistics-information {
     description "Clear DHCPv6 server statistics";
     junos:command "clear dhcpv6 server statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-bulk-leasequery-statistics {
     description "Show DHCP server bulk leasequeery statistics";
     junos:command "clear dhcpv6 server statistics bulk-leasequery-connections";
     input {
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-lockout-entries-information {
     description "Clear DHCP lockout entries";
     junos:command "clear dhcpv6 server lockout-entries";
     input {
       choice clear-lockout-entry {
         case index {
           leaf index {
             description "Clear lockout entry by index";
             type union {
               type uint32;
               type string {
                 pattern "<.*>|$.*";
               }
             }
           }
         }
         case all {
           leaf all {
             description "Clear all lockout entry";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-alq-info-statistics-peer {
     description "Clear active-leasequery peer statistics";
     junos:command "clear dhcpv6 server active-leasequery statistics peer";
     input {
       leaf peer-address {
         description "Active-leasequery peer address";
         junos:cli-feature "nokeyword";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-server-alq-info-stats-interface {
     description "Clear active-leasequery interface statistics";
     junos:command "clear dhcpv6 server active-leasequery statistics interface";
     input {
       leaf interface-name {
         description "Active-leasequery interface name";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-client-binding-information {
     description "Clear DHCPV6 client binding information";
     junos:command "clear dhcpv6 client binding";
     input {
       choice binding-clear-choice {
         case interface {
           leaf interface {
             description "Name of interface";
             type string;
           }
         }
         case all {
           leaf all {
             description "Clear all bindings";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcpv6-client-statistics-information {
     description "Clear DHCPV6 client statistics";
     junos:command "clear dhcpv6 client statistics";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding {
     description "Clear dhcp-security bindings";
     junos:command "clear dhcp-security binding";
     output {
       choice output_c {
         case output-tag {
           leaf output {
             type string;
           }
         }
         case multichassis-tag {
           anyxml multi-routing-engine-results;
         }
       }
     }
   }
   rpc clear-dhcp-security-binding-interface {
     description "Name of interface on which to clear bindings";
     junos:command "clear dhcp-security binding interface";
     input {
       leaf interface-name {
         description "Name of interface";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-dhcp-security-binding-vlan {
     description "Name of vlan on which to clear bindings";
     junos:command "clear dhcp-security binding vlan";
     input {
       leaf vlan-name {
         description "Name of vlan";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding-ip-address {
     description "Ip-address to clear bindings";
     junos:command "clear dhcp-security binding ip-address";
     input {
       leaf ip-address {
         description "Ip-address";
         junos:cli-feature "nokeyword";
         type jt:ipv4addr;
         mandatory true;
       }
     }
     output {
       choice output_c {
         case output-tag {
           leaf output {
             type string;
           }
         }
         case multichassis-tag {
           anyxml multi-routing-engine-results;
         }
       }
     }
   }
   rpc clear-dhcp-security-binding-statistics {
     description "Clear DHCP snooping statistics";
     junos:command "clear dhcp-security binding statistics";
     output {
       choice output_c {
         case output-tag {
           leaf output {
             type string;
           }
         }
         case multichassis-tag {
           anyxml multi-routing-engine-results;
         }
       }
     }
   }
   rpc clear-dhcp-security-ipv6-binding {
     description "Clear DHCPv6 security bindings";
     junos:command "clear dhcp-security ipv6 binding";
     input {
       leaf all {
         description "Clear all bindings";
         type empty;
       }
     }
     output {
       choice output_c {
         case output-tag {
           leaf output {
             type string;
           }
         }
         case multichassis-tag {
           anyxml multi-routing-engine-results;
         }
       }
     }
   }
   rpc clear-dhcp-security-ipv6-binding-interface {
     description "Name of interface on which to clear bindings";
     junos:command "clear dhcp-security ipv6 binding interface";
     input {
       leaf interface-name {
         description "Name of interface";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-dhcp-security-ipv6-binding-vlan {
     description "Name of vlan on which to clear bindings";
     junos:command "clear dhcp-security ipv6 binding vlan";
     input {
       leaf vlan-name {
         description "Name of vlan";
         junos:cli-feature "nokeyword";
         type string;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-dhcp-security-binding-ipv6-address {
     description "IPv6 address to clear bindings";
     junos:command "clear dhcp-security ipv6 binding ipv6-address";
     input {
       leaf ipv6-address {
         description "IPv6 address";
         junos:cli-feature "nokeyword";
         type jt:ipv6addr;
         mandatory true;
       }
     }
     output {
       choice output_c {
         case output-tag {
           leaf output {
             type string;
           }
         }
         case multichassis-tag {
           anyxml multi-routing-engine-results;
         }
       }
     }
   }
   rpc clear-dhcp-v6-security-statistics {
     description "Clear DHCPv6 security statistics";
     junos:command "clear dhcp-security ipv6 statistics";
     output {
       choice output_c {
         case output-tag {
           leaf output {
             type string;
           }
         }
         case multichassis-tag {
           anyxml multi-routing-engine-results;
         }
       }
     }
   }
   rpc clear-dhcp-security-statistics {
     description "Clear DHCP security statistics";
     junos:command "clear dhcp-security statistics";
     output {
       choice output_c {
         case output-tag {
           leaf output {
             type string;
           }
         }
         case multichassis-tag {
           anyxml multi-routing-engine-results;
         }
       }
     }
   }
   rpc clear-lacp-statistics {
     description "Clear LACP statistics";
     junos:command "clear lacp statistics";
     output {
       choice output_c {
         case output-tag {
           leaf output {
             type string;
           }
         }
         case multichassis-tag {
           anyxml multi-routing-engine-results;
         }
       }
     }
   }
   rpc clear-lacp-interface-statistics {
     description "Clear LACP interface statistics";
     junos:command "clear lacp statistics interfaces";
     input {
       leaf interface-name {
         description "Name of interface";
         junos:cli-feature "nokeyword";
         type union {
           type jt:interface-wildcard;
           type string {
             pattern "<.*>|$.*";
           }
         }
       }
     }
     output {
       choice output_c {
         case output-tag {
           leaf output {
             type string;
           }
         }
         case multichassis-tag {
           anyxml multi-routing-engine-results;
         }
       }
     }
   }
   rpc clear-lacp-timeouts {
     description "Clear LACP timeout information";
     junos:command "clear lacp timeouts";
     output {
       choice output_c {
         case output-tag {
           leaf output {
             type string;
           }
         }
         case multichassis-tag {
           anyxml multi-routing-engine-results;
         }
       }
     }
   }
   rpc clear-lacp-interface-timeouts {
     description "Clear LACP interface timeouts";
     junos:command "clear lacp timeouts interfaces";
     input {
       leaf interface-name {
         description "Name of interface";
         junos:cli-feature "nokeyword";
         type union {
           type jt:interface-wildcard;
           type string {
             pattern "<.*>|$.*";
           }
         }
       }
     }
     output {
       choice output_c {
         case output-tag {
           leaf output {
             type string;
           }
         }
         case multichassis-tag {
           anyxml multi-routing-engine-results;
         }
       }
     }
   }
   rpc clear-lfmd-statistics {
     description "Clear link-fault-management statistics";
     junos:command "clear oam ethernet link-fault-management statistics";
     input {
       leaf interface-name {
         description "Name of physical interface";
         junos:cli-feature "nokeyword";
         type union {
           type jt:interface-device;
           type string {
             pattern "<.*>|$.*";
           }
         }
       }
     }
     output {
       leaf lfmd-clear-output {
         type string;
       }
     }
   }
   rpc clear-lfmd-action-profile-statistics {
     description "Clear link-fault-management action-profile statistics";
     junos:command "clear oam ethernet link-fault-management statistics action-profile";
     input {
       leaf action-profile-name {
         description "Name of the action profile to clear";
         junos:cli-feature "nokeyword";
         type string {
           length "1 .. 32";
         }
         mandatory true;
       }
     }
     output {
       leaf lfmd-clear-output {
         type string;
       }
     }
   }
   rpc clear-lfmd-state {
     description "Clear link-fault-management state and restart discovery";
     junos:command "clear oam ethernet link-fault-management state";
     input {
       leaf interface-name {
         description "Name of physical interface";
         junos:cli-feature "nokeyword";
         type union {
           type jt:interface-device;
           type string {
             pattern "<.*>|$.*";
           }
         }
         mandatory true;
       }
     }
     output {
       leaf lfmd-clear-output {
         type string;
       }
     }
   }
   rpc clear-cfm-continuity-measurement {
     description "Clear continuity-measurement information";
     junos:command "clear oam ethernet connectivity-fault-management continuity-measurement";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
       leaf remote-mep {
         description "Identifier for remote maintenance endpoint";
         type union {
           type string {
             pattern "<.*>|$.*";
           }
           type uint32 {
             range "1 .. 8191";
           }
         }
       }
     }
     output {
       leaf cfmd-clear-continuity-measurement {
         type string;
       }
     }
   }
   rpc clear-cfm-delay-statistics {
     description "Clear Ethernet OAM delay statistics";
     junos:command "clear oam ethernet connectivity-fault-management delay-statistics";
     input {
       leaf ethdm-type {
         junos:cli-feature "nokeyword";
         type enumeration {
           enum "one-way" {
             description "One-way delay measurement";
           }
           enum "two-way" {
             description "Two-way delay measurement";
           }
         }
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       leaf cfmd-clear-delay-statistics {
         type string;
       }
     }
   }
   rpc clear-cfm-loss-statistics {
     description "Clear Ethernet OAM loss statistics";
     junos:command "clear oam ethernet connectivity-fault-management loss-statistics";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
     }
     output {
       leaf cfmd-clear-loss-statistics {
         type string;
       }
     }
   }
   rpc clear-cfm-slm-statistics {
     description "Clear Ethernet OAM slm statistics";
     junos:command "clear oam ethernet connectivity-fault-management synthetic-loss-statistics";
     input {
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
       }
     }
     output {
       leaf cfmd-clear-slm-statistics {
         type string;
       }
     }
   }
   rpc clear-cfm-statistics {
     description "Clear connectivity-fault-management statistics";
     junos:command "clear oam ethernet connectivity-fault-management statistics";
     input {
       leaf interface {
         description "Clear the statistics on an interface";
         type string;
       }
       leaf level {
         description "The maintenance-domain level";
         type union {
           type string {
             pattern "<.*>|$.*";
           }
           type int32 {
             range "0 .. 7";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-linktrace-path-database {
     description "Clear linktrace path-database entries of a remote host";
     junos:command "clear oam ethernet connectivity-fault-management path-database";
     input {
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         junos:cli-feature "nokeyword";
         type jt:mac-unicast;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-policer-statistics {
     description "Clear policer statistics";
     junos:command "clear oam ethernet connectivity-fault-management policer";
     input {
       leaf maintenance-domain {
         description "Name of maintenance domain";
         type string {
           length "1 .. 45";
         }
       }
       leaf maintenance-association {
         description "Name of maintenance association";
         type string {
           length "1 .. 45";
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-iterator-statistics {
     description "Clear Ethernet OAM SLA iterator statistics information";
     junos:command "clear oam ethernet connectivity-fault-management sla-iterator-statistics";
     input {
       leaf sla-iterator {
         description "Name of the iterator profile";
         type string;
         mandatory true;
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
         mandatory true;
       }
       leaf remote-mep {
         description "MEP identifier of remote host";
         type union {
           type string {
             pattern "<.*>|$.*";
           }
           type int32 {
             range "1 .. 8191";
           }
         }
         mandatory true;
       }
       leaf current-statistics-type {
         junos:cli-feature "nokeyword";
         type enumeration {
           enum "loss-measurement" {
             description "Show current Frame Loss measurements";
           }
           enum "availability" {
             description "Show current Availability measurements";
           }
           enum "delay-measurement" {
             description "Show current Delay measurement";
           }
           enum "bin" {
             description "Show current Delay measurement bin";
           }
           enum "flap-trap-statistics" {
             description "Show Flap Trap Statistics ";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf verbosity {
         junos:cli-feature "nokeyword";
         default "brief";
         type enumeration {
           enum "brief" {
             description "Display brief output";
           }
           enum "detail" {
             description "Display detail output";
           }
           enum "extensive" {
             description "Display extensive output";
           }
           enum "summary" {
             description "Display summary output";
           }
         }
       }
     }
     output {
       choice output_c {
         case output-tag {
           leaf output {
             type string;
           }
         }
         case multichassis-tag {
           anyxml multi-routing-engine-results;
         }
       }
     }
   }
   rpc clear-cfm-iterator-history {
     description "Clear MEF 36 based Ethernet OAM SLA iterator History statistics information";
     junos:command "clear oam ethernet connectivity-fault-management sla-iterator-history";
     input {
       leaf sla-iterator {
         description "Name of the iterator profile";
         type string;
         mandatory true;
       }
       leaf maintenance-domain {
         description "Name of maintenance domain";
         type string {
           length "1 .. 45";
         }
         mandatory true;
       }
       leaf maintenance-association {
         description "Name of maintenance association";
         type string {
           length "1 .. 45";
         }
         mandatory true;
       }
       leaf local-mep {
         description "Identifier for local maintenance endpoint";
         type union {
           type string {
             pattern "<.*>|$.*";
           }
           type uint32 {
             range "1 .. 8191";
           }
         }
         mandatory true;
       }
       leaf remote-mep {
         description "MEP identifier of remote host";
         type union {
           type string {
             pattern "<.*>|$.*";
           }
           type int32 {
             range "1 .. 8191";
           }
         }
         mandatory true;
       }
       leaf current-statistics-type {
         junos:cli-feature "nokeyword";
         type enumeration {
           enum "loss-measurement" {
             description "Show current Frame Loss measurements";
           }
           enum "availability" {
             description "Show current Availability measurements";
           }
           enum "delay-measurement" {
             description "Show current Delay measurement";
           }
           enum "bin" {
             description "Show current Delay measurement bin";
           }
           enum "flap-trap-statistics" {
             description "Show Flap Trap Statistics ";
           }
         }
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-cfm-cfmman-conn-statistics {
     description "Clear Ethernet OAM cfmman connection statistics information";
     junos:command "clear oam ethernet connectivity-fault-management cfmman-statistics";
     input {
       leaf fpc-slot {
         description "Fpc slot number";
         type union {
           type string {
             pattern "<.*>|$.*";
           }
           type uint32 {
             range "0 .. 80";
           }
         }
       }
     }
     output {
       choice output_c {
         case output-tag {
           leaf output {
             type string;
           }
         }
         case multichassis-tag {
           anyxml multi-routing-engine-results;
         }
       }
     }
   }
   rpc clear-elmi-statistics {
     description "Clear ethernet local management statistics";
     junos:command "clear oam ethernet lmi statistics";
     input {
       leaf interface {
         description "Name of interface";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-arp-table {
     description "Clear address resolution information";
     junos:command "clear arp";
     input {
       leaf hostname {
         description "Name of host";
         type string;
       }
       leaf interface {
         description "Name of the interface";
         type string;
       }
       leaf vpn {
         description "Name of VPN routing table";
         type string;
       }
       leaf logical-system {
         description "Name of logical system";
         type string;
       }
     }
     output {
       container clear-arp-table-results {
         uses clear-arp-table-results-block;
       }
     }
   }
   rpc clear-arp-table-all {
     description "Clear All ARP entries";
     junos:command "clear arp all";
     output {
       container clear-arp-table-results {
         uses clear-arp-table-results-block;
       }
     }
   }
   rpc clear-interfaces-interval {
     description "Clear interface interval table";
     junos:command "clear interfaces interval";
     input {
       leaf interface-name {
         description "Name of physical interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-interface-transport-opt-c-information {
     description "Clear interface transport optics current information";
     junos:command "clear interfaces transport pm optics current";
     input {
       leaf interface-name {
         description "Name of physical interface";
         junos:cli-feature "nokeyword";
         type string;
         mandatory true;
       }
     }
   }
   rpc clear-interface-transport-opt-c-all-information {
     description "Clear interface transport optics current information all interfaces";
     junos:command "clear interfaces transport pm optics current all";
     output {
       container interface-transport-information {
         uses interface-transport-information-block;
       }
     }
   }
   rpc clear-interface-transport-opt-cday-information {
     description "Clear interface transport optics current-day information";
     junos:command "clear interfaces transport pm optics current-day";
     input {
       leaf interface-name {
         description "Name of physical interface";
         junos:cli-feature "nokeyword";
         type string;
         mandatory true;
       }
     }
   }
   rpc clear-interface-transport-opt-cday-all-information {
     description "Clear interface transport optics current-day information all interfaces";
     junos:command "clear interfaces transport pm optics current-day all";
     output {
       container interface-transport-information {
         uses interface-transport-information-block;
       }
     }
   }
   rpc clear-interface-transport-opt-all-information {
     description "Clear interface transport optics all information";
     junos:command "clear interfaces transport pm optics all";
     input {
       leaf interface-name {
         description "Name of physical interface";
         junos:cli-feature "nokeyword";
         type string;
         mandatory true;
       }
     }
   }
   rpc clear-interface-transport-opt-all-all-information {
     description "Clear interface transport optics all information all interfaces";
     junos:command "clear interfaces transport pm optics all all";
     output {
       container interface-transport-information {
         uses interface-transport-information-block;
       }
     }
   }
   rpc clear-interface-transport-otn-c-information {
     description "Clear interface transport otn current information";
     junos:command "clear interfaces transport pm otn current";
     input {
       leaf interface-name {
         description "Name of physical interface";
         junos:cli-feature "nokeyword";
         type string;
         mandatory true;
       }
     }
   }
   rpc clear-interface-transport-otn-c-all-information {
     description "Clear interface transport otn current information all interfaces";
     junos:command "clear interfaces transport pm otn current all";
     output {
       container interface-transport-information {
         uses interface-transport-information-block;
       }
     }
   }
   rpc clear-interface-transport-otn-cday-information {
     description "Clear interface transport otn current-day information";
     junos:command "clear interfaces transport pm otn current-day";
     input {
       leaf interface-name {
         description "Name of physical interface";
         junos:cli-feature "nokeyword";
         type string;
         mandatory true;
       }
     }
   }
   rpc clear-interface-transport-otn-cday-all-information {
     description "Clear interface transport otn current-day information all interfaces";
     junos:command "clear interfaces transport pm otn current-day all";
     output {
       container interface-transport-information {
         uses interface-transport-information-block;
       }
     }
   }
   rpc clear-interface-transport-otn-all-information {
     description "Clear interface transport otn all information";
     junos:command "clear interfaces transport pm otn all";
     input {
       leaf interface-name {
         description "Name of physical interface";
         junos:cli-feature "nokeyword";
         type string;
         mandatory true;
       }
     }
   }
   rpc clear-interface-transport-otn-all-all-information {
     description "Clear interface transport otn all information all interfaces";
     junos:command "clear interfaces transport pm otn all all";
     output {
       container interface-transport-information {
         uses interface-transport-information-block;
       }
     }
   }
   rpc clear-interface-transport-all-c-information {
     description "Clear interface transport both otn and optics current information";
     junos:command "clear interfaces transport pm all current";
     input {
       leaf interface-name {
         description "Name of physical interface";
         junos:cli-feature "nokeyword";
         type string;
         mandatory true;
       }
     }
   }
   rpc clear-interface-transport-all-c-all-information {
     description "Clear interface transport both otn and optics current information all interfaces";
     junos:command "clear interfaces transport pm all current all";
     output {
       container interface-transport-information {
         uses interface-transport-information-block;
       }
     }
   }
   rpc clear-interface-transport-all-cday-information {
     description "Clear interface transport both otn and optics current-day information";
     junos:command "clear interfaces transport pm all current-day";
     input {
       leaf interface-name {
         description "Name of physical interface";
         junos:cli-feature "nokeyword";
         type string;
         mandatory true;
       }
     }
   }
   rpc clear-interface-transport-all-cday-all-information {
     description "Clear interface transport both otn and optics current-day information all interfaces";
     junos:command "clear interfaces transport pm all current-day all";
     output {
       container interface-transport-information {
         uses interface-transport-information-block;
       }
     }
   }
   rpc clear-interface-transport-all-all-information {
     description "Clear interface transport both otn and optics all information";
     junos:command "clear interfaces transport pm all all";
     input {
       leaf interface-name {
         description "Name of physical interface";
         junos:cli-feature "nokeyword";
         type string;
         mandatory true;
       }
     }
   }
   rpc clear-interface-transport-all-all-all-information {
     description "Clear interface transport both otn and optics all information all interfaces";
     junos:command "clear interfaces transport pm all all all";
     output {
       container interface-transport-information {
         uses interface-transport-information-block;
       }
     }
   }
   rpc clear-interfaces-statistics {
     description "Clear interface statistics";
     junos:command "clear interfaces statistics";
     input {
       leaf interface-name {
         description "Name of physical or logical interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-interfaces-statistics-all {
     description "Clear statistics for all interfaces";
     junos:command "clear interfaces statistics all";
     output {
       choice output_c {
         case output-tag {
           leaf output {
             type string;
           }
         }
         case multichassis-tag {
           anyxml multi-routing-engine-results;
         }
       }
     }
   }
   rpc clear-load-balance-statistics {
     description "Clear load balance statistics";
     junos:command "clear interfaces lb-stats";
     input {
       leaf interface-name {
         description "Name of AF interface";
         junos:cli-feature "nokeyword";
         type string {
           junos:posix-pattern "^(af)";
           junos:pattern-message "Only AF interface is supported";
         }
         mandatory true;
       }
     }
     output {
       choice output_c {
         case output-tag {
           leaf output {
             type string;
           }
         }
         case multichassis-tag {
           anyxml multi-routing-engine-results;
         }
       }
     }
   }
   rpc clear-interface-set-statistics {
     description "Clear interface-set statistics";
     junos:command "clear interfaces interface-set statistics";
     input {
       leaf interface-set-name {
         description "Name of interface set";
         junos:cli-feature "nokeyword";
         type string;
       }
     }
     output {
       choice output_c {
         case output-tag {
           leaf output {
             type string;
           }
         }
         case multichassis-tag {
           anyxml multi-routing-engine-results;
         }
       }
     }
   }
   rpc clear-interface-set-statistics-all {
     description "Clear statistics for all interfaces";
     junos:command "clear interfaces interface-set statistics all";
     output {
       choice output_c {
         case output-tag {
           leaf output {
             type string;
           }
         }
         case multichassis-tag {
           anyxml multi-routing-engine-results;
         }
       }
     }
   }
   rpc clear-interfaces-mac-database {
     description "Clear interface mac entries or statistics from mac database";
     junos:command "clear interfaces mac-database";
     input {
       leaf interface-name {
         description "Name of physical or logical interface";
         junos:cli-feature "nokeyword";
         type string;
         mandatory true;
       }
       leaf mac-address {
         description "MAC address";
         type string;
       }
     }
     output {
       choice output_c {
         case output-tag {
           leaf output {
             type string;
           }
         }
         case multichassis-tag {
           anyxml multi-routing-engine-results;
         }
       }
     }
   }
   rpc clear-interface-mac-database-statistics {
     description "Clear interface mac-level statistics from mac database";
     junos:command "clear interfaces mac-database statistics";
     input {
       leaf interface-name {
         description "Name of physical or logical Gigabit or 10-Gigabit Ethernet interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-interface-mac-database-statistics-all {
     description "Clear mac level statistics for all interfaces";
     junos:command "clear interfaces mac-database statistics all";
     output {
       choice output_c {
         case output-tag {
           leaf output {
             type string;
           }
         }
         case multichassis-tag {
           anyxml multi-routing-engine-results;
         }
       }
     }
   }
   rpc clear-sflow-pfe-information {
     description "Clear sflow statistics";
     junos:command "clear pfe sflow";
     output {
       choice output_c {
         case output-tag {
           leaf output {
             type string;
           }
         }
         case multichassis-tag {
           anyxml multi-routing-engine-results;
         }
       }
     }
   }
   rpc clear-vxlan-mcast-stats-information {
     description "Clear sflow vxlan egress mcast stats";
     junos:command "clear pfe sflow egress-mcast-stats";
     output {
       choice output_c {
         case output-tag {
           leaf output {
             type string;
           }
         }
         case multichassis-tag {
           anyxml multi-routing-engine-results;
         }
       }
     }
   }
   rpc clear-snmp-statistics {
     description "Clear SNMP statistics";
     junos:command "clear snmp statistics";
     output {
       choice output_c {
         case output-tag {
           leaf output {
             type string;
           }
         }
         case multichassis-tag {
           anyxml multi-routing-engine-results;
         }
       }
     }
   }
   rpc clear-snmp-subagent-statistics {
     description "Clear statistics for all SNMP subagents";
     junos:command "clear snmp statistics subagents";
     output {
       choice output_c {
         case output-tag {
           leaf output {
             type string;
           }
         }
         case multichassis-tag {
           anyxml multi-routing-engine-results;
         }
       }
     }
   }
   rpc clear-stats-response-statistics-information {
     description "Clear statistics for the stats responses from kernel/PFE";
     junos:command "clear snmp stats-response-statistics";
     output {
       choice output_c {
         case output-tag {
           leaf output {
             type string;
           }
         }
         case multichassis-tag {
           anyxml multi-routing-engine-results;
         }
       }
     }
   }
   rpc clear-snmp-history {
     description "Clear all samples of a particular history index";
     junos:command "clear snmp history";
     input {
       leaf entry {
         junos:cli-feature "nokeyword";
         type string;
         mandatory true;
       }
     }
     output {
       choice output_c {
         case output-tag {
           leaf output {
             type string;
           }
         }
         case multichassis-tag {
           anyxml multi-routing-engine-results;
         }
       }
     }
   }
   rpc clear-vrrp-information {
     description "Clear Virtual Router Redundancy Protocol statistics";
     junos:command "clear vrrp";
     input {
       leaf level {
         junos:cli-feature "nokeyword";
         default "all";
         type enumeration {
           enum "all" {
             description "Clear all statistics";
           }
         }
       }
     }
     output {
       container vrrp-message {
         uses vrrp-message-block;
       }
     }
   }
   rpc clear-vrrp-interface-statistics {
     description "Name of interface on which to clear statistics";
     junos:command "clear vrrp interface";
     input {
       leaf interface-name {
         description "Name of interface";
         junos:cli-feature "nokeyword";
         type string;
         mandatory true;
       }
     }
     output {
       container vrrp-message {
         uses vrrp-message-block;
       }
     }
   }
   rpc clear-ipv6-nd-information {
     description "Clear IPv6 neighbor cache information";
     junos:command "clear ipv6 neighbors";
     input {
       leaf host {
         description "Neighbor host IPV6 address";
         type string;
       }
       leaf interface {
         description "Name of the interface";
         type string;
       }
       leaf vpn {
         description "Name of VPN routing table";
         type string;
       }
       leaf logical-system {
         description "Name of logical system";
         type string;
       }
     }
     output {
       container ipv6-modify-nd {
         uses ipv6-modify-nd-block;
       }
     }
   }
   rpc clear-ipv6-all-neighbors {
     description "Clear all neighbors";
     junos:command "clear ipv6 neighbors all";
     output {
       container ipv6-modify-nd {
         uses ipv6-modify-nd-block;
       }
     }
   }
   rpc clear-ipv6-router-advertisement-information {
     description "Clear IPv6 router advertisement information";
     junos:command "clear ipv6 router-advertisement";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-ift-stats {
     description "Clear inband-telemetry stats";
     junos:command "clear inband-flow-telemetry stats";
     output {
       choice output_c {
         case output-tag {
           leaf output {
             type string;
           }
         }
         case multichassis-tag {
           anyxml multi-routing-engine-results;
         }
       }
     }
   }
   rpc clear-ancp-neighbor-connection {
     description "Clear neighbor connection";
     junos:command "clear ancp neighbor";
     input {
       choice neighbor-opts {
         case ip-address {
           leaf ip-address {
             description "IP address of the neighbor";
             type jt:ipaddr;
           }
         }
         case system-name {
           leaf system-name {
             description "MAC address of the neighbor";
             type string;
           }
         }
       }
     }
     output {
       container ancp-neighbor-information {
         uses ancp-neighbor-information-block;
       }
     }
   }
   rpc clear-ancp-subscriber-connection {
     description "Clear subscriber connections";
     junos:command "clear ancp subscriber";
     input {
       choice subscriber-opts {
         case identifier {
           leaf identifier {
             description "Agent circuit identifier";
             type string;
           }
         }
         case ip-address {
           leaf ip-address {
             description "IP address of the neighbor";
             type jt:ipaddr;
           }
         }
         case system-name {
           leaf system-name {
             description "MAC address of the neighbor";
             type string;
           }
         }
       }
     }
     output {
       container ancp-subscriber-information {
         uses ancp-subscriber-information-block;
       }
     }
   }
   rpc clear-ancp-statistics {
     description "Clear statistics";
     junos:command "clear ancp statistics";
     input {
       choice neighbor-opts {
         case ip-address {
           leaf ip-address {
             description "IP address of the neighbor";
             type jt:ipaddr;
           }
         }
         case system-name {
           leaf system-name {
             description "MAC address of the neighbor";
             type string;
           }
         }
       }
     }
     output {
       choice output_c {
         case output-tag {
           leaf output {
             type string;
           }
         }
         case multichassis-tag {
           anyxml multi-routing-engine-results;
         }
       }
     }
   }
   rpc clear-ancp-access-loop {
     description "Clear access-loop";
     junos:command "clear ancp access-loop";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
       }
       leaf remote-id {
         description "Access loop remote id";
         type string {
           junos:posix-pattern "^.{1,63}$";
           junos:pattern-message "Must be a string of 63 characters or less";
         }
       }
       leaf outer-vlan-id {
         description "Access aggregation circuit id binary";
         type union {
           type string {
             pattern "<.*>|$.*";
           }
           type uint16 {
             range "1 .. 4094";
           }
         }
       }
     }
     output {
       choice output_c {
         case output-tag {
           leaf output {
             type string;
           }
         }
         case multichassis-tag {
           anyxml multi-routing-engine-results;
         }
       }
     }
   }
   rpc clear-authentication-pending-table {
     description "Clear pending authentication requests";
     junos:command "clear network-access requests pending";
     input {
       uses command-forwarding;
       leaf clear-authentication-pending-table-specific {
         description "Clear information for a specific request";
         type union {
           type string {
             pattern "<.*>|$.*";
           }
           type uint64 {
             range "1 .. 18446744073709551615";
           }
         }
       }
     }
     output {
       choice output_c {
         case output-tag {
           leaf output {
             type string;
           }
         }
         case multichassis-tag {
           anyxml multi-routing-engine-results;
         }
       }
     }
   }
   rpc clear-authentication-statistics {
     description "Clear general authentication statistics";
     junos:command "clear network-access requests statistics";
     input {
       uses command-forwarding;
     }
     output {
       choice output_c {
         case output-tag {
           leaf output {
             type string;
           }
         }
         case multichassis-tag {
           anyxml multi-routing-engine-results;
         }
       }
     }
   }
   rpc clear-aaa-subscriber-table {
     description "Logout the subscriber and clear the session entry";
     junos:command "clear network-access aaa subscriber";
     input {
       uses command-forwarding;
     }
     output {
       choice output_c {
         case output-tag {
           leaf output {
             type string;
           }
         }
         case multichassis-tag {
           anyxml multi-routing-engine-results;
         }
       }
     }
   }
   rpc clear-aaa-subscriber-by-username {
     description "Logout the subscriber based on username";
     junos:command "clear network-access aaa subscriber username";
     input {
       uses command-forwarding;
       leaf username {
         description "Username";
         junos:cli-feature "nokeyword";
         type string;
         mandatory true;
       }
       leaf reconnect {
         description "Reconnect subscriber";
         type empty;
       }
     }
     output {
       choice output_c {
         case output-tag {
           leaf output {
             type string;
           }
         }
         case multichassis-tag {
           anyxml multi-routing-engine-results;
         }
       }
     }
   }
   rpc clear-aaa-subscriber-by-session-id {
     description "Logout the subscriber based on session identifier";
     junos:command "clear network-access aaa subscriber session-id";
     input {
       uses command-forwarding;
       leaf id {
         description "Session id";
         junos:cli-feature "nokeyword";
         type union {
           type string {
             pattern "<.*>|$.*";
           }
           type uint64 {
             range "1 .. 18446744073709551615";
           }
         }
         mandatory true;
       }
       leaf reconnect {
         description "Reconnect subscriber";
         type empty;
       }
     }
     output {
       choice output_c {
         case output-tag {
           leaf output {
             type string;
           }
         }
         case multichassis-tag {
           anyxml multi-routing-engine-results;
         }
       }
     }
   }
   rpc clear-aaa-subscriber-table-specific-statistics {
     description "Clear subscriber statistics";
     junos:command "clear network-access aaa subscriber statistics";
     input {
       uses command-forwarding;
       leaf username {
         description "Subscriber session identifier";
         type string;
         mandatory true;
       }
     }
     output {
       choice output_c {
         case output-tag {
           leaf output {
             type string;
           }
         }
         case multichassis-tag {
           anyxml multi-routing-engine-results;
         }
       }
     }
   }
   rpc clear-aaa-statistics-table {
     description "Statistics on subscriber events";
     junos:command "clear network-access aaa statistics";
     input {
       leaf statistics-type {
         junos:cli-feature "nokeyword";
         type enumeration {
           enum "authentication" {
             description "Authentication statistics";
           }
           enum "accounting" {
             description "Accounting statistics";
           }
           enum "dynamic-requests" {
             description "Dynamic requests statistics";
           }
           enum "re-authentication" {
             description "Re-authentication statistics";
           }
           enum "preauthentication" {
             description "Preauthentication statistics";
           }
           enum "terminate-code" {
             description "Terminate-code usage statistics";
           }
           enum "radius" {
             description "RADIUS statistics";
           }
         }
         mandatory true;
       }
     }
   }
   rpc clear-aaa-address-assignment-pool-statistics {
     description "Show pool information based on pool name";
     junos:command "clear network-access aaa statistics address-assignment pool";
     input {
       leaf get-address-assignment-pool-table-specific {
         description "Show information for a specific pool";
         junos:cli-feature "nokeyword";
         type string;
         mandatory true;
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-aaa-address-assignment-client-statistics {
     description "Show pool information based on client";
     junos:command "clear network-access aaa statistics address-assignment client";
     input {
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-aaa-session-limit-per-username {
     description "Clear session-limit per username related information";
     junos:command "clear network-access aaa statistics session-limit-per-username";
     input {
       leaf username {
         description "Clear blocked-requests statistics for this username";
         type string;
       }
       leaf access-profile {
         description "Clear blocked-requests statistics for this profile";
         type string;
       }
     }
     output {
       choice output_c {
         case output-tag {
           leaf output {
             type string;
           }
         }
         case multichassis-tag {
           anyxml multi-routing-engine-results;
         }
       }
     }
   }
   rpc clear-node-secret-file {
     description "Delete SecurID authentication node secret file";
     junos:command "clear network-access securid-node-secret-file";
     input {
       uses command-forwarding;
     }
     output {
       choice output_c {
         case output-tag {
           leaf output {
             type string;
           }
         }
         case multichassis-tag {
           anyxml multi-routing-engine-results;
         }
       }
     }
   }
   rpc clear-gx-plus-statistics-information {
     description "Clear gx-plus statistics";
     junos:command "clear network-access gx-plus statistics";
     input {
       uses command-forwarding;
     }
     output {
       choice output_c {
         case output-tag {
           leaf output {
             type string;
           }
         }
         case multichassis-tag {
           anyxml multi-routing-engine-results;
         }
       }
     }
   }
   rpc clear-gx-plus-replay-information {
     description "Clear gx-plus replay data: request discovery from remote";
     junos:command "clear network-access gx-plus replay";
     input {
       uses command-forwarding;
     }
     output {
       choice output_c {
         case output-tag {
           leaf output {
             type string;
           }
         }
         case multichassis-tag {
           anyxml multi-routing-engine-results;
         }
       }
     }
   }
   rpc clear-nasreq-statistics-information {
     description "Clear nasreq statistics";
     junos:command "clear network-access nasreq statistics";
     input {
       uses command-forwarding;
     }
     output {
       choice output_c {
         case output-tag {
           leaf output {
             type string;
           }
         }
         case multichassis-tag {
           anyxml multi-routing-engine-results;
         }
       }
     }
   }
   rpc clear-pcrf-statistics-information {
     description "Clear pcrf statistics information";
     junos:command "clear network-access pcrf statistics";
     input {
       uses command-forwarding;
     }
     output {
       choice output_c {
         case output-tag {
           leaf output {
             type string;
           }
         }
         case multichassis-tag {
           anyxml multi-routing-engine-results;
         }
       }
     }
   }
   rpc clear-pcrf-subscribers {
     description "Loguout all pcrf subscribers";
     junos:command "clear network-access pcrf subscribers";
     input {
       uses command-forwarding;
     }
     output {
       choice output_c {
         case output-tag {
           leaf output {
             type string;
           }
         }
         case multichassis-tag {
           anyxml multi-routing-engine-results;
         }
       }
     }
   }
   rpc clear-ocs-statistics-information {
     description "Clear ocs statistics information";
     junos:command "clear network-access ocs statistics";
     input {
       uses command-forwarding;
     }
     output {
       choice output_c {
         case output-tag {
           leaf output {
             type string;
           }
         }
         case multichassis-tag {
           anyxml multi-routing-engine-results;
         }
       }
     }
   }
   rpc clear-ocs-backup-information {
     description "Clear ocs backup";
     junos:command "clear network-access ocs backup";
     input {
       uses command-forwarding;
     }
     output {
       choice output_c {
         case output-tag {
           leaf output {
             type string;
           }
         }
         case multichassis-tag {
           anyxml multi-routing-engine-results;
         }
       }
     }
   }
   rpc clear-address-assignment-preserved {
     description "Clear preserved addresses";
     junos:command "clear network-access address-assignment preserved";
     input {
       uses command-forwarding;
       leaf key {
         description "Key to identify reservations";
         type string;
         mandatory true;
       }
     }
     output {
       choice output_c {
         case output-tag {
           leaf output {
             type string;
           }
         }
         case multichassis-tag {
           anyxml multi-routing-engine-results;
         }
       }
     }
   }
   rpc clear-radsec-state {
     description "Clear radsec state";
     junos:command "clear network-access radsec state";
     input {
       uses command-forwarding;
       leaf radsec-state-destination {
         description "Destination to clear";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-radsec-statistics-information {
     description "Clear radsec statistics information";
     junos:command "clear network-access radsec statistics";
     input {
       uses command-forwarding;
       leaf radsec-statistics-destination {
         description "Destination to clear";
         type union {
           type uint32;
           type string {
             pattern "<.*>|$.*";
           }
         }
       }
     }
     output {
       choice output_c {
         case output-tag {
           leaf output {
             type string;
           }
         }
         case multichassis-tag {
           anyxml multi-routing-engine-results;
         }
       }
     }
   }
   rpc clear-local-cert-statistics-information {
     description "Clear local certificate statistics information";
     junos:command "clear network-access local-certificate statistics";
     input {
       uses command-forwarding;
       leaf verbosity_level {
         junos:cli-feature "nokeyword";
         default "brief";
         type enumeration {
           enum "brief" {
             description "Show brief output (deafault)";
           }
           enum "detail" {
             description "Show detailed output";
           }
           enum "extensive" {
             description "Show extensive output";
           }
         }
       }
     }
     output {
       choice output_c {
         case output-tag {
           leaf output {
             type string;
           }
         }
         case multichassis-tag {
           anyxml multi-routing-engine-results;
         }
       }
     }
   }
   rpc clear-nas-5g-statistics-information {
     description "Clear nas-5g statistics";
     junos:command "clear network-access nas-5g statistics";
     input {
       uses command-forwarding;
     }
     output {
       choice output_c {
         case output-tag {
           leaf output {
             type string;
           }
         }
         case multichassis-tag {
           anyxml multi-routing-engine-results;
         }
       }
     }
   }
   rpc clear-auto-configuration-interfaces {
     description "Clear interfaces";
     junos:command "clear auto-configuration interfaces";
     input {
       leaf interface-name {
         description "Name of interface";
         junos:cli-feature "nokeyword";
         type string;
         mandatory true;
       }
       leaf client-type {
         description "Client type of subscriber";
         type enumeration {
           enum "vlan" {
             description "VLAN clients only";
           }
           enum "vlan-oob" {
             description "VLAN out-of-band clients only";
           }
           enum "dyn-ip" {
             description "Dynamic IP clients only";
           }
           enum "vpls-pw" {
             description "VPLS-PW clients only";
           }
           enum "dot1x" {
             description "Dot1x clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
           enum "terminated" {
             description "TERMINATED state only";
           }
         }
       }
     }
     output {
       choice output_c {
         case output-tag {
           leaf output {
             type string;
           }
         }
         case multichassis-tag {
           anyxml multi-routing-engine-results;
         }
       }
     }
   }
   rpc clear-auto-configuration-interfaces-interface-set {
     description "Clear interfaces interface-set";
     junos:command "clear auto-configuration interfaces interface-set";
     input {
       leaf interface-set-name {
         description "Name of interface set";
         junos:cli-feature "nokeyword";
         type string;
         mandatory true;
       }
     }
     output {
       choice output_c {
         case output-tag {
           leaf output {
             type string;
           }
         }
         case multichassis-tag {
           anyxml multi-routing-engine-results;
         }
       }
     }
   }
   rpc clear-bfd-session-information {
     description "Clear BFD sessions";
     junos:command "clear bfd session";
     input {
       leaf all {
         description "Cleae all BFD sessions";
         type empty;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-bfd-session-discriminator {
     description "Clear a BFD session by discriminator";
     junos:command "clear bfd session discriminator";
     input {
       leaf discr_number {
         description "Local discriminator of session to clear";
         junos:cli-feature "nokeyword";
         type union {
           type uint32;
           type string {
             pattern "<.*>|$.*";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-bfd-session-address {
     description "Clear a BFD session by address";
     junos:command "clear bfd session address";
     input {
       leaf session_addr {
         description "Address of session to clear";
         junos:cli-feature "nokeyword";
         type jt:ipaddr;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-bfd-adaptation-information {
     description "Clear BFD adaptation";
     junos:command "clear bfd adaptation";
     input {
       leaf all {
         description "Clear BFD adaptation for all sessions";
         type empty;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-bfd-adaptation-discriminator {
     description "Clear BFD adaptation by discriminator";
     junos:command "clear bfd adaptation discriminator";
     input {
       leaf discr_number {
         description "Local discriminator of session to clear";
         junos:cli-feature "nokeyword";
         type union {
           type uint32;
           type string {
             pattern "<.*>|$.*";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-bfd-adaptation-address {
     description "Clear BFD adaptation by address";
     junos:command "clear bfd adaptation address";
     input {
       leaf session_addr {
         description "Address of session to clear";
         junos:cli-feature "nokeyword";
         type jt:ipaddr;
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       container bfd-session-information {
         uses bfd-session-information-block;
       }
     }
   }
   rpc clear-synchronous-ethernet-esmc-statistics {
     description "Clear ESMC statistics";
     junos:command "clear synchronous-ethernet esmc statistics";
     input {
       leaf interface-name {
         description "Name of interface ";
         junos:cli-feature "nokeyword";
         type union {
           type jt:interface-device;
           type string {
             pattern "<.*>|$.*";
           }
         }
       }
     }
     output {
       leaf clock-synchronization-clear-output {
         type string;
       }
     }
   }
   rpc clear-synchronous-ethernet-wait-to-restore {
     description "Clear wait to restore timer";
     junos:command "clear synchronous-ethernet wait-to-restore";
     input {
       leaf interface {
         description "Name of physical interface";
         type string;
       }
     }
     output {
       leaf clear-wait-to-restore {
         type string;
       }
     }
   }
   rpc clear-ptp-long-term-counters {
     description "Clear all long-term delay performance entries";
     junos:command "clear ptp performance-monitor long-term entries";
     output {
       leaf ptp-clear-long-term-counters {
         type string;
       }
     }
   }
   rpc clear-captive-portal-interface-session {
     description "Clear 802.1X session on an interface";
     junos:command "clear captive-portal interface";
     input {
       leaf interface-name {
         description "Name of interface";
         junos:cli-feature "nokeyword";
         default "all";
         type union {
           type jt:interface-name;
           type string {
             pattern "<.*>|$.*";
           }
         }
       }
     }
   }
   rpc clear-captive-portal-firewall {
     description "Clear captive-portal firewall statistics for a counter";
     junos:command "clear captive-portal firewall";
     input {
       leaf counter-name {
         description "Clear firewall statistics for this counter";
         junos:cli-feature "nokeyword";
         default "all";
         type string;
       }
     }
   }
   rpc clear-captive-portal-firewall-interface {
     description "Clear firewall statistics on this interface";
     junos:command "clear captive-portal firewall interface";
     input {
       leaf interface-name {
         description "Name of interface";
         junos:cli-feature "nokeyword";
         default "all";
         type union {
           type jt:interface-name;
           type string {
             pattern "<.*>|$.*";
           }
         }
       }
     }
     output {
       choice output_c {
         case output-tag {
           leaf output {
             type string;
           }
         }
         case multichassis-tag {
           anyxml multi-routing-engine-results;
         }
       }
     }
   }
   rpc clear-captive-portal-mac-session {
     description "Clear 802.1X session on a MAC address";
     junos:command "clear captive-portal mac-address";
     input {
       leaf session-mac-addr {
         description "MAC address to clear";
         junos:cli-feature "nokeyword";
         default "all";
         type jt:mac-addr;
       }
     }
   }
   rpc clear-dot1x-eapol-block-interface-session {
     description "Clear eapol-block timer for all sessions on an interface";
     junos:command "clear dot1x eapol-block interface";
     input {
       leaf interface-name {
         description "Name of interface";
         junos:cli-feature "nokeyword";
         default "all";
         type union {
           type jt:interface-wildcard;
           type string {
             pattern "<.*>|$.*";
           }
         }
       }
     }
   }
   rpc clear-dot1x-eapol-block-mac-session {
     description "Clear eapol-block timer for session on a MAC address";
     junos:command "clear dot1x eapol-block mac-address";
     input {
       leaf static-mac-addr {
         description "MAC address to clear eapol-block timer";
         junos:cli-feature "nokeyword";
         default "all";
         type jt:mac-addr;
       }
     }
   }
   rpc clear-dot1x-interface-session {
     description "Clear 802.1X session on an interface";
     junos:command "clear dot1x interface";
     input {
       leaf interface-name {
         description "Name of interface";
         junos:cli-feature "nokeyword";
         default "all";
         type union {
           type jt:interface-wildcard;
           type string {
             pattern "<.*>|$.*";
           }
         }
       }
     }
   }
   rpc clear-dot1x-supplicant-interface-session {
     description "Clear supplicant sessions on an interface";
     junos:command "clear dot1x supplicant interface";
     input {
       leaf interface-name {
         description "Name of interface";
         junos:cli-feature "nokeyword";
         default "all";
         type union {
           type jt:interface-wildcard;
           type string {
             pattern "<.*>|$.*";
           }
         }
       }
     }
   }
   rpc clear-dot1x-dynamic-vlan {
     description "Clear 802.1X dynamic created vlan";
     junos:command "clear dot1x dynamic-vlan";
   }
   rpc clear-dot1x-firewall {
     description "Clear dot1x firewall statistics for a counter";
     junos:command "clear dot1x firewall";
     input {
       leaf counter-name {
         description "Clear firewall statistics for this counter";
         junos:cli-feature "nokeyword";
         default "all";
         type string;
       }
     }
   }
   rpc clear-dot1x-firewall-interface {
     description "Clear firewall statistics on this interface";
     junos:command "clear dot1x firewall interface";
     input {
       leaf interface-name {
         description "Name of interface";
         junos:cli-feature "nokeyword";
         default "all";
         type union {
           type jt:interface-wildcard;
           type string {
             pattern "<.*>|$.*";
           }
         }
       }
     }
   }
   rpc clear-dot1x-mac-session {
     description "Clear 802.1X session on a MAC address";
     junos:command "clear dot1x mac-address";
     input {
       leaf static-mac-addr {
         description "MAC address to clear";
         junos:cli-feature "nokeyword";
         default "all";
         type jt:mac-addr;
       }
     }
   }
   rpc clear-dot1x-statistics {
     description "Clear 802.1X statistics on an interface";
     junos:command "clear dot1x statistics";
   }
   rpc clear-dot1x-statistics-interface {
     description "Clear 802.1X statistics on this interface";
     junos:command "clear dot1x statistics interface";
     input {
       leaf interface-name {
         description "Name of interface";
         junos:cli-feature "nokeyword";
         default "all";
         type union {
           type jt:interface-wildcard;
           type string {
             pattern "<.*>|$.*";
           }
         }
       }
     }
   }
   rpc clear-dot1x-recovery-timeout {
     description "Clear port error";
     junos:command "clear dot1x recovery-timeout";
   }
   rpc clear-dot1x-recovery-timeout-interface {
     description "Clear port error for the specified interface";
     junos:command "clear dot1x recovery-timeout interface";
     input {
       leaf interface-name {
         description "Name of interface";
         junos:cli-feature "nokeyword";
         default "all";
         type union {
           type jt:interface-wildcard;
           type string {
             pattern "<.*>|$.*";
           }
         }
       }
     }
   }
   rpc clear-helper-statistics-information {
     description "Clear helper statistics";
     junos:command "clear helper statistics";
     output {
       choice output_c {
         case output-tag {
           leaf output {
             type string;
           }
         }
         case multichassis-tag {
           anyxml multi-routing-engine-results;
         }
       }
     }
   }
   rpc clear-ilmi-statistics {
     description "Clear ILMI statistics";
     junos:command "clear ilmi statistics";
     output {
       choice output_c {
         case output-tag {
           leaf output {
             type string;
           }
         }
         case multichassis-tag {
           anyxml multi-routing-engine-results;
         }
       }
     }
   }
   rpc clear-ipsec-security-associations {
     description "Clear IPSec dynamic security associations";
     junos:command "clear ipsec security-associations";
     input {
       leaf sa-name {
         description "Name of security association";
         junos:cli-feature "nokeyword";
         type string {
           length "1 .. 32";
         }
       }
     }
     output {
       choice output_c {
         case output-tag {
           leaf output {
             type string;
           }
         }
         case multichassis-tag {
           anyxml multi-routing-engine-results;
         }
       }
     }
   }
   rpc clear-ike-security-associations {
     description "Clear IKE security associations";
     junos:command "clear ike security-associations";
     input {
       leaf peer-address {
         description "Name of security association";
         junos:cli-feature "nokeyword";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-ike-statistics {
     description "Clear IKE security associations statistics";
     junos:command "clear ike statistics";
     input {
       leaf peer-address {
         description "Name of security association";
         junos:cli-feature "nokeyword";
         type jt:ipaddr;
       }
       leaf routing-instance {
         description "Name of the local-gateway routing-instance";
         type string;
       }
       leaf service-set {
         description "Name of service set";
         type string {
           junos:posix-pattern "^[A-Za-z0-9][_0-9A-Za-z-]{0,62}$";
           junos:pattern-message "Must be a string beginning with a number or letter and consisting of no more than 63 total letters, numbers, dashes and underscores.";
         }
       }
     }
     output {
       choice output_c {
         case output-tag {
           leaf output {
             type string;
           }
         }
         case multichassis-tag {
           anyxml multi-routing-engine-results;
         }
       }
     }
   }
   rpc clear-diameter-peer {
     description "Clear diameter peer information";
     junos:command "clear diameter peer";
     input {
       leaf clear-peer-what {
         junos:cli-feature "nokeyword";
         default "connection";
         type enumeration {
           enum "connection" {
             description "Clear diameter peer connection(default)";
           }
           enum "statistics" {
             description "Clear diameter peer statistics";
           }
         }
       }
       leaf clear-diameter-peer-name {
         description "Peer name";
         junos:cli-feature "nokeyword";
         type string;
         mandatory true;
       }
     }
     output {
       choice output_c {
         case output-tag {
           leaf output {
             type string;
           }
         }
         case multichassis-tag {
           anyxml multi-routing-engine-results;
         }
       }
     }
   }
   rpc clear-diameter-function {
     description "Clear diameter function information";
     junos:command "clear diameter function";
     input {
       leaf clear-function-what {
         junos:cli-feature "nokeyword";
         type enumeration {
           enum "statistics" {
             description "Clear diameter function statistics";
           }
         }
         mandatory true;
       }
       leaf clear-diameter-function-name {
         description "Function name";
         junos:cli-feature "nokeyword";
         type enumeration {
           enum "jsrc" {
             description "Function to use SRC application";
           }
           enum "charging-gw" {
             description "Function to use CHARGING application";
           }
           enum "gx-plus" {
             description "Function to use GX-PLUS application";
           }
           enum "sd-3gpp" {
             description "Function to use SD-3GPP application";
           }
           enum "nasreq" {
             description "Function to use NASREQ application";
           }
           enum "pcrf" {
             description "Function to use PCRF(GX) application";
           }
           enum "ocs" {
             description "Function to use OCS(GY) application";
           }
           enum "s6a" {
             description "Function to use S6A application";
           }
         }
         mandatory true;
       }
     }
     output {
       choice output_c {
         case output-tag {
           leaf output {
             type string;
           }
         }
         case multichassis-tag {
           anyxml multi-routing-engine-results;
         }
       }
     }
   }
   rpc clear-pgm-negative-acknowledgments {
     description "Clear PGM NAK state information";
     junos:command "clear pgm negative-acknowledgments";
     output {
       choice output_c {
         case output-tag {
           leaf output {
             type string;
           }
         }
         case multichassis-tag {
           anyxml multi-routing-engine-results;
         }
       }
     }
   }
   rpc clear-pgm-source-path-messages {
     description "Clear PGM source path message state information";
     junos:command "clear pgm source-path-messages";
     output {
       choice output_c {
         case output-tag {
           leaf output {
             type string;
           }
         }
         case multichassis-tag {
           anyxml multi-routing-engine-results;
         }
       }
     }
   }
   rpc clear-pgm-statistics {
     description "Clear PGM statistics information";
     junos:command "clear pgm statistics";
     output {
       choice output_c {
         case output-tag {
           leaf output {
             type string;
           }
         }
         case multichassis-tag {
           anyxml multi-routing-engine-results;
         }
       }
     }
   }
   rpc clear-poe-telemetries-information {
     description "Clear PoE telemetries interface information";
     junos:command "clear poe telemetries interface";
     input {
       leaf interface-name {
         description "Name of the interface";
         junos:cli-feature "nokeyword";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-amt-tunnel {
     description "Clear AMT tunnel";
     junos:command "clear amt tunnel";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-amt-tunnel-interface {
     description "AMT tunnel interface";
     junos:command "clear amt tunnel tunnel-interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of the interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-amt-tunnel-gateway-address {
     description "AMT tunnel gateway address";
     junos:command "clear amt tunnel gateway-address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf address {
         description "IP address of the gateway";
         junos:cli-feature "nokeyword";
         type string;
         mandatory true;
       }
       leaf port {
         description "UDP port of the gateway";
         type union {
           type string {
             pattern "<.*>|$.*";
           }
           type uint16 {
             range "1 .. 65535";
           }
         }
       }
     }
     output {
       choice output_c {
         case output-tag {
           leaf output {
             type string;
           }
         }
         case multichassis-tag {
           anyxml multi-routing-engine-results;
         }
       }
     }
   }
   rpc clear-amt-tunnel-statistics {
     description "Clear AMT tunnel message statistics";
     junos:command "clear amt tunnel statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-amt-tunnel-interface-statistics {
     description "AMT tunnel interface";
     junos:command "clear amt tunnel statistics tunnel-interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of the interface";
         junos:cli-feature "nokeyword";
         type string;
         mandatory true;
       }
     }
     output {
       choice output_c {
         case output-tag {
           leaf output {
             type string;
           }
         }
         case multichassis-tag {
           anyxml multi-routing-engine-results;
         }
       }
     }
   }
   rpc clear-amt-tunnel-gateway-address-statistics {
     description "AMT tunnel gateway address";
     junos:command "clear amt tunnel statistics gateway-address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf address {
         description "IP address of the gateway";
         junos:cli-feature "nokeyword";
         type string;
         mandatory true;
       }
       leaf port {
         description "UDP port of the gateway";
         type union {
           type string {
             pattern "<.*>|$.*";
           }
           type uint16 {
             range "1 .. 65535";
           }
         }
       }
     }
     output {
       choice output_c {
         case output-tag {
           leaf output {
             type string;
           }
         }
         case multichassis-tag {
           anyxml multi-routing-engine-results;
         }
       }
     }
   }
   rpc clear-amt-statistics {
     description "Clear AMT statistics";
     junos:command "clear amt statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
     }
     output {
       choice output_c {
         case output-tag {
           leaf output {
             type string;
           }
         }
         case multichassis-tag {
           anyxml multi-routing-engine-results;
         }
       }
     }
   }
   rpc clear-auto-bandwidth-history-log-information {
     description "Clear auto-bandwidth history log";
     junos:command "clear auto-bandwidth history-log";
     output {
       choice output_c {
         case output-tag {
           leaf output {
             type string;
           }
         }
         case multichassis-tag {
           anyxml multi-routing-engine-results;
         }
       }
     }
   }
   rpc clear-auto-bandwidth-traffic-information {
     description "Clear auto-bandwidth probe traffic";
     junos:command "clear auto-bandwidth traffic";
     input {
       choice clear-traffic-arg {
         case all {
           leaf all {
             description "Clear all auto-bandwidth probe traffic";
             type empty;
           }
         }
         case probe-name {
           leaf probe-name {
             description "Name of probe";
             junos:cli-feature "nokeyword";
             type string;
           }
         }
       }
     }
     output {
       choice output_c {
         case output-tag {
           leaf output {
             type string;
           }
         }
         case multichassis-tag {
           anyxml multi-routing-engine-results;
         }
       }
     }
   }
   rpc clear-bgp-damping {
     description "Clear damping information";
     junos:command "clear bgp damping";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf prefix {
         description "Destination prefix and prefix length";
         junos:cli-feature "nokeyword";
         type string;
       }
     }
     output {
       choice output_c {
         case output-tag {
           leaf output {
             type string;
           }
         }
         case multichassis-tag {
           anyxml multi-routing-engine-results;
         }
       }
     }
   }
   rpc clear-bgp-neighbor {
     description "Clear BGP neighbors";
     junos:command "clear bgp neighbor";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf rib-sharding {
         description "Name of rib shard";
         type string {
           junos:posix-pattern "^[a-zA-Z0-9_-]{1,63}$";
           junos:pattern-message "Shard name is a string consisting of up to 63 letters, numbers, dashes and underscores";
         }
       }
       leaf disposition {
         junos:cli-feature "nokeyword";
         type enumeration {
           enum "soft" {
             description "Soft reset outbound state";
           }
           enum "soft-minimum-igp" {
             description "Soft reset outbound state with refresh of minimum igp MED";
           }
           enum "soft-minimum-effective-aigp" {
             description "Soft reset outbound state with refresh of minimum effective aigp MED";
           }
           enum "soft-inbound" {
             description "Soft reset inbound state by issuing Refresh";
           }
           enum "soft-reconfig" {
             description "Soft reset inbound state by import re-evaluation";
           }
           enum "malformed-route" {
             description "Clear malformed routes";
           }
           enum "stale-routes" {
             description "Clear stale routes";
           }
           enum "gracefully" {
             description "Allow peer to start graceful restart receiving-speaker mode, if possible";
           }
         }
       }
       leaf instance {
         description "Name of BGP instance";
         type string;
       }
       leaf as {
         description " Autonomous system number in plain number or 'higher 16bits'.'Lower 16 bits' (asdot notation) format";
         type string {
           junos:posix-pattern "^[0-9]+(.[0-9]+)?$";
           junos:pattern-message "Use format \'x\' or \'x.y\' to specify number \'x\' (Range 1 .. 4294967295) or number with higher 2 bytes \'x\' (Range 0 .. 65535) and lower 2 bytes \'y\' (Range 0 .. 65535) respectively";
         }
       }
       choice neighbor-choice {
         case neighbor {
           leaf neighbor {
             description "Particular BGP neighbor to clear";
             junos:cli-feature "nokeyword";
             type string;
           }
         }
         case all {
           leaf all {
             description "Clear All BGP neighbors";
             type empty;
           }
         }
       }
     }
     output {
       choice output_c {
         case output-tag {
           leaf output {
             type string;
           }
         }
         case multichassis-tag {
           anyxml multi-routing-engine-results;
         }
       }
     }
   }
   rpc clear-bgp-table {
     description "Refresh routes in a routing table";
     junos:command "clear bgp table";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf table {
         description "Name of table to clear";
         junos:cli-feature "nokeyword";
         type string;
         mandatory true;
       }
     }
     output {
       choice output_c {
         case output-tag {
           leaf output {
             type string;
           }
         }
         case multichassis-tag {
           anyxml multi-routing-engine-results;
         }
       }
     }
   }
   rpc clear-esis-adjacency {
     description "Clear ES-IS adjacencies";
     junos:command "clear esis adjacency";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of ES-IS instance";
         type string;
       }
       leaf interface {
         description "Name of interface";
         type string;
       }
       leaf neighbor {
         description "Name of neighbor";
         junos:cli-feature "nokeyword";
         type string;
       }
     }
     output {
       choice output_c {
         case output-tag {
           leaf output {
             type string;
           }
         }
         case multichassis-tag {
           anyxml multi-routing-engine-results;
         }
       }
     }
   }
   rpc clear-esis-statistics {
     description "Clear ES-IS statistics";
     junos:command "clear esis statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of ES-IS instance";
         type string;
       }
     }
     output {
       choice output_c {
         case output-tag {
           leaf output {
             type string;
           }
         }
         case multichassis-tag {
           anyxml multi-routing-engine-results;
         }
       }
     }
   }
   rpc clear-evpn-duplicate-mac-suppression {
     description "Clear duplicate MAC suppression";
     junos:command "clear evpn duplicate-mac-suppression";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Clear duplicate MAC suppression for a specific instance";
         type string;
       }
       leaf l2-domain-id {
         description "Clear duplicate MAC suppression for a specific L2 domain";
         type union {
           type string {
             pattern "<.*>|$.*";
           }
           type int32 {
             range "1 .. 16777214";
           }
         }
       }
       leaf mac-address {
         description "Clear duplicate MAC suppression for a specific MAC address";
         type jt:mac-addr;
       }
     }
     output {
       choice output_c {
         case output-tag {
           leaf output {
             type string;
           }
         }
         case multichassis-tag {
           anyxml multi-routing-engine-results;
         }
       }
     }
   }
   rpc clear-evpn-mac-table {
     description "Clear all learned media access control addresses";
     junos:command "clear evpn mac-table";
     input {
       leaf instance {
         description "Display information for a specified instance";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-evpn-interface-mac-table {
     description "Clear media access control table for specified interface";
     junos:command "clear evpn mac-table interface";
     input {
       leaf interface-name {
         description "Name of interface for which to clear table";
         junos:cli-feature "nokeyword";
         type union {
           type jt:interface-name;
           type string {
             pattern "<.*>|$.*";
           }
         }
         mandatory true;
       }
       leaf vlan-id {
         description "Clear MAC address learned on a specified VLAN";
         type string;
       }
     }
     output {
       choice output_c {
         case output-tag {
           leaf output {
             type string;
           }
         }
         case multichassis-tag {
           anyxml multi-routing-engine-results;
         }
       }
     }
   }
   rpc clear-evpn-mac-ip-table {
     description "Clear IPv4 and IPv6 entries for EVPN instances";
     junos:command "clear evpn mac-ip-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-evpn-arp-table {
     description "Clear all INET addresses learned via ARP";
     junos:command "clear evpn arp-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-evpn-nd-table {
     description "Clear all INET6 addresses learned via NDP";
     junos:command "clear evpn nd-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified vpls";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-exp-segs-all-information {
     description "Clear express segments";
     junos:command "clear express-segments";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf segment-type {
         junos:cli-feature "nokeyword";
         default "all";
         type enumeration {
           enum "all" {
             description "Reset 'all' the express-segments originating on this router";
           }
         }
       }
       leaf clear-exp-segs-name-information {
         description "Reset 'name' matching express-segments - Must select 'name' or 'all'";
         type string;
       }
     }
     output {
       choice output_c {
         case output-tag {
           leaf output {
             type string;
           }
         }
         case multichassis-tag {
           anyxml multi-routing-engine-results;
         }
       }
     }
   }
   rpc clear-exp-segs-trafficd-eng-information {
     description "Clear express-segment insertion into TED";
     junos:command "clear express-segments traffic-engineering";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       choice clear-choice {
         case name {
           leaf clear-exp-segs-traffic-eng-name-information {
             description "Name of express-segment - Must select 'name' or 'all'";
             type string;
           }
         }
         case all {
           leaf all {
             description "All matching express-segments - Must select 'name' or 'all'";
             type empty;
           }
         }
       }
     }
     output {
       choice output_c {
         case output-tag {
           leaf output {
             type string;
           }
         }
         case multichassis-tag {
           anyxml multi-routing-engine-results;
         }
       }
     }
   }
   rpc clear-igmp-statistics {
     description "Clear IGMP statistics";
     junos:command "clear igmp statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-igmp-membership {
     description "Clear IGMP group membership";
     junos:command "clear igmp membership";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       choice clear_arg {
         case group {
           leaf group {
             description "IP address range for group";
             type jt:ipv4prefix;
           }
         }
         case all {
           leaf all {
             description "Clear all IGMP group membership";
             type empty;
           }
         }
       }
     }
     output {
       choice output_c {
         case output-tag {
           leaf output {
             type string;
           }
         }
         case multichassis-tag {
           anyxml multi-routing-engine-results;
         }
       }
     }
   }
   rpc clear-igmp-snooping-statistics {
     description "Clear IGMP snooping statistics";
     junos:command "clear igmp snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-bridge-domain-statistics {
     description "For a particular bridge-domain";
     junos:command "clear igmp snooping statistics bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         junos:cli-feature "nokeyword";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-vlan-statistics {
     description "For a particular VLAN";
     junos:command "clear igmp snooping statistics vlan";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         junos:cli-feature "nokeyword";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-membership {
     description "Clear IGMP snooping group membership";
     junos:command "clear igmp snooping membership";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         junos:cli-feature "nokeyword";
         type jt:ipv4prefix;
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-igmp-snooping-bridge-domain-membership {
     description "For a particular bridge-domain";
     junos:command "clear igmp snooping membership bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         junos:cli-feature "nokeyword";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
       leaf group {
         description "IP address range for group";
         type jt:ipv4prefix;
       }
     }
     output {
       choice output_c {
         case output-tag {
           leaf output {
             type string;
           }
         }
         case multichassis-tag {
           anyxml multi-routing-engine-results;
         }
       }
     }
   }
   rpc clear-igmp-snooping-vlan-membership {
     description "For a particular VLAN";
     junos:command "clear igmp snooping membership vlan";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         junos:cli-feature "nokeyword";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
       leaf group {
         description "IP address range for group";
         junos:cli-feature "nokeyword";
         type jt:ipv4prefix;
       }
     }
     output {
       choice output_c {
         case output-tag {
           leaf output {
             type string;
           }
         }
         case multichassis-tag {
           anyxml multi-routing-engine-results;
         }
       }
     }
   }
   rpc clear-dynamic-tunnels-database-statistics {
     description "Clear dynamic-tunnels statistics";
     junos:command "clear dynamic-tunnels database statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf destination {
         description "IP or IP-color<c> address with optional prefix length of destination";
         junos:cli-feature "nokeyword";
         type string;
       }
       leaf next-hop {
         description "Clear only tunnel nexthop traffic statistics of the tunnels";
         type empty;
       }
       leaf tunnel-type {
         description "Clear traffic statistics of all the tunnels with given tunnel type";
         type enumeration {
           enum "ipoip" {
             description "IPIP tunnel type";
           }
           enum "gre" {
             description "GRE tunnel type";
           }
           enum "udp" {
             description "UDP tunnel type";
           }
           enum "ipv6" {
             description "IPv6 tunnel type";
           }
           enum "grev6" {
             description "GRE v6 tunnel type";
           }
           enum "udpv6" {
             description "UDP v6 tunnel type";
           }
         }
       }
       leaf tunnel-id {
         description "Clear traffic statistics of all the tunnels with given tunnel-id";
         type union {
           type uint32;
           type string {
             pattern "<.*>|$.*";
           }
         }
       }
       leaf table {
         description "Clear traffic statistics of all tunnels belonging to this routing table";
         type string;
       }
       leaf chain-type {
         description "Clear traffic statistics of all tunnels with given next-hop type";
         type enumeration {
           enum "v4" {
             description "V4 next-hops";
           }
           enum "v6" {
             description "V6 next-hops";
           }
         }
       }
     }
     output {
       choice output_c {
         case output-tag {
           leaf output {
             type string;
           }
         }
         case multichassis-tag {
           anyxml multi-routing-engine-results;
         }
       }
     }
   }
   rpc clear-isis-adjacency-information {
     description "Clear IS-IS adjacencies";
     junos:command "clear isis adjacency";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
       leaf interface {
         description "Name of interface";
         type string;
       }
       choice clear-adj-arg {
         case all {
           leaf all {
             description "Clear all IS-IS adjacencies";
             type empty;
           }
         }
         case neighbor {
           leaf neighbor {
             description "Name of neighbor";
             junos:cli-feature "nokeyword";
             type string;
           }
         }
       }
     }
     output {
       choice output_c {
         case output-tag {
           leaf output {
             type string;
           }
         }
         case multichassis-tag {
           anyxml multi-routing-engine-results;
         }
       }
     }
   }
   rpc clear-isis-database-information {
     description "Clear IS-IS database entries";
     junos:command "clear isis database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
       choice clear-db-arg {
         case all {
           leaf all {
             description "Clear all IS-IS database entries";
             type empty;
           }
         }
         case entries {
           leaf entries {
             description "Name of database entry";
             junos:cli-feature "nokeyword";
             type string;
           }
         }
       }
     }
     output {
       choice output_c {
         case output-tag {
           leaf output {
             type string;
           }
         }
         case multichassis-tag {
           anyxml multi-routing-engine-results;
         }
       }
     }
   }
   rpc clear-isis-layer2-map-information {
     description "Clear IS-IS ARP/ND mapping information";
     junos:command "clear isis layer2-map";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
       leaf destination {
         description "IP address of mapping entry";
         junos:cli-feature "nokeyword";
         type jt:ipaddr;
       }
     }
     output {
       choice output_c {
         case output-tag {
           leaf output {
             type string;
           }
         }
         case multichassis-tag {
           anyxml multi-routing-engine-results;
         }
       }
     }
   }
   rpc clear-isis-overload-information {
     description "Clear overload bit and regenerate LSPs";
     junos:command "clear isis overload";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
     }
     output {
       choice output_c {
         case output-tag {
           leaf output {
             type string;
           }
         }
         case multichassis-tag {
           anyxml multi-routing-engine-results;
         }
       }
     }
   }
   rpc clear-isis-statistics-information {
     description "Clear IS-IS statistics";
     junos:command "clear isis statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
     }
     output {
       choice output_c {
         case output-tag {
           leaf output {
             type string;
           }
         }
         case multichassis-tag {
           anyxml multi-routing-engine-results;
         }
       }
     }
   }
   rpc clear-isis-interface-statistics-information {
     description "Clear ISIS interface statistics information";
     junos:command "clear isis statistics interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf instance {
         description "Name of IS-IS instance";
         type string;
       }
       leaf interface-name {
         description "Name of interface";
         junos:cli-feature "nokeyword";
         type string;
       }
       leaf all {
         description "Clear all interface statistics";
         type empty;
       }
     }
     output {
       choice output_c {
         case output-tag {
           leaf output {
             type string;
           }
         }
         case multichassis-tag {
           anyxml multi-routing-engine-results;
         }
       }
     }
   }
   rpc clear-isis-spring-information {
     description "Clear SPRING information";
     junos:command "clear isis spring";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
     }
     output {
       choice output_c {
         case output-tag {
           leaf output {
             type string;
           }
         }
         case multichassis-tag {
           anyxml multi-routing-engine-results;
         }
       }
     }
   }
   rpc clear-isis-spring-flex-algorithm-information {
     description "Clear SPRING flex-algorithm information";
     junos:command "clear isis spring flex-algorithm-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf level {
         description "Number of IS-IS level";
         type union {
           type string {
             pattern "<.*>|$.*";
           }
           type uint32 {
             range "1 .. 2";
           }
         }
       }
     }
     output {
       choice output_c {
         case output-tag {
           leaf output {
             type string;
           }
         }
         case multichassis-tag {
           anyxml multi-routing-engine-results;
         }
       }
     }
   }
   rpc clear-isis-spring-traffic-information {
     description "Clear SPRING traffic-statistics-information";
     junos:command "clear isis spring traffic-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf igp-instance {
         description "Name of igp-instance";
         type string;
       }
       leaf interface {
         description "Name of interface";
         type string;
       }
       leaf all {
         description "Clear all interface traffic-statistics";
         type empty;
       }
     }
     output {
       choice output_c {
         case output-tag {
           leaf output {
             type string;
           }
         }
         case multichassis-tag {
           anyxml multi-routing-engine-results;
         }
       }
     }
   }
   rpc clear-l2ckt-pw-auto-sensing {
     description "Clear Layer 2 circuit PW auto-sensing state";
     junos:command "clear l2circuit auto-sensing";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         default "all";
         type string;
       }
       leaf vc-id {
         description "VC ID";
         default "all";
         type string;
       }
     }
     output {
       choice output_c {
         case output-tag {
           leaf output {
             type string;
           }
         }
         case multichassis-tag {
           anyxml multi-routing-engine-results;
         }
       }
     }
   }
   rpc clear-vpls-mac-address {
     description "Clear a VPLS media access control address";
     junos:command "clear vpls mac-address";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "VPLS instance name";
         default "all";
         type string;
       }
       leaf address {
         description "MAC address to clear";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-vpls-statistics {
     description "Clear a VPLS statistics information";
     junos:command "clear vpls statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "VPLS instance name";
         type string;
         mandatory true;
       }
     }
     output {
       choice output_c {
         case output-tag {
           leaf output {
             type string;
           }
         }
         case multichassis-tag {
           anyxml multi-routing-engine-results;
         }
       }
     }
   }
   rpc clear-vpls-mac-table {
     description "Clear all learned media access control addresses";
     junos:command "clear vpls mac-table";
     input {
       leaf instance {
         description "Display information for a specified instance";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-vpls-interface-mac-table {
     description "Clear media access control table for specified interface";
     junos:command "clear vpls mac-table interface";
     input {
       leaf interface-name {
         description "Name of interface for which to clear table";
         junos:cli-feature "nokeyword";
         type union {
           type jt:interface-unit;
           type string {
             pattern "<.*>|$.*";
           }
         }
         mandatory true;
       }
       leaf vlan-id {
         description "Clear MAC address learned on a specified VLAN";
         type string;
       }
     }
     output {
       choice output_c {
         case output-tag {
           leaf output {
             type string;
           }
         }
         case multichassis-tag {
           anyxml multi-routing-engine-results;
         }
       }
     }
   }
   rpc clear-ldp-neighbors {
     description "Clear LDP neighbors";
     junos:command "clear ldp neighbor";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
       choice clear_arg {
         case all {
           leaf all {
             description "Clear all neighbors";
             type empty;
           }
         }
         case neighbor {
           leaf neighbor {
             description "IP address of the neighbor";
             junos:cli-feature "nokeyword";
             type jt:ipaddr;
           }
         }
         case ldp-family {
           leaf ldp-family {
             junos:cli-feature "nokeyword";
             type enumeration {
               enum "inet" {
                 description "Clear IPv4 neighbors";
               }
               enum "inet6" {
                 description "Clear IPv6 neighbors";
               }
             }
           }
         }
       }
     }
     output {
       choice output_c {
         case output-tag {
           leaf output {
             type string;
           }
         }
         case multichassis-tag {
           anyxml multi-routing-engine-results;
         }
       }
     }
   }
   rpc clear-ldp-sessions {
     description "Clear LDP sessions";
     junos:command "clear ldp session";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
       choice clear_arg {
         case all {
           leaf all {
             description "Clear all sessions";
             type empty;
           }
         }
         case destination {
           leaf destination {
             description "IP address of session destination";
             junos:cli-feature "nokeyword";
             type jt:ipaddr;
           }
         }
         case ldp-family {
           leaf ldp-family {
             junos:cli-feature "nokeyword";
             type enumeration {
               enum "inet" {
                 description "Clear IPv4 sessions";
               }
               enum "inet6" {
                 description "Clear IPv6 sessions";
               }
             }
           }
         }
       }
     }
     output {
       choice output_c {
         case output-tag {
           leaf output {
             type string;
           }
         }
         case multichassis-tag {
           anyxml multi-routing-engine-results;
         }
       }
     }
   }
   rpc clear-ldp-statistics {
     description "Clear LDP statistics counters";
     junos:command "clear ldp statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
     }
     output {
       choice output_c {
         case output-tag {
           leaf output {
             type string;
           }
         }
         case multichassis-tag {
           anyxml multi-routing-engine-results;
         }
       }
     }
   }
   rpc clear-ldp-interface-hello-statistics {
     description "Clear LDP interface hello statistics";
     junos:command "clear ldp statistics interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of LDP routing instance";
         type string;
       }
     }
     output {
       choice output_c {
         case output-tag {
           leaf output {
             type string;
           }
         }
         case multichassis-tag {
           anyxml multi-routing-engine-results;
         }
       }
     }
   }
   rpc clear-mld-statistics {
     description "Clear MLD statistics";
     junos:command "clear mld statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
     }
     output {
       choice output_c {
         case output-tag {
           leaf output {
             type string;
           }
         }
         case multichassis-tag {
           anyxml multi-routing-engine-results;
         }
       }
     }
   }
   rpc clear-mld-membership {
     description "Clear MLD group membership";
     junos:command "clear mld membership";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       choice clear_arg {
         case group {
           leaf group {
             description "IPv6 address range for group";
             type jt:ipv6prefix;
           }
         }
         case all {
           leaf all {
             description "Clear all MLD group membership";
             type empty;
           }
         }
       }
     }
     output {
       choice output_c {
         case output-tag {
           leaf output {
             type string;
           }
         }
         case multichassis-tag {
           anyxml multi-routing-engine-results;
         }
       }
     }
   }
   rpc clear-mld-snooping-statistics {
     description "Clear MLD snooping statistics";
     junos:command "clear mld snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-bridge-domain-statistics {
     description "For a particular bridge-domain";
     junos:command "clear mld snooping statistics bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         junos:cli-feature "nokeyword";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-vlan-statistics {
     description "For a particular VLAN";
     junos:command "clear mld snooping statistics vlan";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         junos:cli-feature "nokeyword";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-membership {
     description "Clear MLD snooping group membership";
     junos:command "clear mld snooping membership";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         junos:cli-feature "nokeyword";
         type jt:ipv6prefix;
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
       leaf qualified-vlan {
         description "VLAN ID for a Qualified VLAN";
         type union {
           type string {
             pattern "<.*>|$.*";
           }
           type uint32 {
             range "0 .. 4094";
           }
         }
       }
     }
     output {
       choice output_c {
         case output-tag {
           leaf output {
             type string;
           }
         }
         case multichassis-tag {
           anyxml multi-routing-engine-results;
         }
       }
     }
   }
   rpc clear-mld-snooping-bridge-domain-membership {
     description "For a particular bridge-domain";
     junos:command "clear mld snooping membership bridge-domain";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf domain-name {
         description "Name of bridge-domain";
         junos:cli-feature "nokeyword";
         type string;
         mandatory true;
       }
       leaf interface {
         description "Name of interface";
         type string;
       }
       leaf vlan-id {
         description "VLAN ID for a learning domain";
         type union {
           type string {
             pattern "<.*>|$.*";
           }
           type uint32 {
             range "0 .. 4094";
           }
         }
       }
       leaf group {
         description "IP address range for group";
         type jt:ipv6prefix;
       }
     }
     output {
       choice output_c {
         case output-tag {
           leaf output {
             type string;
           }
         }
         case multichassis-tag {
           anyxml multi-routing-engine-results;
         }
       }
     }
   }
   rpc clear-mld-snooping-vlan-membership {
     description "For a particular VLAN";
     junos:command "clear mld snooping membership vlan";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf verbosity_level {
         junos:cli-feature "nokeyword";
         default "detail";
         type enumeration {
           enum "brief" {
             description "Display brief output (default)";
           }
           enum "detail" {
             description "Display detailed output";
           }
         }
       }
       leaf virtual-switch {
         description "Name of virtual-switch instance";
         type string;
       }
       leaf vlan-name {
         description "Name of VLAN";
         junos:cli-feature "nokeyword";
         type string;
         mandatory true;
       }
       leaf interface {
         description "Name of interface";
         type string;
       }
       leaf qualified-vlan {
         description "VLAN ID for a Qualified VLAN";
         type union {
           type string {
             pattern "<.*>|$.*";
           }
           type uint32 {
             range "0 .. 4094";
           }
         }
       }
       leaf group {
         description "IP address range for group";
         junos:cli-feature "nokeyword";
         type jt:ipv6prefix;
       }
     }
     output {
       choice output_c {
         case output-tag {
           leaf output {
             type string;
           }
         }
         case multichassis-tag {
           anyxml multi-routing-engine-results;
         }
       }
     }
   }
   rpc clear-mpls-lsp-information {
     description "Reset nontransit or egress LSPs originating on this router";
     junos:command "clear mpls lsp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf opt {
         junos:cli-feature "nokeyword";
         type enumeration {
           enum "optimize" {
             description "Perform nonpreemptive optimization computation now";
           }
           enum "optimize-aggressive" {
             description "Perform aggressive optimization computation now";
           }
         }
       }
       leaf stats {
         junos:cli-feature "nokeyword";
         type enumeration {
           enum "statistics" {
             description "Clear LSP statistics";
           }
           enum "reverse-statistics" {
             description "Clear LSP reverse-statistics for bidirectional LSPs";
           }
           enum "counters" {
             description "Clear LSP Flap/MBB counters";
           }
         }
       }
       leaf autobw {
         junos:cli-feature "nokeyword";
         type enumeration {
           enum "autobandwidth" {
             description "Clear LSP autobandwidth counters";
           }
         }
       }
       choice clear-arg {
         case name {
           leaf regex {
             description "Regular expression for LSP names to match";
             type string;
           }
         }
         case all {
           leaf all {
             description "Reset 'all' the ingress LSPs originating on this router";
             type empty;
           }
         }
       }
       leaf path {
         description "Regular expression for LSP path to match";
         type string;
       }
     }
     output {
       choice output_c {
         case output-tag {
           leaf output {
             type string;
           }
         }
         case multichassis-tag {
           anyxml multi-routing-engine-results;
         }
       }
     }
   }
   rpc clear-mpls-container-lsp-information {
     description "Reset nontransit or egress container LSP originating on this router";
     junos:command "clear mpls container-lsp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf opt {
         junos:cli-feature "nokeyword";
         type enumeration {
           enum "optimize" {
             description "Perform nonpreemptive optimization computation now";
           }
           enum "optimize-aggressive" {
             description "Perform aggressive optimization computation now";
           }
         }
       }
       leaf stats {
         junos:cli-feature "nokeyword";
         type enumeration {
           enum "statistics" {
             description "Clear LSP statistics";
           }
         }
       }
       leaf autobw {
         junos:cli-feature "nokeyword";
         type enumeration {
           enum "autobandwidth" {
             description "Clear LSP autobandwidth counters";
           }
         }
       }
       choice clear-arg {
         case name {
           leaf regex {
             description "Name of Container LSP";
             type string;
           }
         }
         case all {
           leaf all {
             description "Reset 'all' the nontransit or egress Container LSPs originating on this router";
             type empty;
           }
         }
       }
       leaf history {
         junos:cli-feature "nokeyword";
         type enumeration {
           enum "history" {
             description "Clear container LSP samples from the history";
           }
         }
       }
       leaf member {
         description "Regular expression for member LSP names to match";
         type string;
       }
     }
     output {
       choice output_c {
         case output-tag {
           leaf output {
             type string;
           }
         }
         case multichassis-tag {
           anyxml multi-routing-engine-results;
         }
       }
     }
   }
   rpc clear-mpls-label-information {
     description "MPLS label";
     junos:command "clear mpls label";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf history {
         junos:cli-feature "nokeyword";
         type enumeration {
           enum "history" {
             description "Clear label history";
           }
         }
         mandatory true;
       }
     }
     output {
       choice output_c {
         case output-tag {
           leaf output {
             type string;
           }
         }
         case multichassis-tag {
           anyxml multi-routing-engine-results;
         }
       }
     }
   }
   rpc clear-mpls-tunnel-manager-statistics-information {
     description "MPLS tunnel manager statistics";
     junos:command "clear mpls tunnel-manager-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case multichassis-tag {
           anyxml multi-routing-engine-results;
         }
       }
     }
   }
   rpc clear-mpls-static-lsp-information {
     description "Reset static LSP statistics";
     junos:command "clear mpls static-lsp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf stats {
         junos:cli-feature "nokeyword";
         type enumeration {
           enum "statistics" {
             description "Clear LSP statistics";
           }
         }
         mandatory true;
       }
       leaf regex {
         description "Regular expression for LSP names to match";
         type string;
       }
     }
     output {
       choice output_c {
         case output-tag {
           leaf output {
             type string;
           }
         }
         case multichassis-tag {
           anyxml multi-routing-engine-results;
         }
       }
     }
   }
   rpc clear-mpls-traceroute-database-ldp {
     description "Clear FECs";
     junos:command "clear mpls traceroute database ldp";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf fec {
         description "IP address and optional prefix length of FEC";
         junos:cli-feature "nokeyword";
         type jt:ipprefix;
       }
       leaf routing-instance {
         description "Name of routing instance, or 'all'";
         type string {
           junos:posix-pattern "!^((__.*__)|(all)|(.*[ ].*)|(\"\")|(.{129,}))$";
           junos:pattern-message "Must be a non-reserved string of 128 characters or less with no spaces.";
         }
       }
     }
     output {
       choice output_c {
         case output-tag {
           leaf output {
             type string;
           }
         }
         case multichassis-tag {
           anyxml multi-routing-engine-results;
         }
       }
     }
   }
   rpc clear-pm-mpls-lsp-information {
     description "Reset non-transit or egress LSPs originating on this router";
     junos:command "clear performance-monitoring mpls lsp";
     input {
       leaf regex {
         description "Regular expression for LSP names to match";
         type string;
       }
     }
     output {
       choice output_c {
         case output-tag {
           leaf output {
             type string;
           }
         }
         case multichassis-tag {
           anyxml multi-routing-engine-results;
         }
       }
     }
   }
   rpc clear-msdp-statistics {
     description "Clear MSDP peer statistics";
     junos:command "clear msdp statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf peer {
         description "IP address of peer that provided statistics";
         type jt:ipv4addr;
       }
     }
     output {
       choice output_c {
         case output-tag {
           leaf output {
             type string;
           }
         }
         case multichassis-tag {
           anyxml multi-routing-engine-results;
         }
       }
     }
   }
   rpc clear-msdp-cache {
     description "Clear the MSDP source-active cache";
     junos:command "clear msdp cache";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       choice clear_arg {
         case peer {
           leaf peer {
             description "IP address of peer that provided cache entries";
             type jt:ipv4addr;
           }
         }
         case all {
           leaf all {
             description "Clear all MSDP source-active cache entries";
             type empty;
           }
         }
       }
     }
     output {
       choice output_c {
         case output-tag {
           leaf output {
             type string;
           }
         }
         case multichassis-tag {
           anyxml multi-routing-engine-results;
         }
       }
     }
   }
   rpc clear-multicast-sessions {
     description "Clear multicast sessions";
     junos:command "clear multicast sessions";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regexp {
         description "Regular expression for sessions to match";
         junos:cli-feature "nokeyword";
         type string;
       }
     }
     output {
       choice output_c {
         case output-tag {
           leaf output {
             type string;
           }
         }
         case multichassis-tag {
           anyxml multi-routing-engine-results;
         }
       }
     }
   }
   rpc clear-multicast-statistics {
     description "Clear multicast statistics";
     junos:command "clear multicast statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of interface";
         type string;
       }
       leaf family {
         description "Address family";
         junos:cli-feature "nokeyword";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-multicast-forwarding-cache {
     description "Clear multicast forwarding cache";
     junos:command "clear multicast forwarding-cache";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         junos:cli-feature "nokeyword";
         default "inet";
         type enumeration {
           enum "inet" {
             description "Clear IPv4 forwarding cache";
           }
           enum "inet6" {
             description "Clear IPv6 forwarding cache";
           }
         }
       }
       leaf all {
         description "Clear all multicast forwarding cache entries";
         type empty;
         mandatory true;
       }
     }
     output {
       choice output_c {
         case output-tag {
           leaf output {
             type string;
           }
         }
         case multichassis-tag {
           anyxml multi-routing-engine-results;
         }
       }
     }
   }
   rpc clear-multicast-scope-statistics {
     description "Clear multicast scope statistics";
     junos:command "clear multicast scope";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       leaf family {
         description "Address family";
         junos:cli-feature "nokeyword";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-multicast-bandwidth-admission {
     description "Re-apply bandwidth admission control";
     junos:command "clear multicast bandwidth-admission";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         junos:cli-feature "nokeyword";
         default "inet";
         type enumeration {
           enum "inet" {
             description "For IPv4 ";
           }
           enum "inet6" {
             description "For IPv6 ";
           }
         }
       }
       leaf group {
         description "Destination group address";
         type jt:ipaddr;
       }
       leaf source {
         description "Source address";
         type jt:ipaddr;
       }
       leaf interface {
         description "Name of interface";
         type string;
       }
     }
     output {
       choice output_c {
         case output-tag {
           leaf output {
             type string;
           }
         }
         case multichassis-tag {
           anyxml multi-routing-engine-results;
         }
       }
     }
   }
   rpc clear-ospf-neighbor-information {
     description "Clear OSPF neighbors";
     junos:command "clear ospf neighbor";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear all Neighbor";
         type empty;
       }
       leaf interface {
         description "Name of logical interface";
         type string;
       }
       leaf neighbor {
         description "Name of neighbor";
         junos:cli-feature "nokeyword";
         type string;
       }
       leaf area {
         description "OSPF area ID";
         type jt:areaid;
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-database-information {
     description "Clear OSPF database entries";
     junos:command "clear ospf database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf flex-algorithm-id {
         description "Flex Algorithm id";
         type union {
           type string {
             pattern "<.*>|$.*";
           }
           type uint32 {
             range "128 .. 255";
           }
         }
       }
       leaf all {
         description "Clear All Database";
         type empty;
       }
       leaf area {
         description "OSPF area ID";
         default "all";
         type string;
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-database-protection {
     description "Clear OSPF database protection related state";
     junos:command "clear ospf database-protection";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-statistics-information {
     description "Clear OSPF statistics";
     junos:command "clear ospf statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-intf-statistics-information {
     description "Clear OSPF interface statistics information";
     junos:command "clear ospf statistics interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF routing instance";
         type string;
       }
       leaf interface-name {
         description "Name of interface";
         junos:cli-feature "nokeyword";
         type string;
       }
       leaf all {
         description "Clear all interface statistics";
         type empty;
       }
     }
     output {
       choice output_c {
         case output-tag {
           leaf output {
             type string;
           }
         }
         case multichassis-tag {
           anyxml multi-routing-engine-results;
         }
       }
     }
   }
   rpc clear-ospf-io-statistics-information {
     description "Clear OSPF I/O statistics";
     junos:command "clear ospf io-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-ospf-overload-information {
     description "Clear overload bit and rebuild LSAs";
     junos:command "clear ospf overload";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPF instance";
         type string;
       }
     }
     output {
       choice output_c {
         case output-tag {
           leaf output {
             type string;
           }
         }
         case multichassis-tag {
           anyxml multi-routing-engine-results;
         }
       }
     }
   }
   rpc clear-ospf-spring-information {
     description "Clear SPRING information";
     junos:command "clear ospf spring";
     output {
       choice output_c {
         case output-tag {
           leaf output {
             type string;
           }
         }
         case multichassis-tag {
           anyxml multi-routing-engine-results;
         }
       }
     }
   }
   rpc clear-ospf-spring-flex-algorithm-information {
     description "Clear SPRING flex-algorithm information";
     junos:command "clear ospf spring flex-algorithm-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf flex-algorithm-id {
         description "Flex Algorithm id";
         type union {
           type string {
             pattern "<.*>|$.*";
           }
           type uint32 {
             range "128 .. 255";
           }
         }
       }
     }
     output {
       choice output_c {
         case output-tag {
           leaf output {
             type string;
           }
         }
         case multichassis-tag {
           anyxml multi-routing-engine-results;
         }
       }
     }
   }
   rpc clear-ospf3-neighbor-information {
     description "Clear OSPFv3 neighbors";
     junos:command "clear ospf3 neighbor";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear all Neighbor";
         type empty;
       }
       leaf interface {
         description "Name of logical interface";
         type string;
       }
       leaf neighbor {
         description "Name of OSPFv3 neighbor";
         junos:cli-feature "nokeyword";
         type string;
       }
       leaf area {
         description "OSPF area ID";
         type jt:areaid;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-database-information {
     description "Clear OSPFv3 database entries";
     junos:command "clear ospf3 database";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf all {
         description "Clear All Database";
         type empty;
       }
       leaf area {
         description "Area ID of OSPFv3 area";
         default "all";
         type string;
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-database-protection-information {
     description "Clear OSPFv3 database protection related state";
     junos:command "clear ospf3 database-protection";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-statistics-information {
     description "Clear OSPFv3 statistics";
     junos:command "clear ospf3 statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-ospf3-intf-statistics-information {
     description "Clear OSPFv3 interface statistics information";
     junos:command "clear ospf3 statistics interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 routing instance";
         type string;
       }
       leaf interface-name {
         description "Name of interface";
         junos:cli-feature "nokeyword";
         type string;
       }
       leaf all {
         description "Clear all interface statistics";
         type empty;
       }
     }
     output {
       choice output_c {
         case output-tag {
           leaf output {
             type string;
           }
         }
         case multichassis-tag {
           anyxml multi-routing-engine-results;
         }
       }
     }
   }
   rpc clear-ospf3-io-statistics-information {
     description "Clear OSPFv3 I/O statistics";
     junos:command "clear ospf3 io-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-ospf3-overload-information {
     description "Clear overload bit and rebuild LSAs";
     junos:command "clear ospf3 overload";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of OSPFv3 instance";
         type string;
       }
       leaf realm {
         description "Name of realm";
         type enumeration {
           enum "ipv6-multicast" {
             description "IPv6 multicast realm";
           }
           enum "ipv4-unicast" {
             description "IPv4 unicast realm";
           }
           enum "ipv4-multicast" {
             description "IPv4 multicast realm";
           }
         }
       }
     }
     output {
       choice output_c {
         case output-tag {
           leaf output {
             type string;
           }
         }
         case multichassis-tag {
           anyxml multi-routing-engine-results;
         }
       }
     }
   }
   rpc clear-pim-statistics {
     description "Clear PIM statistics";
     junos:command "clear pim statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf interface {
         description "Name of interface";
         type string;
       }
       leaf family {
         description "Address family";
         junos:cli-feature "nokeyword";
         default "inet";
         type enumeration {
           enum "inet" {
             description "Clear IPv4 statistics";
           }
           enum "inet6" {
             description "Clear IPv6 statistics";
           }
         }
       }
     }
     output {
       choice output_c {
         case output-tag {
           leaf output {
             type string;
           }
         }
         case multichassis-tag {
           anyxml multi-routing-engine-results;
         }
       }
     }
   }
   rpc clear-pim-join-state {
     description "Clear PIM join/prune state";
     junos:command "clear pim join";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       choice clear_arg {
         case group {
           leaf group {
             description "IP address and optional prefix length of group";
             junos:cli-feature "nokeyword";
             type jt:ipprefix;
           }
         }
         case all {
           leaf all {
             description "Clear all PIM join/prune states";
             type empty;
           }
         }
       }
       leaf exact {
         description "Clear only group that matches exactly";
         type empty;
       }
       leaf source {
         description "IP address and optional prefix length of source";
         type jt:ipprefix;
       }
       leaf rp {
         description "IP address and optional prefix length of rendezvous point";
         type jt:ipprefix;
       }
       leaf sparse {
         description "Clear only PIM sparse-mode entries (including SSM)";
         type empty;
       }
       leaf dense {
         description "Clear only PIM dense-mode entries";
         type empty;
       }
       leaf bidirectional {
         description "Clear only bidirectional PIM entries";
         type empty;
       }
       leaf star-g {
         description "Clear only *,G entries";
         type empty;
       }
       leaf sg {
         description "Clear only S,G entries";
         type empty;
       }
       leaf family {
         description "Address family";
         junos:cli-feature "nokeyword";
         default "inet";
         type enumeration {
           enum "inet" {
             description "Clear IPv4 join/prune state";
           }
           enum "inet6" {
             description "Clear IPv6 join/prune state";
           }
         }
       }
     }
     output {
       choice output_c {
         case output-tag {
           leaf output {
             type string;
           }
         }
         case multichassis-tag {
           anyxml multi-routing-engine-results;
         }
       }
     }
   }
   rpc clear-pim-register-state {
     description "Clear PIM register state";
     junos:command "clear pim register";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf family {
         description "Address family";
         junos:cli-feature "nokeyword";
         default "inet";
         type enumeration {
           enum "inet" {
             description "Clear IPv4 register state";
           }
           enum "inet6" {
             description "Clear IPv6 register state";
           }
         }
       }
       leaf all {
         description "Clear all PIM register states";
         type empty;
         mandatory true;
       }
     }
     output {
       choice output_c {
         case output-tag {
           leaf output {
             type string;
           }
         }
         case multichassis-tag {
           anyxml multi-routing-engine-results;
         }
       }
     }
   }
   rpc clear-pim-join-distribution {
     description "Redistribute PIM joins";
     junos:command "clear pim join-distribution";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of instance";
         type string;
       }
       leaf all {
         description "Redistribute all PIM joins";
         type empty;
         mandatory true;
       }
     }
     output {
       choice output_c {
         case output-tag {
           leaf output {
             type string;
           }
         }
         case multichassis-tag {
           anyxml multi-routing-engine-results;
         }
       }
     }
   }
   rpc clear-pim-snooping-join {
     description "Clear PIM snooping join";
     junos:command "clear pim snooping join";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf group {
         description "IP address range for group";
         junos:cli-feature "nokeyword";
         type jt:ipv4prefix;
       }
       leaf vlan-id {
         description "VLAN ID for a learning domain";
         type union {
           type string {
             pattern "<.*>|$.*";
           }
           type uint32 {
             range "0 .. 4094";
           }
         }
       }
       leaf instance {
         description "Name of routing-instance";
         type string;
       }
     }
     output {
       choice output_c {
         case output-tag {
           leaf output {
             type string;
           }
         }
         case multichassis-tag {
           anyxml multi-routing-engine-results;
         }
       }
     }
   }
   rpc clear-pim-snooping-statistics {
     description "Clear PIM snooping statistics";
     junos:command "clear pim snooping statistics";
     input {
       leaf logical-system {
         description "Name of logical system, or 'all'";
         type string {
           junos:posix-pattern "^[a-zA-Z0-9_-]{1,63}$";
           junos:pattern-message "Logical-system name is a string consisting of up to 63 letters, numbers, dashes and underscores";
         }
       }
       leaf interface {
         description "Name of interface";
         type string;
       }
       leaf vlan-id {
         description "VLAN ID for a learning domain";
         type union {
           type string {
             pattern "<.*>|$.*";
           }
           type uint32 {
             range "0 .. 4094";
           }
         }
       }
       leaf instance {
         description "Name of routing-instance";
         type string;
       }
     }
     output {
       choice output_c {
         case output-tag {
           leaf output {
             type string;
           }
         }
         case multichassis-tag {
           anyxml multi-routing-engine-results;
         }
       }
     }
   }
   rpc clear-ripng-statistics {
     description "Clear RIPng statistics";
     junos:command "clear ripng statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor-name {
         description "Name of RIPng neighbor";
         junos:cli-feature "nokeyword";
         type string;
       }
       leaf instance {
         description "Name of RIPng instance";
         type string;
       }
     }
     output {
       choice output_c {
         case output-tag {
           leaf output {
             type string;
           }
         }
         case multichassis-tag {
           anyxml multi-routing-engine-results;
         }
       }
     }
   }
   rpc clear-ripng-general-statistics {
     description "Clear RIPng general statistics";
     junos:command "clear ripng general-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-rip-statistics {
     description "Clear RIP statistics";
     junos:command "clear rip statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor-name {
         description "Name of RIP neighbor";
         junos:cli-feature "nokeyword";
         type string;
       }
       leaf instance {
         description "Name of RIP instance";
         type string;
       }
     }
     output {
       choice output_c {
         case output-tag {
           leaf output {
             type string;
           }
         }
         case multichassis-tag {
           anyxml multi-routing-engine-results;
         }
       }
     }
   }
   rpc clear-rip-peer-statistics {
     description "Clear peer statistics";
     junos:command "clear rip statistics peer";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf address {
         description "Ip address of peer";
         junos:cli-feature "nokeyword";
         type string;
       }
       leaf peer-all {
         description "Clear statistics of all peers";
         junos:cli-feature "nokeyword";
         type enumeration {
           enum "all" {
             description "Clear statistics of all peers";
           }
         }
       }
     }
     output {
       choice output_c {
         case output-tag {
           leaf output {
             type string;
           }
         }
         case multichassis-tag {
           anyxml multi-routing-engine-results;
         }
       }
     }
   }
   rpc clear-rip-general-statistics {
     description "Clear RIP general statistics";
     junos:command "clear rip general-statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc clear-validation-database {
     description "Clear the route validation database";
     junos:command "clear validation database";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-validation-session {
     description "Clear route validation session";
     junos:command "clear validation session";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf destination {
         description "IP address of session";
         junos:cli-feature "nokeyword";
         type jt:ipaddr;
       }
       leaf disposition {
         junos:cli-feature "nokeyword";
         type enumeration {
           enum "soft-inbound" {
             description "Soft reset inbound state by issuing Reset request";
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-validation-statistics {
     description "Clear route validation statistics";
     junos:command "clear validation statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf instance {
         description "Name of route validation instance";
         type string;
       }
     }
     output {
       choice output_c {
         case output-tag {
           leaf output {
             type string;
           }
         }
         case multichassis-tag {
           anyxml multi-routing-engine-results;
         }
       }
     }
   }
   rpc clear-rsvp-session-information {
     description "Preempt RSVP session";
     junos:command "clear rsvp session";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       choice clear-choice {
         case name {
           leaf session-name {
             description "Name of session - Must select 'name' or 'all'";
             type string;
           }
         }
         case all {
           leaf all {
             description "All matching sessions - Must select 'name' or 'all'";
             type empty;
           }
         }
       }
       leaf instance {
         description "Name of routing instance";
         type string;
       }
       leaf lsp-id {
         description "LSP ID of the RSVP sender";
         type union {
           type string {
             pattern "<.*>|$.*";
           }
           type uint32 {
             range "1 .. 65535";
           }
         }
       }
       leaf tunnel-id {
         description "Tunnel ID of the RSVP session";
         type union {
           type string {
             pattern "<.*>|$.*";
           }
           type uint32 {
             range "1 .. 65535";
           }
         }
       }
       leaf connection-source {
         description "Source of the label-switched path";
         type jt:ipaddr;
       }
       leaf connection-destination {
         description "Destination of the label-switched path";
         type jt:ipaddr;
       }
       leaf optimize-fast-reroute {
         description "Perform fast-reroute optimization computation now";
         type empty;
       }
       leaf gracefully {
         description "Gracefully tear down RSVP sessions";
         type empty;
       }
     }
     output {
       choice output_c {
         case output-tag {
           leaf output {
             type string;
           }
         }
         case multichassis-tag {
           anyxml multi-routing-engine-results;
         }
       }
     }
   }
   rpc clear-rsvp-counters-information {
     description "Clear RSVP counters";
     junos:command "clear rsvp statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case multichassis-tag {
           anyxml multi-routing-engine-results;
         }
       }
     }
   }
   rpc clear-l2-learning-mac-move-buffer {
     description "Clear the mac move buffer contents";
     junos:command "clear l2-learning mac-move-buffer";
     output {
       choice output_c {
         case output-tag {
           leaf output {
             type string;
           }
         }
         case multichassis-tag {
           anyxml multi-routing-engine-results;
         }
       }
     }
   }
   rpc clear-l2-learning-mac-move-buffer-active {
     description "Clear the active mac move buffer entries";
     junos:command "clear l2-learning mac-move-buffer active";
     output {
       choice output_c {
         case output-tag {
           leaf output {
             type string;
           }
         }
         case multichassis-tag {
           anyxml multi-routing-engine-results;
         }
       }
     }
   }
   rpc clear-l2-learning-context-history {
     description "Clear context history";
     junos:command "clear l2-learning context-history";
     output {
       choice output_c {
         case output-tag {
           leaf output {
             type string;
           }
         }
         case multichassis-tag {
           anyxml multi-routing-engine-results;
         }
       }
     }
   }
   rpc clear-l2-learning-remote-backbone-edge-bridges {
     description "Clear remote backbone edge bridges in a PBBN network";
     junos:command "clear l2-learning remote-backbone-edge-bridges";
     input {
       leaf remote-beb-mac-address {
         description "Remote backbone edge bridge MAC address";
         junos:cli-feature "nokeyword";
         default "all";
         type jt:mac-addr;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
     }
     output {
       choice output_c {
         case output-tag {
           leaf output {
             type string;
           }
         }
         case multichassis-tag {
           anyxml multi-routing-engine-results;
         }
       }
     }
   }
   rpc clear-l2-learning-redundancy-group-statistics {
     description "Clear redundancy group statistics counters";
     junos:command "clear l2-learning redundancy-group";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf redundancy-group-id {
         description "Display information for a specified RG";
         junos:cli-feature "nokeyword";
         default "0";
         type union {
           type string {
             pattern "<.*>|$.*";
           }
           type uint32 {
             range "0 .. 4294967294";
           }
         }
       }
       leaf options {
         description "Clear information for specified RG or all RG(s)";
         junos:cli-feature "nokeyword";
         type enumeration {
           enum "arp-statistics" {
             description "Show MCAE ARP Synchronization statistics";
           }
           enum "nd-statistics" {
             description "Show MCAE ND synchronization statistics";
           }
         }
       }
     }
     output {
       choice output_c {
         case output-tag {
           leaf output {
             type string;
           }
         }
         case multichassis-tag {
           anyxml multi-routing-engine-results;
         }
       }
     }
   }
   rpc clear-bridge-mac-table {
     description "Clear all learned media access control addresses";
     junos:command "clear bridge mac-table";
     input {
       leaf instance {
         description "Display information for a specified instance";
         default "all";
         type string;
       }
       leaf bridge-domain {
         description "Name of bridging domain, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-bridge-interface-mac-table {
     description "Clear media access control table for specified interface";
     junos:command "clear bridge mac-table interface";
     input {
       leaf interface-name {
         description "Name of interface for which to clear table";
         junos:cli-feature "nokeyword";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-bridge-recovery {
     description "Clear port error";
     junos:command "clear bridge recovery-timeout";
     output {
       choice output_c {
         case output-tag {
           leaf output {
             type string;
           }
         }
         case multichassis-tag {
           anyxml multi-routing-engine-results;
         }
       }
     }
   }
   rpc clear-bridge-recovery-interface {
     description "Clear port error for specified interface";
     junos:command "clear bridge recovery-timeout interface";
     input {
       leaf interface-name {
         description "Name of interface for which to clear table";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-bridge-statistics {
     description "Clear bridge statistics information";
     junos:command "clear bridge statistics";
     input {
       leaf bridge-domain {
         description "Name of bridging domain";
         type string;
         mandatory true;
       }
       leaf instance {
         description "Display information for a specified instance";
         type string;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case multichassis-tag {
           anyxml multi-routing-engine-results;
         }
       }
     }
   }
   rpc clear-ethernet-switching-context-history {
     description "Clear context history";
     junos:command "clear ethernet-switching context-history";
     output {
       choice output_c {
         case output-tag {
           leaf output {
             type string;
           }
         }
         case multichassis-tag {
           anyxml multi-routing-engine-results;
         }
       }
     }
   }
   rpc clear-ethernet-switching-table {
     description "Clear all learned media access control addresses";
     junos:command "clear ethernet-switching table";
     input {
       leaf instance {
         description "Display information for a specified instance";
         default "all";
         type string;
       }
       leaf vlan-name {
         description "Name of VLAN, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-ethernet-switching-interface-table {
     description "Clear media access control table for specified interface";
     junos:command "clear ethernet-switching table interface";
     input {
       leaf interface-name {
         description "Name of interface for which to clear table";
         junos:cli-feature "nokeyword";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-ethernet-switching-table-persistent-learning {
     description "Clear persistent-mac entries";
     junos:command "clear ethernet-switching table persistent-learning";
     output {
       choice output_c {
         case output-tag {
           leaf output {
             type string;
           }
         }
         case multichassis-tag {
           anyxml multi-routing-engine-results;
         }
       }
     }
   }
   rpc clear-ethernet-switching-table-persistent-learning-interface {
     description "Clear persistent MACs for specified interface";
     junos:command "clear ethernet-switching table persistent-learning interface";
     input {
       leaf interface-name {
         description "Name of interface for which to clear table";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-ethernet-switching-table-persistent-learning-mac {
     description "Clear one persitent MAC or all peristent MACs";
     junos:command "clear ethernet-switching table persistent-learning mac";
     input {
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-ethernet-switching-recovery {
     description "Clear port error";
     junos:command "clear ethernet-switching recovery-timeout";
     output {
       choice output_c {
         case output-tag {
           leaf output {
             type string;
           }
         }
         case multichassis-tag {
           anyxml multi-routing-engine-results;
         }
       }
     }
   }
   rpc clear-ethernet-switching-recovery-interface {
     description "Clear port error for specified interface";
     junos:command "clear ethernet-switching recovery-timeout interface";
     input {
       leaf interface-name {
         description "Name of interface for which to clear table";
         junos:cli-feature "nokeyword";
         type union {
           type jt:interface-name;
           type string {
             pattern "<.*>|$.*";
           }
         }
         mandatory true;
       }
       leaf vlan {
         description "VLAN(name or ID)";
         type string;
       }
     }
     output {
       choice output_c {
         case output-tag {
           leaf output {
             type string;
           }
         }
         case multichassis-tag {
           anyxml multi-routing-engine-results;
         }
       }
     }
   }
   rpc clear-ethernet-switching-mac-learning-log {
     description "Clear all MAC address learning log";
     junos:command "clear ethernet-switching mac-learning-log";
     output {
       choice output_c {
         case output-tag {
           leaf output {
             type string;
           }
         }
         case multichassis-tag {
           anyxml multi-routing-engine-results;
         }
       }
     }
   }
   rpc clear-vlans-mac-ip-table {
     description "Clear IPv4 and IPv6 entries for EVPN instances";
     junos:command "clear ethernet-switching mac-ip-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-ethernet-switching-evpn-arp-table {
     description "Clear all INET addresses learned via ARP";
     junos:command "clear ethernet-switching evpn arp-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-ethernet-switching-evpn-nd-table {
     description "Clear all INET6 addresses learned via NDP";
     junos:command "clear ethernet-switching evpn nd-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-mac-vrf-mac-table {
     description "Clear all learned media access control addresses";
     junos:command "clear mac-vrf forwarding mac-table";
     input {
       leaf instance {
         description "Display information for a specified instance";
         default "all";
         type string;
       }
       leaf vlan-name {
         description "Name of VLAN, or 'all'";
         default "all";
         type string;
       }
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf vlan-id {
         description "Clear MAC address learned on a specified VLAN";
         type string;
       }
       leaf isid {
         description "Clear MAC address learned on a specified ISID";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-mac-vrf-interface-table {
     description "Clear media access control table for specified interface";
     junos:command "clear mac-vrf forwarding mac-table interface";
     input {
       leaf interface-name {
         description "Name of interface for which to clear table";
         junos:cli-feature "nokeyword";
         type string;
         mandatory true;
       }
       leaf remote-beb-mac-address {
         description "Remote backbone edge bridge MAC address";
         default "all";
         type jt:mac-addr;
       }
       leaf vlan-id {
         description "Clear MAC address learned on a specified VLAN";
         type string;
       }
       leaf isid {
         description "Clear MAC address learned on a specified ISID";
         type string;
       }
     }
     output {
       choice output_c {
         case output-tag {
           leaf output {
             type string;
           }
         }
         case multichassis-tag {
           anyxml multi-routing-engine-results;
         }
       }
     }
   }
   rpc clear-mac-vrf-table-persistent-learning {
     description "Clear persistent-mac entries";
     junos:command "clear mac-vrf forwarding mac-table persistent-learning";
     output {
       choice output_c {
         case output-tag {
           leaf output {
             type string;
           }
         }
         case multichassis-tag {
           anyxml multi-routing-engine-results;
         }
       }
     }
   }
   rpc clear-mac-vrf-persistent-learning-interface {
     description "Clear persistent MACs for specified interface";
     junos:command "clear mac-vrf forwarding mac-table persistent-learning interface";
     input {
       leaf interface-name {
         description "Name of interface for which to clear table";
         junos:cli-feature "nokeyword";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc clear-mac-vrf-table-persistent-learning-mac {
     description "Clear one persitent MAC or all peristent MACs";
     junos:command "clear mac-vrf forwarding mac-table persistent-learning mac";
     input {
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-mac-vrf-recovery {
     description "Clear port error";
     junos:command "clear mac-vrf forwarding recovery-timeout";
     output {
       choice output_c {
         case output-tag {
           leaf output {
             type string;
           }
         }
         case multichassis-tag {
           anyxml multi-routing-engine-results;
         }
       }
     }
   }
   rpc clear-mac-vrf-recovery-interface {
     description "Clear port error for specified interface";
     junos:command "clear mac-vrf forwarding recovery-timeout interface";
     input {
       leaf interface-name {
         description "Name of interface for which to clear table";
         junos:cli-feature "nokeyword";
         type union {
           type jt:interface-name;
           type string {
             pattern "<.*>|$.*";
           }
         }
         mandatory true;
       }
       leaf vlan {
         description "VLAN(name or ID)";
         type string;
       }
     }
     output {
       choice output_c {
         case output-tag {
           leaf output {
             type string;
           }
         }
         case multichassis-tag {
           anyxml multi-routing-engine-results;
         }
       }
     }
   }
   rpc clear-mac-vrf-mac-learning-log {
     description "Clear all MAC address learning log";
     junos:command "clear mac-vrf forwarding mac-learning-log";
     output {
       choice output_c {
         case output-tag {
           leaf output {
             type string;
           }
         }
         case multichassis-tag {
           anyxml multi-routing-engine-results;
         }
       }
     }
   }
   rpc clear-mac-vrf-redundancy-group-statistics {
     description "Clear redundancy group statistics counters";
     junos:command "clear mac-vrf forwarding redundancy-group";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf redundancy-group-id {
         description "Display information for a specified RG";
         junos:cli-feature "nokeyword";
         default "0";
         type union {
           type string {
             pattern "<.*>|$.*";
           }
           type uint32 {
             range "0 .. 4294967294";
           }
         }
       }
       leaf options {
         description "Clear information for specified RG or all RG(s)";
         junos:cli-feature "nokeyword";
         type enumeration {
           enum "arp-statistics" {
             description "Show MCAE ARP Synchronization statistics";
           }
           enum "nd-statistics" {
             description "Show MCAE ND synchronization statistics";
           }
         }
       }
     }
     output {
       choice output_c {
         case output-tag {
           leaf output {
             type string;
           }
         }
         case multichassis-tag {
           anyxml multi-routing-engine-results;
         }
       }
     }
   }
   rpc clear-mac-vrf-mac-ip-table {
     description "Clear IPv4 and IPv6 entries for EVPN instances";
     junos:command "clear mac-vrf forwarding mac-ip-table";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-mac-vrf-mac-ipv4-table {
     description "Clear all INET addresses learned via ARP";
     junos:command "clear mac-vrf forwarding mac-ip-table ipv4";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-mac-vrf-mac-ipv6-table {
     description "Clear all INET6 addresses learned via NDP";
     junos:command "clear mac-vrf forwarding mac-ip-table ipv6";
     input {
       leaf logical-system {
         description "Name of logical system, or 'all'";
         default "all";
         type string {
           junos:posix-pattern "^[a-zA-Z0-9_-]{1,63}$";
           junos:pattern-message "Logical-system name is a string consisting of up to 63 letters, numbers, dashes and underscores";
         }
       }
       leaf instance {
         description "Display information for a specified instance";
         default "all";
         type string;
       }
       leaf vlan-name {
         description "Name of VLAN, or 'all'";
         default "all";
         type string;
       }
       leaf address {
         description "MAC address";
         junos:cli-feature "nokeyword";
         default "all";
         type jt:mac-addr;
       }
     }
     output {
       choice output_c {
         case output-tag {
           leaf output {
             type string;
           }
         }
         case multichassis-tag {
           anyxml multi-routing-engine-results;
         }
       }
     }
   }
   rpc clear-lldp-neighbors {
     description "Clear LLDP neighbor information";
     junos:command "clear lldp neighbors";
     output {
       choice output_c {
         case output-tag {
           leaf output {
             type string;
           }
         }
         case multichassis-tag {
           anyxml multi-routing-engine-results;
         }
       }
     }
   }
   rpc clear-lldp-interface-neighbors {
     description "Clear LLDP interface statistics";
     junos:command "clear lldp neighbors interface";
     input {
       leaf interface-device {
         description "Name of interface";
         junos:cli-feature "nokeyword";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-lldp-statistics {
     description "Clear LLDP statistics";
     junos:command "clear lldp statistics";
     output {
       choice output_c {
         case output-tag {
           leaf output {
             type string;
           }
         }
         case multichassis-tag {
           anyxml multi-routing-engine-results;
         }
       }
     }
   }
   rpc clear-lldp-interface-statistics {
     description "Clear LLDP interface statistics";
     junos:command "clear lldp statistics interface";
     input {
       leaf interface-device {
         description "Name of interface";
         junos:cli-feature "nokeyword";
         type union {
           type jt:interface-device;
           type string {
             pattern "<.*>|$.*";
           }
         }
       }
     }
     output {
       choice output_c {
         case output-tag {
           leaf output {
             type string;
           }
         }
         case multichassis-tag {
           anyxml multi-routing-engine-results;
         }
       }
     }
   }
   rpc clear-passive-monitoring {
     description "Clear passive monitoring statistics";
     junos:command "clear passive-monitoring";
     output {
       choice output_c {
         case output-tag {
           leaf output {
             type string;
           }
         }
         case multichassis-tag {
           anyxml multi-routing-engine-results;
         }
       }
     }
   }
   rpc clear-passive-monitoring-statistics {
     description "Clear statistics";
     junos:command "clear passive-monitoring statistics";
     input {
       leaf interface-name {
         description "Name of monitoring interface, wildcard, or 'all'";
         junos:cli-feature "nokeyword";
         type string;
         mandatory true;
       }
     }
     output {
       choice output_c {
         case output-tag {
           leaf output {
             type string;
           }
         }
         case multichassis-tag {
           anyxml multi-routing-engine-results;
         }
       }
     }
   }
   rpc clear-ppp-statistics-information {
     description "Clear PPP statistics";
     junos:command "clear ppp statistics";
     input {
       leaf type {
         description "Type of statistic to clear";
         junos:cli-feature "nokeyword";
         type enumeration {
           enum "memory" {
             description "Clear PPP process memory statistics";
           }
         }
       }
     }
     output {
       choice output_c {
         case output-tag {
           leaf output {
             type string;
           }
         }
         case multichassis-tag {
           anyxml multi-routing-engine-results;
         }
       }
     }
   }
   rpc clear-database-replication-statistics-information {
     description "Clear database replication statistics";
     junos:command "clear database-replication statistics";
     output {
       choice output_c {
         case output-tag {
           leaf output {
             type string;
           }
         }
         case multichassis-tag {
           anyxml multi-routing-engine-results;
         }
       }
     }
   }
   rpc clear-firewall-counters {
     description "Clear firewall counters";
     junos:command "clear firewall";
     input {
       uses command-forwarding;
       leaf counter {
         description "Counter name";
         type string;
       }
       leaf filter {
         description "Filter name";
         type string;
         mandatory true;
       }
       choice daemon-select {
         case logical-system {
         }
       }
     }
     output {
       choice output_c {
         case output-tag {
           leaf output {
             type string;
           }
         }
         case multichassis-tag {
           anyxml multi-routing-engine-results;
         }
       }
     }
   }
   rpc clear-all-firewall-conters {
     description "Clear all firewall counters";
     junos:command "clear firewall all";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-firewall-policer-counter-statistics {
     description "Clear policer counter statistics";
     junos:command "clear firewall policer counter";
     input {
       uses command-forwarding;
       choice daemon-select {
         case logical-system {
         }
       }
       leaf counter-id {
         description "Counter Index";
         type union {
           type string {
             pattern "<.*>|$.*";
           }
           type uint32 {
             range "0 .. 2";
           }
         }
         mandatory true;
       }
     }
     output {
       choice output_c {
         case output-tag {
           leaf output {
             type string;
           }
         }
         case multichassis-tag {
           anyxml multi-routing-engine-results;
         }
       }
     }
   }
   rpc clear-all-firewall-policer-counter-statistics {
     description "Clear all policer counter statistics";
     junos:command "clear firewall policer counter all";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-firewall-log {
     description "Clear all firewall log";
     junos:command "clear firewall log";
     input {
       uses command-forwarding;
       choice daemon-select {
         case logical-system {
         }
       }
     }
     output {
       choice output_c {
         case output-tag {
           leaf output {
             type string;
           }
         }
         case multichassis-tag {
           anyxml multi-routing-engine-results;
         }
       }
     }
   }
   rpc clear-sflow-collector-statistics {
     description "Clear sFlow collector statistics";
     junos:command "clear sflow collector statistics";
     output {
       choice output_c {
         case output-tag {
           leaf output {
             type string;
           }
         }
         case multichassis-tag {
           anyxml multi-routing-engine-results;
         }
       }
     }
   }
   rpc clear-protection-group-information {
     description "Clear protection group information";
     junos:command "clear protection-group";
     output {
       choice output_c {
         case output-tag {
           leaf output {
             type string;
           }
         }
         case multichassis-tag {
           anyxml multi-routing-engine-results;
         }
       }
     }
   }
   rpc clear-ethernet-ring-information {
     description "Clear ethernet ring information";
     junos:command "clear protection-group ethernet-ring";
     output {
       choice output_c {
         case output-tag {
           leaf output {
             type string;
           }
         }
         case multichassis-tag {
           anyxml multi-routing-engine-results;
         }
       }
     }
   }
   rpc clear-ethernet-ring-statistics {
     description "Clear ethernet ring statistics";
     junos:command "clear protection-group ethernet-ring statistics";
     input {
       leaf group-name {
         description "Name of protection group";
         type string;
       }
     }
     output {
       choice output_c {
         case output-tag {
           leaf output {
             type string;
           }
         }
         case multichassis-tag {
           anyxml multi-routing-engine-results;
         }
       }
     }
   }
   rpc clear-mvrp-interface-statistics {
     description "Clear MVRP interface statistics";
     junos:command "clear mvrp statistics";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf routing-instance {
         description "Name of routing instance";
         type string {
           junos:posix-pattern "!^((__.*__)|(all)|(.*[ ].*)|(\"\")|(.{129,}))$";
           junos:pattern-message "Must be a non-reserved string of 128 characters or less with no spaces.";
         }
       }
       leaf interface {
         description "Name of interface";
         type string;
       }
     }
     output {
       choice output_c {
         case output-tag {
           leaf output {
             type string;
           }
         }
         case multichassis-tag {
           anyxml multi-routing-engine-results;
         }
       }
     }
   }
   rpc clear-stp-interface-statistics {
     description "Clear STP interface statistics";
     junos:command "clear spanning-tree statistics interface";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf interface-name {
         description "Name of interface";
         junos:cli-feature "nokeyword";
         type union {
           type jt:interface-device;
           type string {
             pattern "<.*>|$.*";
           }
         }
       }
       leaf routing-instance {
         description "Name of routing instance";
         type string {
           junos:posix-pattern "!^((__.*__)|(all)|(.*[ ].*)|(\"\")|(.{129,}))$";
           junos:pattern-message "Must be a non-reserved string of 128 characters or less with no spaces.";
         }
       }
     }
     output {
       container stp-interface-statistics {
         uses stp-interface-statistics-block;
       }
     }
   }
   rpc clear-stp-routing-instance-statistics {
     description "Clear STP routing instance statistics";
     junos:command "clear spanning-tree statistics routing-instance";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf routing-instance-name {
         description "Name of routing instance";
         junos:cli-feature "nokeyword";
         type string {
           junos:posix-pattern "!^((__.*__)|(all)|(.*[ ].*)|(\"\")|(.{129,}))$";
           junos:pattern-message "Must be a non-reserved string of 128 characters or less with no spaces.";
         }
       }
     }
   }
   rpc clear-stp-bridge-statistics {
     description "Statistics related to bridge";
     junos:command "clear spanning-tree statistics bridge";
     output {
       choice output_c {
         case output-tag {
           leaf output {
             type string;
           }
         }
         case multichassis-tag {
           anyxml multi-routing-engine-results;
         }
       }
     }
   }
   rpc clear-stp-topology-change-counter {
     description "Clear STP topology change counter";
     junos:command "clear spanning-tree topology-change-counter";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf vlan-id {
         description "VLAN ID";
         type union {
           type string {
             pattern "<.*>|$.*";
           }
           type int32 {
             range "1 .. 4094";
           }
         }
       }
       leaf routing-instance {
         description "Name of routing instance";
         type string {
           junos:posix-pattern "!^((__.*__)|(all)|(.*[ ].*)|(\"\")|(.{129,}))$";
           junos:pattern-message "Must be a non-reserved string of 128 characters or less with no spaces.";
         }
       }
     }
   }
   rpc clear-interface-stp-protocol-migration {
     description "Clear Protocol Migration on an interface";
     junos:command "clear spanning-tree protocol-migration interface";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf interface-name {
         description "Name of interface";
         junos:cli-feature "nokeyword";
         type union {
           type jt:interface-device;
           type string {
             pattern "<.*>|$.*";
           }
         }
       }
       leaf routing-instance {
         description "Name of routing instance";
         type string {
           junos:posix-pattern "!^((__.*__)|(all)|(.*[ ].*)|(\"\")|(.{129,}))$";
           junos:pattern-message "Must be a non-reserved string of 128 characters or less with no spaces.";
         }
       }
     }
   }
   rpc clear-stp-buffer {
     description "Internal buffer for STP";
     junos:command "clear spanning-tree stp-buffer";
     output {
       choice output_c {
         case output-tag {
           leaf output {
             type string;
           }
         }
         case multichassis-tag {
           anyxml multi-routing-engine-results;
         }
       }
     }
   }
   rpc clear-loop-detect-statistics-information {
     description "Clear loop detect interface statistics";
     junos:command "clear loop-detect statistics interface";
     input {
       leaf interface-name {
         junos:cli-feature "nokeyword";
         type string;
         mandatory true;
       }
     }
   }
   rpc clear-loop-detect-enhanced-interface-state {
     description "Clear loop detect enhanced interface";
     junos:command "clear loop-detect enhanced interface";
     input {
       leaf interface-name {
         description "Name of interface";
         junos:cli-feature "nokeyword";
         type union {
           type jt:interface-unit;
           type string {
             pattern "<.*>|$.*";
           }
         }
       }
     }
     output {
       leaf ld-clear-loop-detect-enhanced-interface-state {
         type string;
       }
     }
   }
   rpc clear-bpdu-error {
     description "Clear BPDU error on an interface (BPDU Protect)";
     junos:command "clear error bpdu interface";
     input {
       leaf interface-name {
         junos:cli-feature "nokeyword";
         type string;
         mandatory true;
       }
     }
   }
   rpc clear-loop-detect-error {
     description "Clear Loop Detect error on an interface";
     junos:command "clear error loop-detect interface";
     input {
       leaf interface-name {
         junos:cli-feature "nokeyword";
         type string;
         mandatory true;
       }
     }
   }
   rpc clear-mac-rewrite-error {
     description "Clear mac-rewrite error on an interface";
     junos:command "clear error mac-rewrite interface";
     input {
       leaf interface-name {
         description "Name of interface";
         junos:cli-feature "nokeyword";
         type union {
           type jt:interface-device;
           type string {
             pattern "<.*>|$.*";
           }
         }
       }
     }
   }
   rpc clear-virtual-chassis-port-statistics {
     description "Clear virtual chassis port statistics";
     junos:command "clear virtual-chassis vc-port statistics";
     input {
       uses command-forwarding;
       leaf interface-name {
         description "Name of virtual chassis port";
         junos:cli-feature "nokeyword";
         type string;
       }
     }
   }
   rpc clear-virtual-chassis-statistics {
     description "Clear virtual chassis statistics";
     junos:command "clear virtual-chassis protocol statistics";
     input {
       uses command-forwarding;
     }
   }
   rpc clear-fip-snooping-vlan {
     description "Clear FIP snooping database for this VLAN";
     junos:command "clear fip snooping vlan";
     input {
       leaf vlan {
         description "Name of VLAN";
         junos:cli-feature "nokeyword";
         type string;
         mandatory true;
       }
     }
     output {
       choice output_c {
         case output-tag {
           leaf output {
             type string;
           }
         }
         case multichassis-tag {
           anyxml multi-routing-engine-results;
         }
       }
     }
   }
   rpc clear-fip-snooping-enode {
     description "Clear all FIP snooping session for this Enode";
     junos:command "clear fip snooping enode";
     input {
       leaf mac {
         description "Enode MAC address";
         junos:cli-feature "nokeyword";
         type jt:mac-addr;
         mandatory true;
       }
       leaf vlan {
         description "Name of VLAN";
         type string;
       }
     }
     output {
       choice output_c {
         case output-tag {
           leaf output {
             type string;
           }
         }
         case multichassis-tag {
           anyxml multi-routing-engine-results;
         }
       }
     }
   }
   rpc clear-fip-snooping-statistics {
     description "Clear FIP snooping statistics";
     junos:command "clear fip snooping statistics";
     input {
       leaf vlan {
         description "Name of VLAN";
         type string;
       }
     }
     output {
       choice output_c {
         case output-tag {
           leaf output {
             type string;
           }
         }
         case multichassis-tag {
           anyxml multi-routing-engine-results;
         }
       }
     }
   }
   rpc clear-fip-snooping-vlandiscovery-statistics {
     description "Clear FIP vlan discovery statistics";
     junos:command "clear fip vlan-discovery statistics";
     output {
       choice output_c {
         case output-tag {
           leaf output {
             type string;
           }
         }
         case multichassis-tag {
           anyxml multi-routing-engine-results;
         }
       }
     }
   }
   grouping command-forwarding {
     leaf no-forwarding {
       description "No forwarding";
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member which is master";
           type union {
             type string {
               pattern "<.*>|$.*";
             }
             type uint32;
           }
         }
       }
     }
   }
   grouping clear-system-login-lockout-block {
     leaf no-login-lockout {
       type empty;
       description "No users locked out from logins";
     }
     leaf no-login-lockout-user {
       type empty;
       description "User not locked out from logins";
     }
   }
   grouping clear-reboot-status-block {
     leaf reboot-information-results {
       type string;
       description "Reboot status";
     }
     leaf clear-reboot-status-results {
       type string;
       description "Status of clear reboot request";
     }
   }
   grouping bbe-smgd-generic-command-block {
     list bbe-smgd-generic-string-list {
       leaf bbe-smgd-generic-string {
         type string;
       }
     }
   }
   grouping clear-security-alarm-results-block {
     leaf security-alarms-disabled {
       type empty;
       description "Security alarm subsystem disabled";
     }
     leaf no-security-alarms-active {
       type empty;
       description "No security alarms active";
     }
     leaf no-security-alarms-cleared {
       type empty;
       description "No security alarms cleared for this filter";
     }
     leaf clear-security-alarm-result {
       type string;
       description "Results of a clear security alarms command";
     }
   }
   grouping mka-statistics-block {
     container mka-interface-statistics {
       leaf interface-name {
         type string;
       }
       leaf received-packets {
         type uint32;
         description "Number of MKA packets received";
       }
       leaf sent-packets {
         type uint32;
         description "Number of MKA packets sent";
       }
       leaf version-error {
         type uint32;
         description "Number of MKA packets with version mismatch";
       }
       leaf cak-error {
         type uint32;
         description "Number of MKA packets with CAK invalid or mismatch";
       }
       leaf integrity-check-value-mismatch {
         type uint32;
         description "Number of MKA packets with integrity check value mismatch";
       }
       leaf duplicate-message-identifier {
         type uint32;
         description "Number of MKA packets with duplicate message identifier";
       }
       leaf duplicate-message-number {
         type uint32;
         description "Number of MKA packets with duplicate message number";
       }
       leaf duplicate-address {
         type uint32;
         description "Number of MKA packets with duplicate address";
       }
       leaf invalid-destination {
         type uint32;
         description "Number of MKA packets with invalid destination";
       }
       leaf format-error {
         type uint32;
         description "Number of MKA packets with format errors";
       }
       leaf old-message-number {
         type uint32;
         description "Number of MKA packets with old or replayed message number";
       }
     }
   }
   grouping clear-request-response-client-information-block {
     container clear-request-response-client-status {
       description "Status of session termination";
       leaf-list success {
         type string;
         description "Client session successfully terminated";
       }
       leaf-list fail {
         type string;
         description "Client session termination failure";
       }
     }
   }
   grouping service-msp-flow-drain-information-block {
     list service-msp-flow-drain {
       description "Flow removed";
       leaf interface-name {
         type string;
         description "Name of the adaptive services interface";
       }
       leaf service-set-name {
         type string;
         description "Name of the service set";
       }
       leaf flows-removed {
         type uint32;
         description "Number of flows removed in the service set";
       }
     }
   }
   grouping service-msp-sess-drain-information-block {
     list service-msp-sess-drain {
       description "Session removed";
       leaf interface-name {
         type string;
         description "Name of the adaptive services interface";
       }
       leaf service-set-name {
         type string;
         description "Name of the service set";
       }
       leaf sess-marked-for-deletion {
         type uint32;
         description "Number of sessions marked for deletion in the service set";
       }
     }
   }
   grouping service-session-analysis-information-block {
     container service-session-analysis-entry {
       container session-analysis-statistics-pic-info {
         leaf interface-name {
           type string;
           description "Name of the adaptive services interface";
         }
         leaf pic-name {
           type string;
           description "Services PIC Name";
         }
       }
       list session-analysis-statistics-entry {
         description "Session Analysis Statistics";
         leaf num-total-session-active {
           type uint32;
           description "Total number of Sessions Active";
         }
         leaf num-total-tcp-session-active {
           type uint32;
           description "Total number of TCP Sessions Active";
         }
         leaf num-total-tcp-regular-session-active {
           type uint32;
           description "Total number of TCP Regular Sessions Active";
         }
         leaf num-total-tcp-tunneled-session-active {
           type uint32;
           description "Total number of Tunneled Sessions Active";
         }
         leaf num-total-tcp-gated-session-active {
           type uint32;
           description "Total number of TCP Gated Sessions Active";
         }
         leaf num-total-tcp-ipv4-session-active {
           type uint32;
           description "Total number of TCP Sessions Active";
         }
         leaf num-total-tcp-ipv6-session-active {
           type uint32;
           description "Total number of TCP Sessions Active";
         }
         leaf num-total-udp-session-active {
           type uint32;
           description "Total number of UDP Sessions Active";
         }
         leaf num-total-udp-regular-session-active {
           type uint32;
           description "Total number of UDP Regular Sessions Active";
         }
         leaf num-total-udp-gated-session-active {
           type uint32;
           description "Total number of UDP Gated Sessions Active";
         }
         leaf num-total-udp-tunneled-session-active {
           type uint32;
           description "Total number of UDP Tunneled Sessions Active";
         }
         leaf num-total-udp-ipv4-session-active {
           type uint32;
           description "Total number of UDP IPv4 Sessions Active";
         }
         leaf num-total-udp-ipv6-session-active {
           type uint32;
           description "Total number of UDP IPv6 Sessions Active";
         }
         leaf num-total-other-session-active {
           type uint32;
           description "Total number of Other Sessions Active";
         }
         leaf num-total-other-ipv4-session-active {
           type uint32;
           description "Total number of Other IPv4 Sessions Active";
         }
         leaf num-total-other-ipv6-session-active {
           type uint32;
           description "Total number of Other IPv6 Sessions Active";
         }
         leaf num-created-session-per-sec {
           type uint32;
           description "Number of Created Sessions per Second";
         }
         leaf num-deleted-session-per-sec {
           type uint32;
           description "Number of Deleted sessions per Second";
         }
         leaf peak-total-session-active {
           type uint32;
           description "Peak Total Sessions Active";
         }
         leaf peak-total-tcp-session-active {
           type uint32;
           description "Peak Total TCP Sessions Active";
         }
         leaf peak-total-udp-session-active {
           type uint32;
           description "Peak Total UDP Sessions Active";
         }
         leaf peak-total-other-session-active {
           type uint32;
           description "Peak Total Other Sessions Active";
         }
         leaf peak-created-session-per-second {
           type uint32;
           description "Peak Created Sessions per Second";
         }
         leaf peak-deleted-session-per-second {
           type uint32;
           description "Peak Deleted Sessions per Second";
         }
         leaf session-pkts-received {
           type uint64;
           description "Packets received";
         }
         leaf session-pkts-transmitted {
           type uint64;
           description "Packets transmitted";
         }
         leaf session-slow-path-forward {
           type uint64;
           description "Slow Path Forward";
         }
         leaf session-slow-path-discard {
           type uint64;
           description "Slow Path Discard";
         }
       }
       container sess-analysis-num-sess-sec-samples-entry {
         leaf num-sess-sec-samples {
           type uint32;
         }
       }
       list sess-analysis-num-sess-sec-entry {
         description "Session Rate Statistics";
         leaf sess-operation {
           type string;
         }
         leaf num-sess-sec-400000-plus {
           type uint64;
           description "Session setup rate is above 400k";
         }
         leaf num-sess-sec-350000-plus {
           type uint64;
           description "Session setup rate is above 350k";
         }
         leaf num-sess-sec-300000-plus {
           type uint64;
           description "Session setup rate is above 300k";
         }
         leaf num-sess-sec-250000-plus {
           type uint64;
           description "Session setup rate is above 250k";
         }
         leaf num-sess-sec-200000-plus {
           type uint64;
           description "Session setup rate is above 200k";
         }
         leaf num-sess-sec-150000-plus {
           type uint64;
           description "Session setup rate is above 150k butless than or equal to 200k";
         }
         leaf num-sess-sec-50000-plus {
           type uint64;
           description "Session setup rate is above 50k butless than or equal to 150k";
         }
         leaf num-sess-sec-40000-50000 {
           type uint64;
           description "Session setup rate is above 40k butless than or equal to 50k";
         }
         leaf num-sess-sec-30000-40000 {
           type uint64;
           description "Session setup rate is above 30k butless than or equal to 40k";
         }
         leaf num-sess-sec-20000-30000 {
           type uint64;
           description "Session setup rate is above 20k butless than or equal to 30k";
         }
         leaf num-sess-sec-10000-20000 {
           type uint64;
           description "Session setup rate is above 10k butless than or equal to 20k";
         }
         leaf num-sess-sec-1000-10000 {
           type uint64;
           description "Session setup rate is above 1k butless than or equal to 10k";
         }
         leaf num-sess-sec-1000-minus {
           type uint64;
           description "Session setup rate is greater than 0 butless than or equal to 1k";
         }
         leaf num-sess-sec-0 {
           type uint64;
           description "Session setup rate is equal to 0";
         }
       }
       list sess-analysis-protocol-lifetime-entry {
         description "Session Analysis Protocol Lifetime Statistics";
         leaf tcp-sess-lifetime-240s-plus {
           type uint64;
           description "Number of TCP sessions that lastedfor more than 240 sec";
         }
         leaf udp-sess-lifetime-240s-plus {
           type uint64;
           description "Number of UDP sessions that lastedfor more than 240 sec";
         }
         leaf http-sess-lifetime-240s-plus {
           type uint64;
           description "Number of HTTP sessions that lastedfor more than 240 sec";
         }
         leaf tcp-sess-lifetime-120s-240s {
           type uint64;
           description "Number of TCP sessions that lastedfor more than 120 sec but less thanor equal to 240 sec";
         }
         leaf udp-sess-lifetime-120s-240s {
           type uint64;
           description "Number of UDP sessions that lastedfor more than 120 sec but less thanor equal to 240 sec";
         }
         leaf http-sess-lifetime-120s-240s {
           type uint64;
           description "Number of HTTP sessions that lastedfor more than 120 sec but less thanor equal to 240 sec";
         }
         leaf tcp-sess-lifetime-60s-120s {
           type uint64;
           description "Number of TCP sessions that lastedfor more than 60 sec but less thanor equal to 120 sec";
         }
         leaf udp-sess-lifetime-60s-120s {
           type uint64;
           description "Number of UDP sessions that lastedfor more than 60 sec but less thanor equal to 120 sec";
         }
         leaf http-sess-lifetime-60s-120s {
           type uint64;
           description "Number of HTTP sessions that lastedfor more than 60 sec but less thanor equal to 120 sec";
         }
         leaf tcp-sess-lifetime-30s-60s {
           type uint64;
           description "Number of TCP sessions that lastedfor more than 30 sec but less thanor equal to 60 sec";
         }
         leaf udp-sess-lifetime-30s-60s {
           type uint64;
           description "Number of UDP sessions that lastedfor more than 30 sec but less thanor equal to 60 sec";
         }
         leaf http-sess-lifetime-30s-60s {
           type uint64;
           description "Number of HTTP sessions that lastedfor more than 30 sec but less thanor equal to 60 sec";
         }
         leaf tcp-sess-lifetime-15s-30s {
           type uint64;
           description "Number of TCP sessions that lastedfor more than 15 sec but less thanor equal to 30 sec";
         }
         leaf udp-sess-lifetime-15s-30s {
           type uint64;
           description "Number of UDP sessions that lastedfor more than 15 sec but less thanor equal to 30 sec";
         }
         leaf http-sess-lifetime-15s-30s {
           type uint64;
           description "Number of HTTP sessions that lastedfor more than 15 sec but less thanor equal to 30 sec";
         }
         leaf tcp-sess-lifetime-5s-15s {
           type uint64;
           description "Number of TCP sessions that lastedfor more than 5 sec but less thanor equal to 15 sec";
         }
         leaf udp-sess-lifetime-5s-15s {
           type uint64;
           description "Number of UDP sessions that lastedfor more than 5 sec but less thanor equal to 15 sec";
         }
         leaf http-sess-lifetime-5s-15s {
           type uint64;
           description "Number of HTTP sessions that lastedfor more than 5 sec but less thanor equal to 15 sec";
         }
         leaf tcp-sess-lifetime-1s-5s {
           type uint64;
           description "Number of TCP sessions that lastedfor more than 1 sec but less thanor equal to 5 sec";
         }
         leaf udp-sess-lifetime-1s-5s {
           type uint64;
           description "Number of UDP sessions that lastedfor more than 1 sec but less thanor equal to 5 sec";
         }
         leaf http-sess-lifetime-1s-5s {
           type uint64;
           description "Number of HTTP sessions that lastedfor more than 1 sec but less thanor equal to 5 sec";
         }
         leaf tcp-sess-lifetime-1s-minus {
           type uint64;
           description "Number of TCP sessions that lastedfor less than 1 sec";
         }
         leaf udp-sess-lifetime-1s-minus {
           type uint64;
           description "Number of UDP sessions that lastedfor less than 1 sec";
         }
         leaf http-sess-lifetime-1s-minus {
           type uint64;
           description "Number of HTTP sessions that lastedfor less than 1 sec";
         }
       }
     }
   }
   grouping msp-service-subs-analysis-information-block {
     container subs-analysis-statistics-pic-info {
       leaf pic-name {
         type string;
         description "Services PIC Name";
       }
     }
     list subs-analysis-statistics-entry {
       description "Subscriber Analysis Statistics";
       leaf num-total-subs-active {
         type uint32;
         description "Number of Total Subscribers Active";
       }
       leaf num-created-subs-per-sec {
         type uint32;
         description "Number of Created Subscribers per Second";
       }
       leaf num-deleted-subs-per-sec {
         type uint32;
         description "Number of Deleted Subscribers per Second";
       }
       leaf peak-total-subs-active {
         type uint32;
         description "Peak Total Subscribers Active";
       }
       leaf peak-created-subs-per-second {
         type uint32;
         description "Peak Created Subscribers per Second";
       }
       leaf peak-deleted-subs-per-second {
         type uint32;
         description "Peak Deleted Subscribers per Second";
       }
     }
     container subs-analysis-num-subs-sec-samples-entry {
       leaf num-subs-sec-samples {
         type uint32;
       }
     }
     list msp-subs-analysis-num-subs-sec-entry {
       description "Subscriber Rate Statistics";
       leaf msp-subs-operation {
         type string;
       }
       leaf msp-num-subs-sec-400000-plus {
         type uint32;
         description "Subscriber setup rate is 400k or above";
       }
       leaf msp-num-subs-sec-350000-plus {
         type uint32;
         description "Subscriber setup rate is 350k or above";
       }
       leaf msp-num-subs-sec-300000-plus {
         type uint32;
         description "Subscriber setup rate is 300k or above";
       }
       leaf msp-num-subs-sec-250000-plus {
         type uint32;
         description "Subscriber setup rate is 250k or above";
       }
       leaf msp-num-subs-sec-200000-plus {
         type uint32;
         description "Subscriber setup rate is 200k or above";
       }
       leaf msp-num-subs-sec-150000-plus {
         type uint32;
         description "Subscriber setup rate is 150k or above";
       }
       leaf msp-num-subs-sec-100000-plus {
         type uint32;
         description "Subscriber setup rate is 100k or above";
       }
       leaf msp-num-subs-sec-50000-plus {
         type uint32;
         description "Subscriber setup rate is 50k or above";
       }
       leaf msp-num-subs-sec-40000-plus {
         type uint32;
         description "Subscriber setup rate is > 40k or above";
       }
       leaf msp-num-subs-sec-30000-plus {
         type uint32;
         description "Subscriber setup rate is > 30k or above";
       }
       leaf msp-num-subs-sec-20000-plus {
         type uint32;
         description "Subscriber setup rate is > 20k or above";
       }
       leaf msp-num-subs-sec-10000-plus {
         type uint32;
         description "Subscriber setup rate is > 10k or above";
       }
       leaf msp-num-subs-sec-1000-plus {
         type uint32;
         description "Subscriber setup rate is > 1k or above";
       }
       leaf msp-num-subs-sec-1000-minus {
         type uint32;
         description "Subscriber setup rate is > 0 but <= 1k";
       }
       leaf msp-num-subs-sec-0 {
         type uint32;
         description "Subscriber setup rate is 0";
       }
     }
   }
   grouping service-pcp-epoch-information-block {
     leaf epoch-value {
       type uint32;
     }
   }
   grouping clear-arp-table-results-block {
     container clear-arp-table-result {
       description "Results of a clear ARP command";
       leaf ip-address {
         type jt:ipaddr;
         description "IP address of the ARP entry";
       }
       leaf clear-success {
         type empty;
         description "Clear ARP was successful";
       }
     }
   }
   grouping interface-transport-information-block {
     list interface-transport-state {
       leaf interface-transport-admin-state {
         type string;
         description "GR1093 Administrative state";
       }
       leaf interface-transport-oper-state {
         type string;
         description "GR1093 Operational state";
       }
     }
   }
   grouping vrrp-message-block {
     leaf message {
       type string;
       description "Message to be displayed in case of error conditions.";
     }
   }
   grouping ipv6-modify-nd-block {
     list ipv6-modify-nd-entry {
       leaf ipv6-nd-neighbor-address {
         type jt:ipv6addr;
         description "Address of the neighbor";
       }
       leaf ipv6-nd-neighbor-l2-address {
         type string;
         description "Layer 2 address of the neighbor";
       }
       leaf ipv6-nd-change {
         type string;
       }
     }
   }
   grouping ancp-neighbor-information-block {
     list ancp-neighbor {
       leaf neighbor-stale-flag {
         type string;
         description "ANCP neighbor stale entry flag";
       }
       leaf protocol-version {
         type string;
         description "Neighbor protocol version";
       }
       leaf ip-address {
         type jt:ipaddr;
         description "Neighbor IP address";
       }
       leaf partition-identifier {
         type int32;
         description "Neighbor partition identifier";
       }
       leaf state {
         type string;
         description "Neighbor adjacency state";
       }
       leaf up-time {
         type string;
         description "Up time";
       }
       leaf neighbor-subscriber-count {
         type int32;
         description "Neighbor subscriber count";
       }
       leaf capabilities {
         type string;
         description "Neighbor capabilities";
       }
       leaf received-rcode-bad-request-msg-count {
         type uint64;
         description "Result code: bad request message count";
       }
       leaf sent-rcode-bad-request-msg-count {
         type uint64;
         description "Result code: bad request message count";
       }
       leaf received-rcode-port-down-count {
         type uint64;
         description "Result code: port(s) down count";
       }
       leaf sent-rcode-port-down-count {
         type uint64;
         description "Result code: port(s) down count";
       }
       leaf received-rcode-out-of-resources-count {
         type uint64;
         description "Result code: out of resources count";
       }
       leaf sent-rcode-out-of-resources-count {
         type uint64;
         description "Result code: out of resources count";
       }
       leaf received-rcode-request-msg-not-implemented-count {
         type uint64;
         description "Result code: message not implemented count";
       }
       leaf sent-rcode-request-msg-not-implemented-count {
         type uint64;
         description "Result code: message not implemented count";
       }
       leaf received-rcode-bad-msg-count {
         type uint64;
         description "Result code: bad message count";
       }
       leaf sent-rcode-bad-msg-count {
         type uint64;
         description "Result code: bad message count";
       }
       leaf received-rcode-tlv-missing-count {
         type uint64;
         description "Result code: TLV missing count";
       }
       leaf sent-rcode-tlv-missing-count {
         type uint64;
         description "Result code: TLV missing count";
       }
       leaf received-rcode-bad-tlv-contents-count {
         type uint64;
         description "Result code: invalid TLV contents count";
       }
       leaf sent-rcode-bad-tlv-contents-count {
         type uint64;
         description "Result code: invalid TLV contents count";
       }
       leaf received-rcode-unknown-port-count {
         type uint64;
         description "Result code: unknown port count";
       }
       leaf sent-rcode-unknown-port-count {
         type uint64;
         description "Result code: unknown port count";
       }
       leaf partition-id {
         type int32;
         description "Neighbor partition ID";
       }
       leaf mac-address {
         type jt:mac-addr;
         description "Neighbor MAC address";
       }
       leaf neighbor-autoconf-interface {
         type string;
         description "Auto-configure trigger interface";
       }
       leaf tcp-port {
         type int32;
         description "TCP port used by connection";
       }
       leaf system-instance {
         type int32;
         description "Neighbor system instance";
       }
       leaf peer-instance {
         type int32;
         description "Neighbor peer instance";
       }
       leaf adjacency-time {
         type int32;
         description "Adjacency time advertised in 100ms";
       }
       leaf peer-adjacency-time {
         type int32;
         description "Neighbor adjacency timer value in 100ms";
       }
       leaf adjacency-loss-hold-time {
         type int32;
         description "Audit duration upon adjacency loss in seconds";
       }
       leaf partition-type {
         type int32;
         description "Neighbor partition type";
       }
       leaf partition-flag {
         type int32;
         description "Neighbor partition flag";
       }
       leaf partition-adjacencies {
         type int32;
         description "Adjacencies established on partition";
       }
       leaf dead-time {
         type int32;
         description "Time left to receive an adjacency message";
       }
       leaf received-syn-count {
         type uint64;
         description "Count of SYN messages received";
       }
       leaf received-synack-count {
         type uint64;
         description "Count of SYNACK messages received";
       }
       leaf received-rstack-count {
         type uint64;
         description "Count of RSTACK messages received";
       }
       leaf received-ack-count {
         type uint64;
         description "Count of ACK messages received";
       }
       leaf received-port-up-count {
         type uint64;
         description "Count of port up messages received";
       }
       leaf received-port-down-count {
         type uint64;
         description "Count of port down messages received";
       }
       leaf received-generic-response-count {
         type uint64;
         description "Count of generic response messages received";
       }
       leaf received-adjacency-update-count {
         type uint64;
         description "Count of adjacency update messages received";
       }
       leaf received-oam-count {
         type uint64;
         description "Count of OAM messages received";
       }
       leaf received-other-count {
         type uint64;
         description "Count of other messages received";
       }
       leaf sent-syn-count {
         type uint64;
         description "Count of SYN messages sent";
       }
       leaf sent-synack-count {
         type uint64;
         description "Count of SYNACK messages sent";
       }
       leaf sent-rstack-count {
         type uint64;
         description "Count of RSTACK messages sent";
       }
       leaf sent-ack-count {
         type uint64;
         description "Count of ACK messages sent";
       }
       leaf sent-generic-response-count {
         type uint64;
         description "Count of generic response messages sent";
       }
       leaf sent-oam-count {
         type uint64;
         description "Count of OAM messages sent";
       }
       leaf max-discovery-limit-exceed-count {
         type uint64;
         description "Count of discovery table entries not created due to limit";
       }
     }
   }
   grouping ancp-subscriber-information-block {
     leaf subscriber-stale-flag {
       type string;
       description "ANCP neighbor stale entry flag";
     }
     leaf access-loop-identifier {
       type string;
       description "Subscriber circuit identifier";
     }
     leaf dsl-line-state {
       type string;
       description "DSL line state";
     }
     leaf access-tech-type {
       type string;
       description "Access Technology Type";
     }
     leaf access-type {
       type string;
       description "Access type";
     }
     leaf interface {
       type string;
       description "Subscriber's interface name";
     }
     leaf actual-net-data-downstream {
       type uint32;
       description "Actual net data downstream";
     }
     leaf neighbor-ip-address {
       type jt:ipaddr;
       description "IP address of the ANCP neighbor";
     }
     list ancp-subscriber {
       leaf subscriber-stale-flag {
         type string;
         description "ANCP neighbor stale entry flag";
       }
       leaf access-loop-identifier {
         type string;
         description "Subscriber circuit identifier";
       }
       leaf dsl-line-state {
         type string;
         description "DSL line state";
       }
       leaf access-tech-type {
         type string;
         description "Access Technology Type";
       }
       leaf access-type {
         type string;
         description "Access type";
       }
       leaf interface {
         type string;
         description "Subscriber's interface name";
       }
       leaf actual-net-data-downstream {
         type uint32;
         description "Actual net data downstream";
       }
       leaf neighbor-ip-address {
         type jt:ipaddr;
         description "IP address of the ANCP neighbor";
       }
     }
     list ancp-neighbor {
       leaf received-rcode-bad-request-msg-count {
         type uint64;
         description "Result code: bad request message count";
       }
       leaf sent-rcode-bad-request-msg-count {
         type uint64;
         description "Result code: bad request message count";
       }
       leaf received-rcode-port-down-count {
         type uint64;
         description "Result code: port(s) down count";
       }
       leaf sent-rcode-port-down-count {
         type uint64;
         description "Result code: port(s) down count";
       }
       leaf received-rcode-out-of-resources-count {
         type uint64;
         description "Result code: out of resources count";
       }
       leaf sent-rcode-out-of-resources-count {
         type uint64;
         description "Result code: out of resources count";
       }
       leaf received-rcode-request-msg-not-implemented-count {
         type uint64;
         description "Result code: message not implemented count";
       }
       leaf sent-rcode-request-msg-not-implemented-count {
         type uint64;
         description "Result code: message not implemented count";
       }
       leaf received-rcode-bad-msg-count {
         type uint64;
         description "Result code: bad message count";
       }
       leaf sent-rcode-bad-msg-count {
         type uint64;
         description "Result code: bad message count";
       }
       leaf received-rcode-tlv-missing-count {
         type uint64;
         description "Result code: TLV missing count";
       }
       leaf sent-rcode-tlv-missing-count {
         type uint64;
         description "Result code: TLV missing count";
       }
       leaf received-rcode-bad-tlv-contents-count {
         type uint64;
         description "Result code: invalid TLV contents count";
       }
       leaf sent-rcode-bad-tlv-contents-count {
         type uint64;
         description "Result code: invalid TLV contents count";
       }
       leaf received-rcode-unknown-port-count {
         type uint64;
         description "Result code: unknown port count";
       }
       leaf sent-rcode-unknown-port-count {
         type uint64;
         description "Result code: unknown port count";
       }
       leaf partition-id {
         type int32;
         description "Neighbor partition ID";
       }
     }
     leaf access-loop-remote-identifier {
       type string;
       description "Subscriber remote identifier";
     }
     leaf access-aggregate-circuit-ascii-identifier {
       type string;
       description "Aggregate circuit ASCII identifier";
     }
     leaf access-aggregate-circuit-binary-identifier {
       type string;
       description "Aggregate circuit binary identifier";
     }
     leaf access-loop-encapsulation-data-link {
       type string;
       description "Access loop encapsulation data link type";
     }
     leaf access-loop-encapsulation-encapsulation1 {
       type string;
       description "Access loop encapsulation encapsulation1";
     }
     leaf access-loop-encapsulation-encapsulation2 {
       type string;
       description "Access loop encapsulation encapsulation2";
     }
     leaf interface-type {
       type string;
       description "Subscriber's interface type";
     }
     leaf actual-net-data-upstream {
       type uint32;
       description "Actual net data upstream";
     }
     leaf minimum-net-data-upstream {
       type uint32;
       description "Minimum net data upstream";
     }
     leaf minimum-net-data-downstream {
       type uint32;
       description "Minimum net data downstream";
     }
     leaf maximum-net-data-upstream {
       type uint32;
       description "Maximum net data upstream";
     }
     leaf maximum-net-data-downstream {
       type uint32;
       description "Maximum net data downstream";
     }
     leaf attainable-net-data-upstream {
       type uint32;
       description "Attainable net data upstream";
     }
     leaf attainable-net-data-downstream {
       type uint32;
       description "Attainable net data downstream";
     }
     leaf minimum-low-power-data-upstream {
       type uint32;
       description "Minimum net low power upstream";
     }
     leaf minimum-low-power-data-downstream {
       type uint32;
       description "Minimum net low power downstream";
     }
     leaf maximum-interleave-delay-upstream {
       type uint32;
       description "Maximum interleaving delay upstream";
     }
     leaf maximum-interleave-delay-downstream {
       type uint32;
       description "Maximum interleaving delay downstream";
     }
     leaf actual-interleave-delay-upstream {
       type uint32;
       description "Actual interleaving delay upstream";
     }
     leaf actual-interleave-delay-downstream {
       type uint32;
       description "Actual interleaving delay downstream";
     }
     leaf expected-throughput-upstream {
       type uint32;
       description "Expected throughput at L2 upstream";
     }
     leaf expected-throughput-downstream {
       type uint32;
       description "Expected throughput at L2 downstream";
     }
     leaf attainable-expected-throughput-upstream {
       type uint32;
       description "Attainable expected throughput at L2 upstream";
     }
     leaf attainable-expected-throughput-downstream {
       type uint32;
       description "Attainable expected throughput at L2 downstream";
     }
     leaf gamma-data-upstream {
       type uint32;
       description "Gamma data rate upstream";
     }
     leaf gamma-data-downstream {
       type uint32;
       description "Gamma data rate downstream";
     }
     leaf attainable-gamma-data-upstream {
       type uint32;
       description "Attainable gamma data rate upstream";
     }
     leaf attainable-gamma-data-downstream {
       type uint32;
       description "Attainable gamma data rate downstream";
     }
     leaf ont-onu-average-data-downstream {
       type uint32;
       description "ONT/ONU average data rate downsteam";
     }
     leaf ont-onu-peak-data-downstream {
       type uint32;
       description "ONT/ONU peak data rate downsteam";
     }
     leaf ont-onu-max-data-upstream {
       type uint32;
       description "ONT/ONU maximum data rate upsteam";
     }
     leaf ont-onu-assured-data-upstream {
       type uint32;
       description "ONT/ONU assured data rate upsteam";
     }
     leaf pon-tree-max-data-upstream {
       type uint32;
       description "PON tree maximum data rate upsteam";
     }
     leaf pon-tree-max-data-downstream {
       type uint32;
       description "PON tree maximum data rate downsteam";
     }
     leaf downstream-rate {
       type uint32;
       description "Downstream rate";
     }
   }
   grouping bfd-session-information-block {
     leaf sessions-shop {
       type int32;
       description "Total number of single-hop BFD sessions";
     }
     leaf sessions-shop-echolite {
       type int32;
       description "Total number of single-hop-echolite BFD sessions";
     }
     leaf sessions-shop-seamless {
       type int32;
       description "Total number of single-hop-seamless BFD sessions";
     }
     leaf sessions-mhop {
       type int32;
       description "Total number of multi-hop BFD sessions";
     }
     leaf sessions-mhop-seamless {
       type int32;
       description "Total number of multi-hop-seamless BFD sessions";
     }
     leaf sessions-micro {
       type int32;
       description "Total number of micro BFD sessions";
     }
     leaf sessions-mpls {
       type int32;
       description "Total number of mpls BFD sessions";
     }
     leaf sessions-vccv {
       type int32;
       description "Total number of vccv BFD sessions";
     }
     leaf sessions-admindown {
       type int32;
       description "Total number of Admin Down BFD sessions";
     }
     leaf sessions-down {
       type int32;
       description "Total number of Down state BFD sessions";
     }
     leaf sessions-init {
       type int32;
       description "Total number of Init state BFD sessions";
     }
     leaf sessions-up {
       type int32;
       description "Total number of Up state BFD sessions";
     }
     leaf sessions-failing {
       type int32;
       description "Total number of Failing BFD sessions";
     }
     leaf sessions {
       type int32;
       description "Total number of active BFD sessions";
     }
     leaf clients {
       type int32;
       description "Total number of clients that are hosting BFD sessions";
     }
     leaf up-sessions {
       type string;
       description "Total number of BFD sessions which are UP";
     }
     leaf down-sessions {
       type string;
       description "Total number of BFD sessions which are not UP";
     }
     leaf cumulative-transmission-rate {
       type string;
       description "Number of BFD control packets transmitted per second inall active sessions";
     }
     leaf cumulative-reception-rate {
       type string;
       description "Number of BFD control packets received per second inall active sessions";
     }
     leaf cumulative-up-time {
       type string;
       description "Time taken to being up bfd sesison";
     }
     list bfd-session {
       leaf session-neighbor {
         type string;
         description "IP address of the neighbor for the BFD session";
       }
       leaf session-state {
         type string;
         description "BFD session state";
       }
       leaf session-interface {
         type string;
         description "Name of the interface on which the BFD session is active";
       }
       leaf session-detection-time {
         type string;
         description "Time period within which the host must receive BFD controlpackets to continue considering the session active (seconds)";
       }
       leaf session-transmission-interval {
         type string;
         description "Frequency at which the host system sends BFD controlpackets (seconds)";
       }
       leaf session-adaptive-multiplier {
         type int32;
         description "The adjusted value of detect multiplier.";
       }
       leaf session-up-time {
         type string;
         description "Time since the current session began (hours:minutes:seconds)";
       }
       leaf previous-down-time {
         type string;
         description "Amount of time the previous session was down(hours:minutes:seconds)";
       }
       leaf session-down-time {
         type string;
         description "Time for which the current session was down(hours:minutes:seconds)";
       }
       leaf previous-up-time {
         type string;
         description "Duration of the previous session (hours:minutes:seconds)";
       }
       leaf local-diagnostic {
         type string;
         description "Information provided by the local host about BFD sessionsthat have failed (for example if the node is administrativelydown or a control timer has expired)";
       }
       leaf remote-diagnostic {
         type string;
         description "Information provided by the remote host about BFD sessionsthat have failed (for example if the node is administrativelydown or a control timer has expired)";
       }
       leaf v0-remote-state {
         type string;
         description "(BFD version 0 only.) Indicates whether the local system is receiving BFD control packets from the remote system.";
       }
       leaf remote-listen {
         type string;
         description "(BFD version 0 only.) Indicates whether the remote system isreceiving control packets transmitted by the local system.";
       }
       leaf remote-state {
         type string;
         description "(BFD version 1 only.) Indicates the remote session state";
       }
       leaf session-version {
         type int32;
         description "Version of the BFD protocol being used for the session";
       }
       leaf logical-system-id {
         type int32;
         description "Logical system on which the session is established";
       }
       leaf route-table-index {
         type int32;
         description "Routing table index for the current logical system";
       }
       leaf replicated {
         type string;
         description "Indicates whether the session is replicated between master andstandby RE";
       }
       leaf session-type {
         type string;
         description "Indicates the flavor of the BFD session";
       }
       leaf minimum-asynchronous-interval {
         type string;
         description "Minimum amount of time that the local system proposes forthe delay between transmission of asynchronous control packetsacross the BFD session (seconds)";
       }
       leaf minimum-slow-interval {
         type string;
         description "Either one second or the minimum asynchronous interval,whichever is greater";
       }
       leaf adaptive-asynchronous-transmission-interval {
         type string;
         description "Minimum asynchronous interval used when there is routeflapping";
       }
       leaf adaptive-reception-interval {
         type string;
         description "Adjusted value of minimum reception interval.";
       }
       leaf minimum-transmission-interval {
         type string;
         description "Minimum amount of time that the local system proposes forthe delay between transmission of control packets across theBFD session (seconds). It is either the minimum slow interval orthe adaptive asynchronous transmission interval";
       }
       leaf minimum-reception-interval {
         type string;
         description "Minimum amount of time that the local system waits betweenchecks for newly received control packets (seconds)";
       }
       leaf detection-multiplier {
         type int32;
         description "Desired detect time multiplier for BFD control packets.It is multiplied by the negotiated control packet receptioninterval to determine the session detection time (time todetect whether the session is alive).";
       }
       leaf neighbor-minimum-transmission-interval {
         type string;
         description "Minimum amount of time that the remote system proposes forthe delay between transmission of control packets across the BFDsession (seconds)";
       }
       leaf neighbor-minimum-reception-interval {
         type string;
         description "Minimum amount of time that the remote system waits betweenchecks for newly received control packets (seconds)";
       }
       leaf neighbor-session-multiplier {
         type int32;
         description "Neighbor's detection multiplier";
       }
       leaf issu-state {
         type string;
         description "ISSU state of the session";
       }
       leaf original-transmission-interval {
         type int32;
         description "Original pre-ISSU transmission interval";
       }
       leaf original-reception-interval {
         type int32;
         description "Original pre-ISSU reception interval";
       }
       leaf local-discriminator {
         type int32;
         description "Authentication code used by the local system to identify theBFD session";
       }
       leaf remote-discriminator {
         type uint32;
         description "Authentication code used by the remote system to identify theBFD session";
       }
       leaf echo-tx-interval {
         type string;
         description "Echo tx interval";
       }
       leaf echo-detection-interval {
         type string;
         description "Echo detection interval";
       }
       leaf threshold-transmission-interval {
         type string;
         description "The maximum duration (in seconds) for the transmissioninterval before an SNMP trap is generated";
       }
       leaf threshold-detection-time {
         type int32;
         description "The maximum duration (in seconds) for the detection timebefore an SNMP trap is generated";
       }
       leaf authentication {
         type string;
         description "Authentication status";
       }
       leaf session-keychain {
         type string;
         description "Authentication status";
       }
       leaf session-algorithm {
         type int32;
         description "Session authentication algorithm";
       }
       leaf session-authentication-loose {
         type int32;
         description "Session authentication mode";
       }
       leaf neighbor-fate {
         type string;
         description "Indicates whether the remote system is control-planeindependent";
       }
       leaf adaptation-disabled {
         type string;
         description "Indicates whether adaptation has been disabled";
       }
       leaf holddown-timer {
         type string;
         description "Status of version negotiation";
       }
       leaf l2ckt-neighbor-address {
         type string;
         description "L2circuit neighbor address";
       }
       leaf l2ckt-vc-id {
         type int32;
         description "L2circuit virtual circuit id";
       }
       leaf l2vpn-local-site-id {
         type int32;
         description "Local site id of the L2vpn";
       }
       leaf l2vpn-remote-site-id {
         type int32;
         description "Remote site id of the L2vpn";
       }
       leaf l2vpn-fec129-agi {
         type string;
         description "AGI of the L2vpn";
       }
       leaf l2vpn-fec129-saii {
         type string;
         description "SAII of the L2vpn";
       }
       leaf l2vpn-fec129-taii {
         type string;
         description "TAII of the L2vpn";
       }
       leaf tunnel-name {
         type string;
         description "Name of the BFD tunnel";
       }
       leaf tunnel-path {
         type string;
         description "Path of the BFD tunnel";
       }
       leaf tunnel-prefix {
         type string;
         description "Prefix for the Label Distribution Protocol tunnel";
       }
       leaf tunnel-prefix-length {
         type int32;
         description "Length of prefix for the Label Distribution Protocol tunnel";
       }
       leaf tunnel-type {
         type string;
         description "Type of tunnel";
       }
       leaf tunnel-destination {
         type string;
         description "Destination for the Label Distribution Protocol tunnel";
       }
       leaf multihop {
         type string;
         description "Multihop session";
       }
       leaf multihop-time-to-live {
         type int32;
         description "Time-to-live for multihop session";
       }
       leaf multihop-routing-table-index {
         type int32;
         description "Multihop session index in the routing table ";
       }
       leaf multihop-local-address {
         type string;
         description "Multihop local address";
       }
       leaf echo-mode-desired {
         type string;
         description "Indicates whether the local system proposes that echotransmissions be enabled for the BFD session";
       }
       leaf echo-mode-state {
         type string;
         description "Indicates whether echo transmissions are enabled for theBFD session";
       }
       leaf no-async {
         type string;
         description "No async enabled for this bfd session";
       }
       leaf no-absorb {
         type string;
         description "Incoming packets are not absorbed";
       }
       leaf no-refresh {
         type string;
         description "The adjacency is not refreshed";
       }
       leaf update-adjacency {
         type string;
         description "Indicates whether the adjacency needs to be updated";
       }
       leaf update-transmit {
         type string;
         description "Indicates whether a transmission needs to be updated";
       }
       leaf bfd-pdu-size {
         type uint32;
         description "Bfd pdu size incase of large pkt support";
       }
       leaf session-id {
         type uint32;
         description "Session repair ID";
       }
       leaf trace-session-id-state {
         type string;
         description "Session repair ID State";
       }
       leaf trace-session-type {
         type string;
         description "Trace session type";
       }
       leaf trace-rtbl-index {
         type int32;
         description "Route table Index";
       }
       leaf trace-ifl-index {
         type int32;
         description "Interface index";
       }
       leaf trace-src-addr {
         type string;
         description "Source address";
       }
       leaf trace-dest-addr {
         type string;
         description "Destination address";
       }
       leaf trace-tunnel-label {
         type int32;
         description "Tunnel label for PW";
       }
       leaf trace-bundle-ifd {
         type int32;
         description "Bundle ifd";
       }
       leaf trace-bundle-af {
         type int32;
         description "Bundle family";
       }
       leaf trace-session-enabled {
         type string;
         description "Session tracing status";
       }
       list bfd-client {
         leaf client-name {
           type string;
           description "Protocol for which the BFD session is active (forexample: OSPF, ISIS, Static, and so on) ";
         }
         leaf client-transmission-interval {
           type string;
           description "Base frequency that the client proposes for sending BFDcontrol packets (seconds)";
         }
         leaf client-reception-interval {
           type string;
           description "Base frequency that the client has proposed for peersto send BFD control packets (seconds)";
         }
         leaf client-echo-transmission-interval {
           type string;
           description "Base frequency that the client proposes for sending BFD Echocontrol packets (seconds)";
         }
         leaf client-multiplier {
           type int32;
           description "Multiplier that the client has requested to determine theliveness of the BFD session.";
         }
         leaf client-authentication {
           type string;
           description "Client requested authentication";
         }
         leaf client-holddown-interval {
           type string;
           description "Hold interval for which BFD does not send a session UP notification to the client (seconds)";
         }
         leaf client-state {
           type string;
           description "Tells whether client is in holddown or not";
         }
         leaf client-keychain {
           type string;
           description "Client requested keychain name";
         }
         leaf client-algorithm {
           type int32;
           description "Client requested algorithm";
         }
         leaf client-authentication-loose {
           type string;
           description "Client requested mode";
         }
       }
     }
     leaf error-value {
       type string;
       description "Error code that is returned when a 'clear' operation fails";
     }
   }
   grouping stp-interface-statistics-block {
     list stp-interface-statistics-entry {
       description "STP interface statistics";
       leaf interface-name {
         type string;
         description "Name of interface";
       }
       leaf total-bpdus-sent {
         type int32;
         description "Total number of BPDUs sent";
       }
       leaf total-bpdus-received {
         type int32;
         description "Total number of BPDUs received";
       }
       leaf next-bpdu-time {
         type int32;
         description "How long before sending next BPDU";
       }
       leaf total-tcn-bpdus-sent-received {
         type string;
         description "Total number of TCN BPDUs sent/received";
       }
       leaf total-proposal-bpdus-sent-received {
         type string;
         description "Total number of Proposal BPDUs sent/received";
       }
       leaf total-agreement-bpdus-sent-received {
         type string;
         description "Total number of Agreement BPDUs sent/received";
       }
     }
     container vstp-interface-statistics {
       description "Statistics information about one or more VLAN STP interfaces";
       leaf vlan-id {
         type int32;
         description "VLAN identifier";
       }
       list stp-interface-statistics-entry {
         description "STP interface statistics";
         leaf interface-name {
           type string;
           description "Name of interface";
         }
         leaf total-bpdus-sent {
           type int32;
           description "Total number of BPDUs sent";
         }
         leaf total-bpdus-received {
           type int32;
           description "Total number of BPDUs received";
         }
         leaf next-bpdu-time {
           type int32;
           description "How long before sending next BPDU";
         }
         leaf total-tcn-bpdus-sent-received {
           type string;
           description "Total number of TCN BPDUs sent/received";
         }
         leaf total-proposal-bpdus-sent-received {
           type string;
           description "Total number of Proposal BPDUs sent/received";
         }
         leaf total-agreement-bpdus-sent-received {
           type string;
           description "Total number of Agreement BPDUs sent/received";
         }
       }
     }
   }
 }
