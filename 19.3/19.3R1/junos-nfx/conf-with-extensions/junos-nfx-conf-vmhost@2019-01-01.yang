/*
 * Copyright (c) 2019 Juniper Networks, Inc.
 * All rights reserved.
 */
 module junos-nfx-conf-vmhost {
   namespace "http://yang.juniper.net/junos-nfx/conf/vmhost";

   prefix jc-vmhost;

   import junos-common-ddl-extensions {
     prefix junos;
   }

   import junos-common-types {
     prefix jt;
   }

   import junos-nfx-conf-root {
     prefix jc;
   }

   organization "Juniper Networks, Inc.";

   contact "yang-support@juniper.net";

   description "Junos vmhost configuration module";

   revision 2019-01-01 {
     description "Junos: 19.3R1.8";
   }

   augment /jc:configuration {
     uses vmhost-group;
   }
   augment /jc:configuration/jc:groups {
     uses vmhost-group;
   }
   grouping vmhost-group {
     container vmhost {
       description "Vmhost configuration";
       uses apply-advanced;
       leaf no-auto-recovery {
         description "Disable Guest auto recovery by the host";
         type empty;
       }
       container management-if {
         presence "enable management-if";
         description "Configuration for the host's side management interface";
         uses apply-advanced;
         leaf link-mode {
           description "Link operational mode";
           default "automatic";
           type enumeration {
             enum "automatic" {
               description "Automatically negotiate duplex";
               junos:must "(\"vmhost management-if speed automatic\")";
               junos:must-message "speed should be configured as auto";
             }
             enum "half-duplex" {
               description "Half-duplex operation";
               junos:must "((\"vmhost management-if speed 10m\" || \"vmhost management-if speed 100m\"))";
               junos:must-message "speed should be 10Mbps or 100Mbps";
             }
             enum "full-duplex" {
               description "Full-duplex operation";
               junos:must "((\"vmhost management-if speed 10m\" || (\"vmhost management-if speed 100m\" || \"vmhost management-if speed 1g\")))";
               junos:must-message "speed should be 10Mbps, 100Mbps or 1Gbps";
             }
           }
         }
         leaf speed {
           description "Link speed";
           default "automatic";
           type enumeration {
             enum "automatic" {
               description "Automatically negotiate speed";
               junos:must "(\"vmhost management-if link-mode automatic\")";
               junos:must-message "link-mode should be configured as auto";
             }
             enum "10m" {
               description "10Mbps operation";
               junos:must "((\"vmhost management-if link-mode half-duplex\" || \"vmhost management-if link-mode full-duplex\"))";
               junos:must-message "link-mode should be half or full-duplex";
             }
             enum "100m" {
               description "100Mbps operation";
               junos:must "((\"vmhost management-if link-mode half-duplex\" || \"vmhost management-if link-mode full-duplex\"))";
               junos:must-message "link-mode should be half or full-duplex";
             }
             enum "1g" {
               description "1Gbps operation";
               junos:must "(\"vmhost management-if link-mode full-duplex\")";
               junos:must-message "link-mode should be configured as full";
             }
           }
         }
         leaf disable {
           description "Administratively disable the management port";
           type empty;
         }
       }
       container resize {
         junos:must "(\"system commit synchronize\")";
         junos:must-message "[system commit synchronize] has to be configured";
         description "Resize the resource allocation of guest VM";
         uses apply-advanced;
         container vjunos {
           description "Vjunos/adminjunos VM";
           uses apply-advanced;
           leaf compact {
             description "Reduce the resource allocation of vjunos VM";
             type empty;
           }
         }
       }
       list interfaces {
         key name;
         ordered-by user;
         description "Interface configuration";
         leaf name {
           type enumeration {
             enum "management-if0" {
               description "Configuration for the host's side management interface0";
             }
             enum "management-if1" {
               description "Configuration for the host's side management interface1";
             }
           }
         }
         uses apply-advanced;
         container family {
           description "Protocol family";
           container inet {
             presence "enable inet";
             description "IPv4 parameters";
             uses apply-advanced;
             list address {
               key name;
               ordered-by user;
               description "Interface address/destination prefix";
               leaf name {
                 description "Interface address/destination prefix";
                 type jt:ipv4prefix;
               }
               uses apply-advanced;
               leaf master-only {
                 description "Master management IP address for host";
                 type empty;
               }
             }
             leaf gateway {
               description "Gateway IP address";
               type jt:ipv4addr;
             }
           }
           container inet6 {
             presence "enable inet6";
             description "IPv6 parameters";
             uses apply-advanced;
             list address {
               key name;
               ordered-by user;
               description "Interface address/destination prefix";
               leaf name {
                 description "Interface address/destination prefix";
                 type jt:ipv6prefix;
               }
               uses apply-advanced;
               leaf master-only {
                 description "Master management IP address for host";
                 type empty;
               }
             }
             leaf gateway {
               description "Gateway IP address";
               type jt:ipv6addr;
             }
           }
         }
         list interface {
           key name;
           uses interfaces_type_ri;
         }
       }
       container syslog {
         presence "enable syslog";
         description "VMhost logging facility";
         uses apply-advanced;
         list file {
           key name;
           ordered-by user;
           description "File in which to log data";
           leaf name {
             description "Name of file in which to log data";
             type string {
               length "1 .. 1024";
               junos:posix-pattern "![/ %]";
               junos:pattern-message "Must not contain '/', % or a space";
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
         }
         list host {
           key name;
           ordered-by user;
           description "Host to be notified";
           leaf name {
             description "Host to be notified";
             type string {
               junos:posix-pattern "^[[:alnum:]._:-]+$";
               junos:pattern-message "Must be a string of alphanumericals, dashes or underscores, or a valid IP address";
             }
           }
           uses apply-advanced;
           list vmhost-syslog-object {
             key "facility level";
             leaf facility {
               description "Facility type";
               type enumeration {
                 enum "any" {
                   description "All facilities";
                 }
                 enum "authorization" {
                   description "Authorization system";
                 }
                 enum "privileged" {
                   description "Privileged authorization events";
                 }
                 enum "cron" {
                   description "Cron daemon";
                 }
                 enum "daemon" {
                   description "Various system processes";
                 }
                 enum "kernel" {
                   description "Kernel";
                 }
                 enum "lpr" {
                   description "Line printer spooling system";
                 }
                 enum "mail" {
                   description "Mail system";
                 }
                 enum "mark" {
                 }
                 enum "news" {
                   description "Network news system";
                 }
                 enum "syslog" {
                 }
                 enum "user" {
                   description "User processes";
                 }
                 enum "uucp" {
                   description "UUCP system";
                 }
                 enum "local0" {
                   description "Local logging option number 0";
                 }
                 enum "local1" {
                   description "Local logging option number 1";
                 }
                 enum "local2" {
                   description "Local logging option number 2";
                 }
                 enum "local3" {
                   description "Local logging option number 3";
                 }
                 enum "local4" {
                   description "Local logging option number 4";
                 }
                 enum "local5" {
                   description "Local logging option number 5";
                 }
                 enum "local6" {
                   description "Local logging option number 6";
                 }
                 enum "local7" {
                   description "Local logging option number 7";
                 }
               }
             }
             leaf level {
               description "Level name";
               type enumeration {
                 enum "any" {
                   description "All levels";
                 }
                 enum "emergency" {
                   description "Panic conditions";
                 }
                 enum "alert" {
                   description "Conditions that should be corrected immediately";
                 }
                 enum "critical" {
                   description "Critical conditions";
                 }
                 enum "error" {
                   description "Error conditions";
                 }
                 enum "warning" {
                   description "Warning messages";
                 }
                 enum "notice" {
                   description "Conditions that should be handled specially";
                 }
                 enum "info" {
                   description "Informational messages";
                 }
                 enum "none" {
                   description "No messages";
                 }
               }
             }
           }
           leaf transport {
             description "Transport type";
             default "udp";
             type enumeration {
               enum "tcp" {
                 description "TCP as transport of syslog";
               }
               enum "udp" {
                 description "UDP as transport of syslog";
               }
             }
           }
         }
       }
       container services {
         presence "enable services";
         description "System services";
         uses apply-advanced;
         container ssh {
           presence "enable ssh";
           description "Allow ssh access";
           uses apply-advanced;
           leaf root-login {
             description "Configure vmhost root access via ssh";
             type enumeration {
               enum "allow" {
                 description "Allow root access via ssh";
               }
               enum "deny" {
                 description "Do not allow root access via ssh";
               }
             }
           }
         }
       }
       leaf internal-ip-network {
         description "Internal Liveliness Bridge Interface address/destination prefix";
         type jt:ipv4prefix;
       }
       container virtualization-options {
         description "Virtualization options configuration";
         uses apply-advanced;
         list interfaces {
           key name;
           ordered-by user;
           description "Virtual interfaces configuration";
           leaf name {
             description "Virtual Interface name";
             type string {
               junos:posix-pattern "^(ge-([0|7])/0/([0-9]|(1[0-3]?)))$|^((ge-([1|8])/0/([1-9]|1[0-5])))$";
               junos:pattern-message "virtual interface name not allowed";
             }
           }
           uses apply-advanced;
           container mapping {
             description "Peer configuration";
             uses apply-advanced;
             choice mapping-choice {
               case case_1 {
                 leaf interface {
                   description "Set heth peer interface";
                   type string {
                     junos:posix-pattern "^(heth-[0-1]-([0-9]))$";
                     junos:pattern-message "invalid virtual heth interface name";
                   }
                 }
               }
               case case_2 {
                 leaf vlan {
                   description "Name of custom vlan";
                   junos:must "(\"vmhost vlans $$ vlan-id none\")";
                   junos:must-message "Custom vlan must be configured under vmhost vlans stanza";
                   type string;
                 }
               }
             }
           }
         }
       }
       container vlans {
         description "VLAN configuration";
         uses apply-advanced;
         list vlan {
           key name;
           description "Virtual LAN";
           uses vlan-types;
         }
       }
       container forwarding-options {
         description "Configure options to control packet forwarding";
         uses apply-advanced;
         list analyzer {
           key name;
           description "Analyzer options";
           leaf name {
             description "Analyzer name";
             type string;
           }
           uses apply-advanced;
           container input {
             junos:must "(\".. output\")";
             junos:must-message "output port must be specified";
             description "Port to monitor";
             uses apply-advanced;
             container ingress {
               description "Ports to monitor incoming traffic";
               uses analyzer-input-port-type;
             }
             container egress {
               description "Ports to monitor outgoing traffic";
               uses analyzer-input-port-type;
             }
           }
           container output {
             description "Outgoing port for mirrored packets";
             junos:must "(\".. input\")";
             junos:must-message "input port must be specified";
             uses analyzer-output-port-type;
           }
         }
       }
       container cross-connect {
         description "Cross connect configuration";
         uses apply-advanced;
         list pcc {
           key name;
           uses cross-connect-type;
         }
       }
     }
   }
   grouping analyzer-input-port-type {
     uses apply-advanced;
     list virtual-network-function {
       key name;
       ordered-by user;
       description "Virtual network function";
       leaf name {
         description "Virtual network function name";
         junos:must "(\"virtual-network-functions $$\")";
         junos:must-message "Specified VNF doesn't exist";
         junos:must "(\".. interface\")";
         junos:must-message "vnf interface name must be specified";
         type string;
       }
       uses apply-advanced;
       list interface {
         key name;
         ordered-by user;
         description "Virtual network function interface";
         leaf name {
           description "Virtual network function interface name";
           type string {
             junos:posix-pattern "^eth[0-9]$";
             junos:pattern-message "Only eth0 to eth9 interface is supported";
           }
         }
         uses apply-advanced;
       }
     }
   }
   grouping analyzer-output-port-type {
     uses apply-advanced;
     leaf virtual-network-function {
       description "Virtual network function name";
       junos:must "(\"virtual-network-functions $$\")";
       junos:must-message "Specified VNF doesn't exist";
       junos:must "(\".. interface\")";
       junos:must-message "vnf interface name must be specified";
       type string;
     }
     leaf interface {
       description "Virtual network function interface name";
       junos:must "(\".. virtual-network-function\")";
       junos:must-message "virtual-network-function must be specified";
       type string {
         junos:posix-pattern "^eth[0-9]$";
         junos:pattern-message "Only eth0 to eth9 interface is supported";
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping cross-connect-type {
     description "Bidirectional switch between interfaces";
     leaf name {
       description "Name of interface switch";
       type string;
     }
     uses apply-advanced;
     container from {
       presence "enable from";
       description "Cross-connect from vnf or physical interface";
       uses apply-advanced;
       list virtual-interface {
         key name;
         ordered-by user;
         description "Set virtual interface as switch port";
         leaf name {
           description "Virtual interface name";
           type string {
             junos:posix-pattern "^(hsxe0)$|^(hsxe1)|^((ge-1/0/([0-9]|1[0-5])))$";
             junos:pattern-message "Only hsxe(0/1) and ge-1/0/* interfaces are allowed";
           }
         }
         uses apply-advanced;
         leaf vlan-id {
           description "IEEE 802.1q VLAN identifier for VLAN";
           type string;
         }
       }
       list virtual-network-function {
         key name;
         ordered-by user;
         description "Set virtual interface as switch port";
         leaf name {
           description "Virtual network function name";
           junos:must "(\".. interface\")";
           junos:must-message "interface name must be specified for this vnf";
           type string;
         }
         uses apply-advanced;
         leaf interface {
           description "Virtual network function interfaces";
           type string;
         }
         leaf vlan-id {
           description "IEEE 802.1q VLAN identifier for VLAN";
           type string;
         }
       }
     }
     container to {
       presence "enable to";
       description "Cross-connect to vnf or physical interface";
       uses apply-advanced;
       list virtual-interface {
         key name;
         ordered-by user;
         description "Set virtual interface as switch port";
         leaf name {
           description "Virtual interface name";
           type string {
             junos:posix-pattern "^(hsxe0)$|^(hsxe1)|^((ge-1/0/([0-9]|1[0-5])))$";
             junos:pattern-message "Only hsxe(0/1) and ge-1/0/* interfaces are allowed";
           }
         }
         uses apply-advanced;
         leaf vlan-id {
           description "IEEE 802.1q VLAN identifier for VLAN";
           type string;
         }
       }
       list virtual-network-function {
         key name;
         ordered-by user;
         description "Set virtual interface as switch port";
         leaf name {
           description "Virtual network function name";
           junos:must "(\".. interface\")";
           junos:must-message "interface name must be specified for this vnf";
           type string;
         }
         uses apply-advanced;
         leaf interface {
           description "Virtual network function interfaces";
           type string;
         }
         leaf vlan-id {
           description "IEEE 802.1q VLAN identifier for VLAN";
           type string;
         }
       }
     }
     list virtual-interface {
       key name;
       ordered-by user;
       description "Set virtual interface as switch port";
       leaf name {
         description "Virtual interface name";
         type string {
           junos:posix-pattern "^(hsxe0)$|^(hsxe1)|^((ge-1/0/([0-9]|1[0-5])))$";
           junos:pattern-message "Only hsxe(0/1) and ge-1/0/* interfaces are allowed";
         }
       }
       uses apply-advanced;
       leaf vlan-id {
         description "IEEE 802.1q VLAN identifier for VLAN";
         type string;
       }
     }
     list virtual-network-function {
       key name;
       ordered-by user;
       description "Set virtual interface as switch port";
       leaf name {
         description "Virtual network function name";
         junos:must "(\".. interface\")";
         junos:must-message "interface name must be specified for this vnf";
         type string;
       }
       uses apply-advanced;
       leaf interface {
         description "Virtual network function interfaces";
         type string;
       }
       leaf vlan-id {
         description "IEEE 802.1q VLAN identifier for VLAN";
         type string;
       }
     }
   }
   grouping interfaces_type_ri {
     description "Physical interface";
     leaf name {
       type string;
     }
     uses apply-advanced;
     container ether-options {
       description "Ethernet interface-specific options";
       uses apply-advanced;
       choice auto-negotiation-choice {
         leaf auto-negotiation {
           description "Enable auto-negotiation";
           type empty;
         }
         leaf no-auto-negotiation {
           description "Don't enable auto-negotiation";
           type empty;
         }
       }
       choice flow-control-choice {
         leaf flow-control {
           description "Enable flow control";
           type empty;
         }
         leaf no-flow-control {
           description "Don't enable flow control";
           type empty;
         }
       }
       leaf link-mode {
         description "Link duplex";
         type enumeration {
           enum "automatic" {
             description "Automatic negotiate duplex ";
             junos:must "(\".. auto-negotiation\")";
             junos:must-message "auto-negotiation must be configured to enable link-mode auto-negotiation";
           }
           enum "half-duplex" {
             description "Half-duplex operation";
             junos:must "((\".. auto-negotiation\" || \".. speed\"))";
             junos:must-message "link-mode and speed must be configured if auto-negotiation is not enabled";
           }
           enum "full-duplex" {
             description "Full-duplex operation";
             junos:must "((\".. auto-negotiation\" || \".. speed\"))";
             junos:must-message "link-mode and speed must be configured if auto-negotiation is not enabled";
           }
         }
       }
       container speed {
         description "Specify speed";
         choice automatic {
           case case_1 {
             container auto-negotiation {
               presence "enable auto-negotiation";
               junos:must "(\".. .. auto-negotiation\")";
               junos:must-message "auto-negotiation must be configured to enable speed auto-negotiation";
               description "Enable auto-negotiation";
               leaf auto-negotiate-10-100 {
                 description "Limits the auto-negotiation to 10m/100m only";
                 type empty;
               }
             }
           }
           case case_2 {
             leaf ethernet-10m {
               description "10Mbps";
               junos:must "((\".. .. auto-negotiation\" || \".. .. link-mode\"))";
               junos:must-message "link-mode and speed must be configured if auto-negotiation is not enabled";
               type empty;
             }
           }
           case case_3 {
             leaf ethernet-100m {
               description "100Mbps";
               junos:must "((\".. .. auto-negotiation\" || \".. .. link-mode\"))";
               junos:must-message "link-mode and speed must be configured if auto-negotiation is not enabled";
               type empty;
             }
           }
           case case_4 {
             leaf ethernet-1g {
               description "1Gbps";
               junos:must "((\".. .. auto-negotiation\" || \".. .. link-mode\"))";
               junos:must-message "link-mode and speed must be configured if auto-negotiation is not enabled";
               type empty;
             }
           }
         }
       }
     }
     container dsl-sfp-options {
       description "DSL SFP options";
       uses apply-advanced;
       container adsl-options {
         description "ADSL options";
         uses apply-advanced;
         leaf vpi {
           description "Virtual path identifier";
           junos:must "(\".. vci\")";
           junos:must-message "vci must be specified";
           type union {
             type string {
               pattern "<.*>|$.*";
             }
             type int32 {
               range "0 .. 255";
             }
           }
         }
         leaf vci {
           description "Virtual circuit identifier";
           junos:must "(\".. vpi\")";
           junos:must-message "vpi must be specified";
           type union {
             type string {
               pattern "<.*>|$.*";
             }
             type int32 {
               range "32 .. 65535";
             }
           }
         }
         leaf encap {
           description "Encapsulation";
           junos:must "((\".. vci\" && \".. vpi\"))";
           junos:must-message "vci and vpi must be specified";
           type enumeration {
             enum "llcsnap-bridged-802.1q" {
               description "LLCSNAP bridged 802.1q";
             }
             enum "vc-mux-bridged" {
               description "VC MUX bridged";
             }
           }
         }
       }
       container vdsl-options {
         description "VDSL options";
         uses apply-advanced;
         leaf profile {
           description "VDSL profile";
           type enumeration {
             enum "auto" {
               description "Automatic";
             }
             enum "8a" {
               description "Profile 8a";
             }
             enum "8b" {
               description "Profile 8b";
             }
             enum "8c" {
               description "Profile 8c";
             }
             enum "8d" {
               description "Profile 8d";
             }
             enum "12a" {
               description "Profile 12a";
             }
             enum "12b" {
               description "Profile 12b";
             }
             enum "17a" {
               description "Profile 17a";
             }
             enum "30a" {
               description "Profile 30a";
             }
           }
         }
         leaf carrier {
           description "Carrier setting";
           type enumeration {
             enum "auto" {
               description "Automatic";
             }
             enum "a43" {
               description "Carrier A43";
             }
             enum "b43" {
               description "Carrier B43";
             }
           }
         }
       }
     }
     choice vlan_tag_mode {
       case case_1 {
         leaf vlan-tagging {
           description "802.1q VLAN tagging support";
           junos:must "((!(\".. unit\") || all \".. unit <*> vlan-id\"))";
           junos:must-message "All units under this ifd must be configured with vlan-id ";
           junos:must "(!(\".. unit $$={0} family ethernet-switching\"))";
           junos:must-message "vlan-tagging cannot be specified for an interface with family ethernet-switching";
           type empty;
         }
       }
       case case_2 {
         leaf flexible-vlan-tagging {
           description "Support for no tagging, or single VLAN tagging";
           junos:must "((!(\".. unit\") || all \".. unit <*> vlan-id\"))";
           junos:must-message "All units under this ifd must be configured with vlan-id ";
           junos:must "(!(\".. unit $$={0} family ethernet-switching\"))";
           junos:must-message "flexible-vlan-tagging cannot be specified for an interface with family ethernet-switching";
           type empty;
         }
       }
     }
     leaf native-vlan-id {
       description "Virtual LAN identifier for untagged frames";
       junos:must "((\".. flexible-vlan-tagging\" || \".. unit $$={0} family ethernet-switching interface-mode trunk\"))";
       junos:must-message "native-vlan-id can be specified with flexible-vlan-tagging mode or with interface-mode trunk";
       type union {
         type string {
           pattern "<.*>|$.*";
         }
         type uint32 {
           range "0 .. 4094";
         }
       }
     }
     leaf mtu {
       description "Transmit packet size ";
       type union {
         type uint32;
         type string {
           pattern "<.*>|$.*";
         }
       }
     }
     leaf mac {
       description "Hardware MAC address";
       type jt:mac-unicast;
     }
     list unit {
       key name;
       description "Logical interface";
       leaf name {
         junos:must "((!(\".. .. .. .. interfaces $$={irb} unit $$={${unit}}\") || any \"vmhost vlans <*> l3-interface irb.${unit}\"))";
         junos:must-message "irb logical units must be associated with vlans";
         type string;
       }
       uses apply-advanced;
       choice enable-disable {
         case case_1 {
           leaf disable {
             description "Disable this logical interface";
             type empty;
           }
         }
       }
       leaf vlan-id {
         description "Virtual LAN identifier value for 802.1q VLAN tags";
         junos:must "((\".. .. vlan-tagging\" || \".. .. flexible-vlan-tagging\"))";
         junos:must-message "vlan-id can only be specified on tagged interfaces";
         junos:must "(unique \".. .. unit <*> vlan-id $$\")";
         junos:must-message "vlan-id has to be unique for different ifls";
         type string;
       }
       container family {
         description "Protocol family";
         container inet {
           presence "enable inet";
           description "IPv4 parameters";
           uses apply-advanced;
           container dhcp {
             description "Dynamic Host Configuration Protocol client configuration";
             presence "enable dhcp";
             junos:must "(!(\"system autoinstallation\"))";
             junos:must-message "Incompatible with 'system autoinstallation'";
             junos:must "(!(\".. address\"))";
             junos:must-message "Incompatible with interface assigned with address";
             uses dhcp-client-type;
           }
           list address {
             key name;
             ordered-by user;
             description "Interface address/destination prefix";
             max-elements 1;
             leaf name {
               description "Interface address/destination prefix";
               type jt:ipv4prefix;
             }
             uses apply-advanced;
           }
         }
         container inet6 {
           presence "enable inet6";
           description "IPv6 protocol parameters";
           uses apply-advanced;
           list address {
             key name;
             ordered-by user;
             description "Interface address or destination prefix";
             junos:must "(!(\".. unnumbered-address\"))";
             junos:must-message "ipv6 unnumbered-address and ipv6 address must not be defined simultaneously";
             max-elements 1;
             leaf name {
               description "Interface address or destination prefix";
               type jt:ipv6prefix;
             }
             uses apply-advanced;
           }
           container dhcp {
             description "Dynamic Host Configuration Protocol client configuration";
             presence "enable dhcp";
             junos:must "(!(\"system autoinstallation\"))";
             junos:must-message "Incompatible with 'system autoinstallation'";
             junos:must "(!(\".. address\"))";
             junos:must-message "Incompatible with interface assigned with address";
             uses dhcp-client-type;
           }
         }
         container ethernet-switching {
           description "Ethernet switching parameters";
           presence "enable ethernet-switching";
           junos:must "(!(\".. .. .. .. ..  interfaces $$={irb} unit $$={0} family ethernet-switching\"))";
           junos:must-message "Family ethernet-switching cannot be configured on irb interfaces";
           junos:must "((!(\".. inet\") && !(\".. inet6\")))";
           junos:must-message "Family ethernet-switching and rest of the families are mutually exclusive";
           junos:must "(\".. .. .. unit $$={0}\")";
           junos:must-message "Family ethernet-switching can be configured only on unit 0";
           uses jdm-ethernet-switching-type;
         }
       }
     }
   }
   grouping dhcp-client-type {
     description "Dynamic Host Configuration Protocol client configuration";
     uses apply-advanced;
     container client-identifier {
       description "DHCP server identifies a client by client-identifier value ";
       uses apply-advanced;
       choice client-identifier-choice {
         case case_1 {
           leaf ascii {
             description "Client identifier as an ASCII string";
             type string;
           }
         }
         case case_2 {
           leaf hexadecimal {
             description "Client identifier as a hexadecimal string";
             type string {
               junos:posix-pattern "^[[:xdigit:]]+$";
               junos:pattern-message "Must be hexadecimal digits (0-9, a-f, A-F)";
             }
           }
         }
       }
       container user-id {
         description "Add user id to client-id option ";
         choice user-id-choice {
           case case_1 {
             leaf ascii {
               description "Client identifier as an ASCII string";
               type string;
             }
           }
           case case_2 {
             leaf hexadecimal {
               description "Client identifier as a hexadecimal string";
               type string {
                 junos:posix-pattern "^[[:xdigit:]]+$";
                 junos:pattern-message "Must be hexadecimal digits (0-9, a-f, A-F)";
               }
             }
           }
         }
       }
       container prefix {
         description "Add prefix to client-id option";
         uses apply-advanced;
         leaf host-name {
           description "Add router host name to client-id option";
           type empty;
         }
         leaf logical-system-name {
           description "Add logical system name to client-id option";
           type empty;
         }
         leaf routing-instance-name {
           description "Add routing instance name to client-id option";
           type empty;
         }
       }
       leaf use-interface-description {
         description "Use the interface description";
         type enumeration {
           enum "logical" {
             description "Use the logical interface description";
           }
           enum "device" {
             description "Use the device interface description";
           }
         }
       }
     }
     container no-dns-install {
       presence "enable no-dns-install";
       description "Do not install DNS information learned from DHCP server";
     }
     leaf lease-time {
       description "Lease time in seconds requested in DHCP client protocol packet";
       units "seconds";
       type string;
     }
     leaf retransmission-attempt {
       description "Number of attempts to retransmit the DHCP client protocol packet";
       default "4";
       type union {
         type string {
           pattern "<.*>|$.*";
         }
         type uint32 {
           range "0 .. 6";
         }
       }
     }
     leaf retransmission-interval {
       description "Number of seconds between successive retransmission";
       default "4";
       units "seconds";
       type union {
         type string {
           pattern "<.*>|$.*";
         }
         type uint32 {
           range "4 .. 64";
         }
       }
     }
     leaf metric {
       description "Client initiated default-route metric";
       default "0";
       type union {
         type string {
           pattern "<.*>|$.*";
         }
         type uint32 {
           range "0 .. 255";
         }
       }
     }
     leaf server-address {
       description "DHCP Server-address";
       type jt:ipv4addr;
     }
     leaf update-server {
       description "Propagate TCP/IP settings to DHCP server";
       type empty;
     }
     leaf vendor-id {
       description "Vendor class id for the DHCP Client";
       type string {
         length "1 .. 60";
       }
     }
     leaf force-discover {
       description "Send DHCPDISCOVER after DHCPREQUEST retransmission failure";
       type empty;
     }
     container options {
       description "DHCP options";
       uses apply-advanced;
       list number {
         key name;
         description "DHCP option code";
         leaf name {
           description "DHCP option identifier code";
           type union {
             type string {
               pattern "<.*>|$.*";
             }
             type uint32 {
               range "1 .. 254";
             }
           }
         }
         choice option-type-choice {
           case case_1 {
             leaf hex-string {
               description "Hexadecimal string";
               type string {
                 length "1 .. 510";
                 junos:posix-pattern "^[[:xdigit:]]+$";
                 junos:pattern-message "Must be hexadecimal digits (0-9, a-f, A-F)";
               }
             }
           }
         }
       }
       leaf no-hostname {
         description "Do not carry hostname (RFC option code is 12) in packet";
         type empty;
       }
     }
     list requested-options {
       key name;
       description "DHCP options";
       leaf name {
         description "DHCP option identifier code";
         type union {
           type string {
             pattern "<.*>|$.*";
           }
           type uint32 {
             range "1 .. 254";
           }
         }
       }
     }
   }
   grouping jdm-ethernet-switching-type {
     description "Ethernet switching family";
     uses apply-advanced;
     leaf interface-mode {
       description "Type of interface mode";
       default "access";
       type enumeration {
         enum "access" {
           description "Interface mode is access";
         }
         enum "trunk" {
           description "Interface mode is trunk";
           junos:must "(\".. vlan members\")";
           junos:must-message "For trunk interface, please ensure vlan members is configured";
         }
       }
     }
     container vlan {
       description "Virtual LAN parameters";
       uses apply-advanced;
       leaf-list members {
         ordered-by user;
         description "Membership for this interface";
         type string;
       }
     }
   }
   grouping macro-data-type {
     leaf name {
       description "Keyword part of the keyword-value pair";
       type string;
     }
     leaf value {
       description "Value part of the keyword-value pair";
       type string;
     }
   }
   grouping vlan-types {
     description "Virtual LAN";
     leaf name {
       description "VLAN name";
       junos:must "((\".. vlan-id\" || \".. vlan-id-list\"))";
       junos:must-message "vlan-id/vlan-id-list must be configure";
       junos:must "(((!(\"vlans ${vlan} isolated-vlan\") && (!(\"vlans ${vlan} community-vlans\") && !(\"vlans ${vlan} private-vlan\"))) || !(\"vlans ${vlan} forwarding-options filter output\")))";
       junos:must-message "Configuring Egress VACL is not supported on PVLAN";
       type string {
         length "2 .. 64";
       }
     }
     uses apply-advanced;
     leaf vlan-id {
       description "IEEE 802.1q VLAN identifier for VLAN";
       type string;
     }
     leaf-list vlan-id-list {
       description "Create VLAN for each of the vlan-id specified in the vlan-id-list";
       junos:must "(!(\".. vlan-id\"))";
       junos:must-message "vlan-id and vlan-id-list cannot be configured together";
       junos:must "((!(\".. isolated-vlan\") && !(\".. community-vlans\")))";
       junos:must-message "PVLAN related configuration cannot be specified with vlan-id-list";
       junos:must "(!(\" .. multicast-snooping-options\"))";
       junos:must-message "multicast-snooping-options can not be specified under vlan-id-list";
       junos:must "(!(\" .. domain-type\"))";
       junos:must-message "domain-type can not be specified  under vlan-id-list";
       junos:must "(!(\".. interface\"))";
       junos:must-message "interface can not be specified under vlan-id-list";
       junos:must "(!(any \".. switch-options interface <*> static-mac\"))";
       junos:must-message "static mac can not be specified under vlan-id-list";
       type jt:vlan-range;
     }
     leaf l3-interface {
       description "L3 interface name for this vlans";
       junos:must "(\".. vlan-id none\")";
       junos:must-message "l3-interface can be configured only under vlans with 'vlan-id none'";
       junos:must "(unique \"vmhost vlans <*> l3-interface $$\")";
       junos:must-message "Same l3-interface cannot be attached to more than one vlan";
       junos:must "(!((\".. .. .. protocols evpn mclag\" && !(\".. no-arp-suppression\"))))";
       junos:must-message "no-arp-suppression needs to be configured, when evpn is configured with mclag.";
       junos:must "(!((\".. mcae-mac-synchronize\" && \"interfaces $$-IFL mac\")))";
       junos:must-message "irb-ifl mac and vlan mcae-mac-synchronize cannot coexist";
       junos:must "((!(\"interfaces $$-IFL family mpls\") || !((\"routing-instances ${instance} instance-type virtual-switch\" && (\"routing-instances ${instance} protocols vpls\" && \"routing-instances ${instance} route-distinguisher\")))))";
       junos:must-message "routing-interface with family MPLS cannot be added to virtual-switch with protocol VPLS";
       junos:must "((!(\".. vlan-tags\") || !(\"interfaces $$-IFL family mpls\")))";
       junos:must-message "routing-interface with family MPLS cannot be added to bridge-domain with 'vlan-tags'";
       junos:must "((!(\".. vlan-id all\") && !(\".. vlan-id inner-all\")))";
       junos:must-message "l3-interface cannot be configured under vlans with 'vlan-id all' or 'vlan-id inner-all'";
       junos:must "((\".. vlan-id\" || \".. vlan-tags\"))";
       junos:must-message "l3-interface can be configured only under vlans with 'vlan-id'/'vlan-tags'";
       junos:must "(\"interfaces $$-IFL\")";
       junos:must-message "Interface must already be defined under [edit interfaces]";
       type union {
         type jt:interface-unit;
         type string {
           pattern "<.*>|$.*";
         }
       }
     }
     leaf description {
       description "Text description of VLANs";
       type string {
         junos:posix-pattern "^.{1,255}$";
         junos:pattern-message "Must be a string of 255 characters or less";
       }
     }
     choice vlan-identifier-choice {
       case case_1 {
         container vlan-tags {
           presence "enable vlan-tags";
           description "IEEE 802.1q VLAN tags for VLANs";
           leaf outer {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
           leaf inner {
             description "[tpid.]vlan-id, tpid format is 0xNNNN and is optional";
             type string {
               junos:posix-pattern "^(0[Xx][0-9A-Fa-f]{4}.([0-9]{1,3}|1[0-9]{3}|2[0-9]{3}|3[0-9]{3}|40[0-8][0-9]|409[0-4]))$|^([0-9]{1,3}|1[0-9]{3}|2[0-9]{3}|3[0-9]{3}|40[0-8][0-9]|409[0-4])$";
               junos:pattern-message "vlan-id in vlan-tag (0xNNNN.vlan-id) must be 0 to 4094";
             }
           }
         }
       }
     }
     list interface {
       key name;
       ordered-by user;
       description "Interface name for this VLAN";
       leaf name {
         junos:must "((!(\"interfaces $$-IFL family\") || \"interfaces $$-IFL family ethernet-switching\"))";
         junos:must-message "only family bridge can be configured on this interface";
         junos:must "((!((\"interfaces $$ vlan-id-list\" || \"interfaces $$ vlan-tags inner-list\")) || (!((\".. .. vlan-id\" || \".. .. vlan-tags\")) || (\".. no-normalization\" || \".. .. switch-options no-normalization\"))))";
         junos:must-message "interface with vlan-id-list/inner-list cannot be added to a vlan with a vlan-id/vlan-tags configured";
         junos:must "(!((\"interfaces $$-IFL family ethernet-switching interface-mode\" || \"interfaces $$-IFL family ethernet-switching vlan members\")))";
         junos:must-message "Interface with 'interface-mode' config is not allowed under vlans";
         junos:must "(!(\".. .. .. interfaces $$\"))";
         junos:must-message "This interface is already defined at the routing-instance level";
         junos:must "((\"interfaces $$-IFL\" || !(\".. .. .. .. protocols evpn encapsulation\")))";
         junos:must-message "Interface not defined; Interface must be defined for configuring under VLAN for protocols evpn";
         junos:must "(((\".. .. vlan-id all\" && \"interfaces $$-IFL input-vlan-map pop\") || ((\".. .. vlan-id inner-all\" && \"interfaces $$-IFL input-vlan-map\") || (!((\".. .. vlan-id\" || \".. .. vlan-tags\")) || (!((\"interfaces $$-IFL input-vlan-map\" || \"interfaces $$-IFL output-vlan-map\")) || (\".. no-normalization\" || \".. .. switch-options no-normalization\"))))))";
         junos:must-message "interface with input/output vlan-maps cannot be added to a routing-instance with a vlan-id/vlan-tags configured";
         junos:must "((!(\"interfaces $$-IFL vlan-tags inner-range\") || ((\".. .. vlan-id all\" || \".. .. vlan-id inner-all\") || (\".. no-normalization\" || \".. .. switch-options no-normalization\"))))";
         junos:must-message "vlan-tags inner-range is specified for this logical interface; 'vlan-id all' or 'vlan-id inner-all' should also be enabled";
         junos:must "(((!(\"interfaces $$-IFL vlan-id-range\") || \".. .. vlan-id all\") || (\".. no-normalization\" || \".. .. switch-options no-normalization\")))";
         junos:must-message "vlan-id-range is specified for this logical interface; 'vlan-id all' should also be enabled";
         junos:must "(!(\".. .. switch-options interface $$ interface-mac-limit\"))";
         junos:must-message "Interface mac limit should not be configured at VLAN level for sub interfaces";
         junos:must "((!(\"interfaces $$-IFL vlan-id-list\") || !((\"interfaces $$-IFL input-vlan-map swap\" || \"interfaces $$-IFL input-vlan-map pop\"))))";
         junos:must-message "interface with vlan-id-list and input-vlan-map swap/pop is not supported";
         junos:must "((!(\"interfaces $$-IFL vlan-id\") || !((\".. .. vlan-tags\" || \".. .. vlan-id-list\"))))";
         junos:must-message "interface with vlan-id cannot be added to vlan with vlan-tags/vlan-id-list configured";
         junos:must "((!(\"interfaces $$-IFL vlan-id-list\") || !((\".. .. vlan-id\" || (\".. .. vlan-tags\" || \".. .. vlan-id-list\")))))";
         junos:must-message "interface with vlan-id-list cannot be added to a vlan with a vlan-id/vlan-tags/vlan-id-list configured";
         type string;
       }
       uses apply-advanced;
     }
     leaf no-local-switching {
       description "Disable local switching within CE-facing interfaces";
       type empty;
     }
     container forwarding-options {
       description "Forwarding options configuration";
       uses juniper-ethernet-switching-forwarding-options;
     }
     container multicast-snooping-options {
       description "Multicast snooping option configuration";
       junos:must "(\".. .. .. protocols igmp-snooping vlan ${vlan}\")";
       junos:must-message "multicast-snooping-options can be configured only if snooping is enabled on the vlan";
       uses juniper-multicast-snooping-options;
     }
     container switch-options {
       description "VLANs switch-options configuration";
       uses juniper-protocols-vlan;
     }
     leaf domain-type {
       description "Type of VLANs SVLAN/DVLAN";
       type enumeration {
         enum "bridge" {
           description "Forwarding instance";
         }
       }
     }
     leaf no-irb-layer-2-copy {
       description "Disable transmission of layer-2 copy of packets of IRB routing-interface";
       junos:must "(\".. l3-interface\")";
       junos:must-message "l3-interface must be configured to configure this feature";
       type empty;
     }
     leaf service-id {
       description "Service id required if VLAN is of type MC-AE, and vlan-id all or vlan-id none or vlan-tags is configured";
       type union {
         type string {
           pattern "<.*>|$.*";
         }
         type uint32 {
           range "1 .. 65535";
         }
       }
     }
     leaf domain-id {
       description "Domain-id for auto derived Route Target";
       junos:must "(\".. .. .. protocols evpn encapsulation vxlan\")";
       junos:must-message "domain-id is allowed for EVPN instances only";
       type union {
         type string {
           pattern "<.*>|$.*";
         }
         type uint32 {
           range "1 .. 15";
         }
       }
     }
     leaf mcae-mac-synchronize {
       description "Enable IRB MAC synchronization in this VLAN";
       junos:must "(\".. l3-interface\")";
       junos:must-message "Layer 3 interface for this VLAN is not configured";
       type empty;
     }
     container proxy-mac {
       junos:must "(\".. .. .. instance-type virtual-switch\")";
       junos:must-message "Applicable to instance-type evpn only";
       description "Proxy MAC settings";
       uses apply-advanced;
       leaf irb {
         description "Reply with virtual-gateway MAC or IRB MAC";
         junos:must "(!(\".. .. no-arp-suppression\"))";
         junos:must-message "Proxy MAC is not supported with no-arp-supression";
         junos:must "((\".. .. l3-interface\" && !(\".. proxy-mac-address\")))";
         junos:must-message "Proxy MAC in IRB mode should have routing-interface configured";
         type empty;
       }
       leaf proxy-mac-address {
         description "Reply with configured MAC for all requests";
         junos:must "(!(\".. .. no-arp-suppression\"))";
         junos:must-message "Proxy MAC is not supported with no-arp-supression";
         junos:must "((!(\".. .. l3-interface\") && !(\".. irb\")))";
         junos:must-message "Proxy MAC with specified MAC should not have routing-interface configured";
         type jt:mac-unicast;
       }
     }
     leaf mcae-mac-flush {
       description "Enable IRB MAC flush in a/s mode for this VLAN on MCAE link up";
       type empty;
     }
     leaf private-vlan {
       description "Type of secondary vlan for private vlan";
       junos:must "(!((\".. isolated-vlan\" || \".. community-vlans\")))";
       junos:must-message "This vlan is already configured as primary vlan";
       junos:must "(!(\".. l3-interface\"))";
       junos:must-message "l3-interface cannot be configured on a secondary vlan";
       type enumeration {
         enum "isolated" {
           description "Isolated vlan";
         }
         enum "community" {
           description "Community vlan";
         }
       }
     }
     leaf isolated-vlan {
       description "VLAN id or name";
       junos:must "(!(\".. private-vlan\"))";
       junos:must-message "This vlan is already configured as secondary vlan";
       type string {
         junos:posix-pattern "^([[:alpha:]][[:alnum:]_.-]+)|^([1-9][0-9]{0,2}|[1-3][0-9]{3}|40[0-8][0-9]|409[0-4])$";
         junos:pattern-message "Must be a valid VLAN name or VLAN tag";
       }
     }
     leaf-list community-vlans {
       ordered-by user;
       description "List of VLAN id or name";
       junos:must "(!(\".. private-vlan\"))";
       junos:must-message "This vlan is already configured as secondary vlan";
       type string;
     }
     container vxlan {
       junos:must "((((\". ovsdb-managed\" || \".. .. .. switch-options ovsdb-managed\") && (!((\". ingress-node-replication\" || \".. .. .. protocols evpn encapsulation vxlan\")) && !(\". multicast-group\"))) || ((!((\". ovsdb-managed\" || \".. .. .. switch-options ovsdb-managed\")) && ((\". ingress-node-replication\" || \".. .. .. protocols evpn encapsulation vxlan\") && !(\". multicast-group\"))) || (!((\". ovsdb-managed\" || \".. .. .. switch-options ovsdb-managed\")) && (!((\". ingress-node-replication\" || \".. .. .. protocols evpn encapsulation vxlan\")) && \". multicast-group\")))))";
       junos:must-message "ovsdb, multicast-group, ingress-node-replication cannot be configured together";
       junos:must "((\". ovsdb-managed\" || (\".. .. .. switch-options ovsdb-managed\" || (\". multicast-group\" || (\"routing-instances ${instance} remote-vtep-list\" || (\".. .. .. switch-options remote-vtep-list\" || (\". ingress-node-replication\" || \".. .. .. protocols evpn encapsulation vxlan\")))))))";
       junos:must-message "One of multicast-group or ovsdb-managed or ingress-node-replication or protocols evpn encapsulation vxlan or remote-vtep-list should be enabled";
       junos:must "((!(\".. vlan-id all\") && !(\".. vlan-id all\")))";
       junos:must-message "vxlan does not support bridge domain with 'vlan-id all' or 'vlan-id inner-all'";
       junos:must "((\"routing-instances ${instance} vtep-source-interface\" || \".. .. .. switch-options vtep-source-interface\"))";
       junos:must-message "vtep-source-interface is required for VXLAN configuration";
       uses apply-advanced;
       leaf ovsdb-managed {
         description "Bridge-domain is managed remotely via VXLAN OVSDB Controller";
         junos:must "(!((\"routing-instances ${instance} remote-vtep-list\" || (\".. .. .. .. switch-options remote-vtep-list\" || (\".. multicast-group\" || \".. .. .. .. protocols evpn encapsulation vxlan\")))))";
         junos:must-message "ovsdb-managed not valid with remote-vtep-list or multicast-group or protocol evpn encapsulation vxlan";
         type empty;
       }
       leaf vni {
         description "VXLAN identifier";
         type union {
           type string {
             pattern "<.*>|$.*";
           }
           type uint32 {
             range "0 .. 16777214";
           }
         }
       }
       leaf multicast-group {
         description "Multicast group registered for VXLAN segment";
         junos:must "(!((\"routing-instances ${instance} remote-vtep-list\" || (\".. .. .. switch-options remote-vtep-list\" || (\".. ovsdb-managed\" || (\"routing-instances ${instance} switch-options ovsdb-managed\" || \".. .. .. .. protocols evpn encapsulation vxlan\"))))))";
         junos:must-message "multicast-group not valid with remote-vtep-list or ovsdb-managed or evpn configuration";
         type jt:ipv4addr;
       }
       leaf encapsulate-inner-vlan {
         description "Retain inner VLAN in the packet";
         type empty;
       }
       leaf decapsulate-accept-inner-vlan {
         description "Accept VXLAN packets with inner VLAN";
         type empty;
       }
       leaf unreachable-vtep-aging-timer {
         description "Unreachable VXLAN tunnel endpoint removal timer";
         units "seconds";
         type union {
           type string {
             pattern "<.*>|$.*";
           }
           type uint16 {
             range "300 .. 1800";
           }
         }
       }
       leaf ingress-node-replication {
         description "Enable ingress node replication";
         junos:must "(!(\".. .. .. .. protocols evpn assisted-replication\"))";
         junos:must-message "ingress-node-replication cannot be configured with assisted-replication";
         junos:must "((\".. ovsdb-managed\" || (\".. .. .. .. switch-options ovsdb-managed\" || (\"routing-instances ${instance} remote-vtep-list\" || (\".. .. .. .. switch-options remote-vtep-list\" || \".. .. .. .. protocols evpn encapsulation vxlan\")))))";
         junos:must-message "Valid for ovsdb-managed instance or with remote-vtep-list or with protocols evpn encapsulation vxlan";
         type empty;
       }
     }
   }
   grouping juniper-ethernet-switching-forwarding-options {
     uses apply-advanced;
     container filter {
       description "Filtering for ethernet switching forwarding table";
       uses apply-advanced;
       leaf input {
         description "Name of input filter to apply for forwarded packets";
         type string;
       }
       leaf output {
         description "Name of output filter to apply for forwarded packets";
         junos:must "(!(any \"firewall family ethernet-switching filter $$ term <*> from traffic-type-except\"))";
         junos:must-message "Vacl with term as 'from traffic-type-except' not supported on the egress side";
         junos:must "(!(any \"firewall family ethernet-switching filter $$ term <*> from traffic-type\"))";
         junos:must-message "Vacl with term as 'from traffic-type' not supported on the egress side";
         type string;
       }
     }
     container flood {
       description "Filtering for ethernet switching flood table";
       uses apply-advanced;
       leaf input {
         description "Name of input filter to apply for ethernet switching flood packets";
         type string;
       }
     }
     container dhcp-relay {
       description "Dynamic Host Configuration Protocol relay configuration";
       status deprecated;
       junos:must "(!(\"forwarding-options helpers bootp\"))";
       junos:must-message "'dhcp-relay' statement cannot be included along with 'forwarding-options helpers bootp' statement";
       uses jdhcp-relay-type;
     }
     container dhcp-security {
       description "DHCP access security configuration";
       presence "enable dhcp-security";
       uses jdhcp-security-type;
     }
     container fip-security {
       description "FCoE Initiation Protocol security configuration";
       presence "enable fip-security";
       uses fip-security-type;
     }
   }
   grouping fip-security-type {
     uses apply-advanced;
     list interface {
       key name;
       description "Configure access port security for this interface";
       leaf name {
         junos:must "(!(any \"vlans <*> interface $$ egress\"))";
         junos:must-message "Fip security options cannot be configured on egress members of a vlan";
         type union {
           type jt:interface-name;
           type string {
             pattern "<.*>|$.*";
           }
         }
       }
       uses apply-advanced;
       choice fcoe-trusted-choice {
         leaf fcoe-trusted {
           description "Make this interface trusted for FCoE";
           type empty;
         }
         leaf no-fcoe-trusted {
           description "Don't make this interface trusted for FCoE";
           type empty;
         }
       }
     }
     leaf fc-map {
       description "FCoE MAC address prefix";
       type string {
         junos:posix-pattern "^0x0EF[CD][abcdefABCDEF0123456789]{2}$";
         junos:pattern-message "Must be hexadecimal bit pattern of 0x0EFCHH or 0x0EFDHH";
       }
     }
     container examine-vn2vf {
       presence "enable examine-vn2vf";
       junos:must "(!(\".. examine-vn2vn\"))";
       junos:must-message "examine-vn2vf cannot be used with examine-vn2vn";
       description "Enable FIP snooping on this VLAN";
       uses apply-advanced;
       leaf satellite {
         description "FIP snooping enabled for extended port";
         type empty;
       }
     }
     container examine-vn2vn {
       presence "enable examine-vn2vn";
       junos:must "(!(\".. examine-vn2vf\"))";
       junos:must-message "examine-vn2vn cannot be used with examine-vn2vf";
       description "Enable VN2VN FIP snooping on this VLAN";
       uses apply-advanced;
       leaf beacon-period {
         description "FCoE VN2VN beacon period";
         default "8000";
         units "milliseconds";
         type union {
           type string {
             pattern "<.*>|$.*";
           }
           type uint32 {
             range "250 .. 90000";
           }
         }
       }
     }
   }
   grouping jdhcp-relay-type {
     description "Dynamic Host Configuration Protocol relay configuration";
     uses apply-advanced;
     container traceoptions {
       description "DHCP relay trace options";
       status deprecated;
       junos:must "(!(\"forwarding-options helpers bootp\"))";
       junos:must-message "Incompatible with 'forwarding-options helpers bootp'";
       junos:must "(!(\"system services dhcp\"))";
       junos:must-message "Incompatible with 'set system services dhcp'";
       uses jdhcp-traceoptions-type;
     }
     container persistent-storage {
       description "Trigger to enable flat file storage";
       leaf automatic {
         description "Trigger automatically";
         type empty;
       }
     }
     leaf duplicate-clients-on-interface {
       description "Allow duplicate clients on different interfaces in a subnet";
       status deprecated;
       type empty;
     }
     container duplicate-clients-in-subnet {
       description "Allow duplicate clients in a subnet";
       junos:must "(!(\".. duplicate-clients-on-interface\"))";
       junos:must-message "Cannot specify duplicate-clients-in-subnet with duplicate-clients-on-interface";
       uses jdhcp-duplicate-clients-in-subnet-type;
     }
     container interface-traceoptions {
       description "DHCP relay interface trace options";
       status deprecated;
       uses jdhcp-interface-traceoptions-type;
     }
     container dhcpv6 {
       description "DHCPv6 configuration";
       uses dhcpv6-relay-type;
     }
     leaf arp-inspection {
       description "Enable Dynamic ARP Inspection";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container authentication {
       description "DHCP authentication";
       junos:must "(!(\"forwarding-options helpers bootp\"))";
       junos:must-message "'authentication' statement cannot be included along with 'forwarding-options helpers bootp' statement";
       uses authentication-type;
     }
     container liveness-detection {
       description "DHCP client liveness detection processing";
       junos:must "(!(\"forwarding-options helpers bootp\"))";
       junos:must-message "'liveness-detection' statement cannot be included along with 'forwarding-options helpers bootp' statement";
       uses dhcp-liveness-detection-type;
     }
     container dynamic-profile {
       description "Dynamic profile to use";
       junos:must "(!(\"forwarding-options helpers bootp\"))";
       junos:must-message "'dynamic-profile' statement cannot be included along with 'forwarding-options helpers bootp' statement";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       junos:must "(!(\"forwarding-options helpers bootp\"))";
       junos:must-message "'access-profile' statement cannot be included along with 'forwarding-options helpers bootp' statement";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCP override processing";
       presence "enable overrides";
       junos:must "(!(\"forwarding-options helpers bootp\"))";
       junos:must-message "'overrides' statement cannot be included along with 'forwarding-options helpers bootp' statement";
       uses override-type;
     }
     container relay-option {
       description "DHCP option processing";
       presence "enable relay-option";
       junos:must "((!(\".. relay-option-60\") && !(any \".. group <*> relay-option-60\")))";
       junos:must-message "Cannot specify relay-option-60 with relay-option";
       uses dhcp-generic-v4-option;
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option-60 {
       description "DHCP option-60 processing";
       presence "enable relay-option-60";
       status deprecated;
       junos:must "(!(\"forwarding-options helpers bootp\"))";
       junos:must-message "'relay-option-60' statement cannot be included along with 'forwarding-options helpers bootp' statement";
       junos:must "((!(\".. relay-option\") && !(any \".. group <*> relay-option\")))";
       junos:must-message "Cannot specify relay-option with relay-option-60 ";
       uses relay-option-60-type-top;
     }
     container relay-option-82 {
       description "DHCP option-82 processing";
       presence "enable relay-option-82";
       junos:must "(!(\"forwarding-options helpers bootp\"))";
       junos:must-message "'relay-option-82' statement cannot be included along with 'forwarding-options helpers bootp' statement";
       uses relay-option-82-type;
     }
     container forward-only {
       description "Forward DHCP packets without creating binding";
       presence "enable forward-only";
       junos:must "(!(\"forwarding-options helpers bootp\"))";
       junos:must-message "'forward-only' statement cannot be included along with 'forwarding-options helpers bootp' statement";
       uses forward-only-to-rc-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     leaf forward-only-replies {
       description "Forward-only replies from server to appropriate logical-system:routing-instance based on options";
       type empty;
     }
     container server-group {
       description "Define a DHCP server group";
       junos:must "(!(\"forwarding-options helpers bootp\"))";
       junos:must-message "'server-group' statement cannot be included along with 'forwarding-options helpers bootp' statement";
       uses server-group-type;
     }
     container active-server-group {
       description "Name of DHCP server group";
       uses dhcpv4-gbl-active-sg-type;
     }
     container route-suppression {
       description "Suppress access-internal and/or destination route addition";
       junos:must "(!(\".. liveness-detection method layer2-liveness-detection\"))";
       junos:must-message "Cannot specify route-suppression with liveness-detection method layer2-liveness-detection";
       junos:must "(!(\".. overrides no-arp\"))";
       junos:must-message "Cannot specify route-suppression with overrides no-arp";
       uses dhcp-route-suppression-type;
     }
     list group {
       key name;
       ordered-by user;
       description "Define a DHCP group";
       junos:must "(!(\"forwarding-options helpers bootp\"))";
       junos:must-message "'group' statement cannot be included along with 'forwarding-options helpers bootp' statement";
       uses dhcp-group;
     }
     list dual-stack-group {
       key name;
       description "Define a DHCP dual stack group";
       uses dhcp-dual-stack-group;
     }
     leaf no-snoop {
       description "Do not snoop DHCP packets";
       junos:must "(!(\"legacy-snooping\"))";
       junos:must-message "'no-snoop' statement cannot be included along with 'legacy-snooping' statement";
       type empty;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
     container leasequery {
       description "DHCP leasequery configuration";
       presence "enable leasequery";
       junos:must "(\".. overrides always-write-option-82\")";
       junos:must-message "Must configure [overrides always-write-option-82] to overwrite circuit-id";
       junos:must "((\".. relay-option-82 circuit-id\" && (!(\".. relay-option-82 circuit-id use-interface-description\") && !(\".. relay-option-82 circuit-id require-interface-description\"))))";
       junos:must-message "Must configure [relay-option-82 circuit-id] without description to insert circuit-id";
       uses relay-leasequery-type;
     }
     container bulk-leasequery {
       description "DHCP bulk leasequery configuration";
       presence "enable bulk-leasequery";
       junos:must "(\".. overrides always-write-option-82\")";
       junos:must-message "Must configure [overrides always-write-option-82] to overwrite circuit-id";
       junos:must "((\".. relay-option-82 circuit-id\" && (!(\".. relay-option-82 circuit-id use-interface-description\") && !(\".. relay-option-82 circuit-id require-interface-description\"))))";
       junos:must-message "Must configure [relay-option-82 circuit-id] without description to insert circuit-id";
       uses relay-bulk-leasequery-v4-type;
     }
     container active-leasequery {
       description "DHCPv4 active leasequery configuration";
       presence "enable active-leasequery";
       junos:must "(\".. bulk-leasequery\")";
       junos:must-message "Must configure bulk-leasequery";
       uses relay-active-leasequery-v4-type;
     }
     container remote-id-mismatch {
       description "DHCP client remote-id mismatch";
       presence "enable remote-id-mismatch";
       uses dhcp-remote-id-mismatch-type;
     }
   }
   grouping authentication-type {
     description "DHCP authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       container option-82 {
         presence "enable option-82";
         description "Include option 82";
         leaf circuit-id {
           description "Include option 82 circuit-id (sub option 1)";
           type empty;
         }
         leaf remote-id {
           description "Include option 82 remote-id (sub option 2)";
           type empty;
         }
       }
       leaf logical-system-name {
         description "Include logical system name";
         type empty;
       }
       leaf routing-instance-name {
         description "Include routing instance name";
         type empty;
       }
       leaf option-60 {
         description "Include option 60";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcp-dual-stack-group {
     description "DHCP dual stack groups";
     leaf name {
       description "Dual stack group name";
       type string {
         length "1 .. 64";
         junos:posix-pattern "^[A-Za-z0-9][_0-9A-Za-z-]*$";
         junos:pattern-message "Must be a non-reserved string of 64 characters or less";
       }
     }
     uses apply-advanced;
     container authentication {
       description "DHCP authentication";
       uses dual-stack-authentication-type;
     }
     leaf service-profile {
       description "Dynamic profile to use for default service activation";
       type string {
         length "1 .. 128";
       }
     }
     leaf access-profile {
       description "Access profile to be used for jdhcpd";
       type string {
         length "1 .. 128";
       }
     }
     container dynamic-profile {
       description "Dynamic profile to use";
       uses dynamic-profile-type;
     }
     container liveness-detection {
       description "DHCP client liveness detection processing";
       uses dhcp-liveness-detection-dualstack-type;
     }
     container relay-agent-interface-id {
       description "Interface-id option processing";
       presence "enable relay-agent-interface-id";
       uses v6-relay-option-interface-id-type;
     }
     container relay-agent-remote-id {
       description "Remote-id option processing";
       presence "enable relay-agent-remote-id";
       uses v6-relay-option-remote-id-type;
     }
     container classification-key {
       description "Classification key for identifying dual stack household";
       junos:must "(\".. dynamic-profile\")";
       junos:must-message "dynamic profile configuration in dual-stack-group is must for configuring classification-type";
       uses classification-types;
     }
     leaf dual-stack-interface-client-limit {
       description "Limit the number of client allowed on an interface";
       type union {
         type string {
           pattern "<.*>|$.*";
         }
         type uint32 {
           range "1 .. 500000";
         }
       }
     }
     container protocol-master {
       description "Select family as protocol master";
       uses jdhcp-dual-stack-protocol-mstr-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
   }
   grouping classification-types {
     description "Different mechanisms to identify a single household";
     uses apply-advanced;
     leaf mac-address {
       description "MAC address of client";
       type empty;
     }
     leaf circuit-id {
       description "Circuit-id as key";
       type empty;
     }
     leaf remote-id {
       description "Remote-id as key";
       type empty;
     }
   }
   grouping dhcp-generic-v4-option {
     description "Generic DHCP options processing";
     uses apply-advanced;
     leaf option-number {
       description "Option number";
       status deprecated;
       type enumeration {
         enum "60" {
           description "Option 60";
           status deprecated;
         }
         enum "77" {
           description "Option 77";
           status deprecated;
         }
       }
     }
     container equals {
       description "Generic option equals";
       status deprecated;
       uses relay-v4-option-ascii-hex;
     }
     container default-action {
       description "Generic option default action";
       status deprecated;
       uses dhcp-v4-option-default-action;
     }
     container starts-with {
       description "Generic option starts with";
       status deprecated;
       uses relay-v4-option-ascii-hex;
     }
     container option-60 {
       description "Add option 60 processing";
       presence "enable option-60";
       junos:must "(!(\"option-number\"))";
       junos:must-message "Cannot specify option-60  with option-number";
       uses dhcp-generic-v4-option-type;
     }
     container option-77 {
       description "Add option 77 processing";
       presence "enable option-77";
       junos:must "(!(\"option-number\"))";
       junos:must-message "Cannot specify option-77  with option-number";
       uses dhcp-generic-v4-option-type;
     }
     list option-order {
       key name;
       ordered-by user;
       description "Options precedence order";
       junos:must "(!(\"option-number\"))";
       junos:must-message "Cannot specify option-order  with option-number";
       leaf name {
         description "Option number";
         type enumeration {
           enum "60" {
             description "Option 60";
           }
           enum "77" {
             description "Option 77";
           }
         }
       }
       uses apply-advanced;
     }
   }
   grouping dhcp-generic-v4-option-type {
     uses apply-advanced;
     container equals {
       description "Generic option equals";
       uses relay-v4-option-ascii-hex;
     }
     container default-action {
       description "Generic option default action";
       uses dhcp-v4-option-default-action;
     }
     container starts-with {
       description "Generic option starts with";
       uses relay-v4-option-ascii-hex;
     }
   }
   grouping dhcp-group {
     description "DHCP groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCP server group";
       uses dhcpv4-gp-active-sg-type;
     }
     container authentication {
       description "DHCP authentication";
       uses authentication-type;
     }
     container liveness-detection {
       description "DHCP client liveness detection processing";
       uses dhcp-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container overrides {
       description "DHCP override processing";
       presence "enable overrides";
       uses override-type;
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container server-match {
       description "Server match processing";
       uses apply-advanced;
       container default-action {
         description "Server match default action";
         presence "enable default-action";
         uses server-match-action-choice;
       }
       list address {
         key name;
         ordered-by user;
         description "Server address";
         leaf name {
           description "Server address for matching";
           type jt:ipv4prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     container relay-option {
       description "DHCP option processing";
       presence "enable relay-option";
       junos:must "((!(\".. relay-option-60\") && !(\".. .. relay-option-60\")))";
       junos:must-message "Cannot specify relay-option-60 with relay-option";
       uses dhcp-generic-v4-option;
     }
     container relay-option-60 {
       description "DHCP option-60 processing";
       presence "enable relay-option-60";
       status deprecated;
       junos:must "((!(\".. relay-option\") && !(\".. .. relay-option\")))";
       junos:must-message "Cannot specify relay-option with relay-option-60";
       uses relay-option-60-type-group;
     }
     container relay-option-82 {
       description "DHCP option-82 processing";
       presence "enable relay-option-82";
       uses relay-option-82-type;
     }
     container forward-only {
       description "Forward DHCP packets without creating binding";
       presence "enable forward-only";
       uses forward-only-to-rc-type;
     }
     container route-suppression {
       description "Suppress access-internal and/or destination route addition";
       junos:must "(!(\".. liveness-detection method layer2-liveness-detection\"))";
       junos:must-message "Cannot specify route-suppression with liveness-detection method layer2-liveness-detection";
       junos:must "((!(\".. overrides no-arp\") && !(\".. .. overrides no-arp\")))";
       junos:must-message "Cannot specify route-suppression with overrides no-arp";
       uses dhcp-route-suppression-type;
     }
     leaf description {
       description "Text description of servers";
       type string;
     }
     leaf maximum-hop-count {
       description "Maximum number of hops per packet";
       type union {
         type string {
           pattern "<.*>|$.*";
         }
         type uint32 {
           range "1 .. 16";
         }
       }
     }
     leaf minimum-wait-time {
       description "Minimum number of seconds before requests are forwarded";
       type union {
         type string {
           pattern "<.*>|$.*";
         }
         type uint32 {
           range "0 .. 30000";
         }
       }
     }
     leaf client-response-ttl {
       description "IP time-to-live value to set in responses to client";
       type union {
         type string {
           pattern "<.*>|$.*";
         }
         type uint32 {
           range "1 .. 255";
         }
       }
     }
     leaf source-ip-change {
       description "Use address of egress interface as source ip";
       type empty;
     }
     list interface {
       key name;
       description "One or more interfaces";
       leaf name {
         description "Interface name";
         type union {
           type jt:interface-name;
           type string {
             pattern "<.*>|$.*";
           }
         }
       }
       uses apply-advanced;
       leaf upto {
         description "Interface up to";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCP override processing";
         junos:must "(!(\".. exclude\"))";
         junos:must-message "Cannot specify overrides with exclude";
         uses override-type;
       }
       container dynamic-profile {
         description "Dynamic profile to use";
         junos:must "(!(\".. exclude\"))";
         junos:must-message "Cannot specify overrides with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container remote-id-mismatch {
       description "DHCP client remote-id mismatch";
       presence "enable remote-id-mismatch";
       uses dhcp-remote-id-mismatch-type;
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv4 offer and ack packets";
           type empty;
         }
       }
     }
   }
   grouping dhcp-liveness-detection-dualstack-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-arp-nud-liveness-detection-type {
     description "Address Resolution detection options";
     uses apply-advanced;
     leaf transmit-interval {
       description "Transmit interval for address resolution";
       default "300";
       units "seconds";
       type union {
         type string {
           pattern "<.*>|$.*";
         }
         type uint32 {
           range "300 .. 1800";
         }
       }
     }
     leaf max-consecutive-retries {
       description "Retry attempts";
       default "3";
       type union {
         type string {
           pattern "<.*>|$.*";
         }
         type uint32 {
           range "3 .. 6";
         }
       }
     }
   }
   grouping dhcp-liveness-detection-failure-action-type {
     description "Liveness detection failure action options";
     uses apply-advanced;
     choice failure-action-type {
       case case_1 {
         leaf clear-binding {
           description "Clear the client binding";
           type empty;
         }
       }
       case case_2 {
         leaf clear-binding-if-interface-up {
           description "Clear the client binding only if the incoming interface is up";
           type empty;
         }
       }
       case case_3 {
         leaf log-only {
           description "Maintain the client binding and log the failure event";
           type empty;
         }
       }
     }
   }
   grouping dhcp-liveness-detection-type {
     description "DHCP client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Address resolution options";
             junos:must "((!(\".. .. route-suppression\") && (!(\".. .. .. route-suppression\") && !(\".. .. .. .. route-suppression\"))))";
             junos:must-message "Method not allowed with route-suppression enabled";
             uses dhcp-arp-nud-liveness-detection-type;
           }
         }
       }
     }
   }
   grouping dhcp-bfd-liveness-detection-type {
     description "Bidirectional Forwarding Detection (BFD) options";
     uses apply-advanced;
     leaf version {
       description "BFD protocol version number";
       default "automatic";
       type enumeration {
         enum "0" {
           description "BFD version 0 (deprecated)";
         }
         enum "1" {
           description "BFD version 1";
         }
         enum "automatic" {
           description "Choose BFD version automatically";
         }
       }
     }
     leaf minimum-interval {
       description "Minimum transmit and receive interval";
       units "milliseconds";
       type union {
         type string {
           pattern "<.*>|$.*";
         }
         type uint32 {
           range "30000 .. 255000";
         }
       }
     }
     leaf minimum-transmit-interval {
       description "Minimum transmit interval";
       status deprecated;
       units "milliseconds";
       type union {
         type string {
           pattern "<.*>|$.*";
         }
         type uint32 {
           range "30000 .. 255000";
         }
       }
     }
     leaf minimum-receive-interval {
       description "Minimum receive interval";
       units "milliseconds";
       type union {
         type string {
           pattern "<.*>|$.*";
         }
         type uint32 {
           range "30000 .. 255000";
         }
       }
     }
     leaf multiplier {
       description "Detection time multiplier";
       default "3";
       type union {
         type string {
           pattern "<.*>|$.*";
         }
         type uint32 {
           range "1 .. 255";
         }
       }
     }
     choice adaptation-choice {
       case case_1 {
         leaf no-adaptation {
           description "Disable adaptation";
           type empty;
         }
       }
     }
     container transmit-interval {
       description "Transmit-interval options";
       uses apply-advanced;
       leaf minimum-interval {
         description "Minimum transmit interval";
         units "milliseconds";
         type union {
           type string {
             pattern "<.*>|$.*";
           }
           type uint32 {
             range "30000 .. 255000";
           }
         }
       }
       leaf threshold {
         description "High transmit interval triggering a trap";
         units "milliseconds";
         type union {
           type uint32;
           type string {
             pattern "<.*>|$.*";
           }
         }
       }
     }
     container detection-time {
       description "Detection-time options";
       uses apply-advanced;
       leaf threshold {
         description "High detection-time triggering a trap";
         units "milliseconds";
         type union {
           type uint32;
           type string {
             pattern "<.*>|$.*";
           }
         }
       }
     }
     leaf session-mode {
       description "BFD single-hop or multihop session-mode";
       default "automatic";
       type enumeration {
         enum "automatic" {
           description "Choose session-mode automatically";
         }
         enum "single-hop" {
           description "Use single-hop";
         }
         enum "multihop" {
           description "Use multihop";
         }
       }
     }
     leaf holddown-interval {
       description "Time to hold the session-UP notification to the client";
       default "0";
       units "milliseconds";
       type union {
         type string {
           pattern "<.*>|$.*";
         }
         type uint32 {
           range "0 .. 255000";
         }
       }
     }
   }
   grouping dhcp-remote-id-mismatch-type {
     description "DHCP client remote-id-mismatch processing";
     uses apply-advanced;
     leaf disconnect {
       description "Disconnect session on remote-id mismatch";
       type empty;
     }
   }
   grouping dhcp-route-suppression-type {
     uses apply-advanced;
     choice dhcp-route-suppression-choice {
       case case_1 {
         leaf access-internal {
           description "Suppress access-internal and destination route addition";
           type empty;
         }
       }
       case case_2 {
         leaf destination {
           description "Suppress destination route addition";
           type empty;
         }
       }
     }
   }
   grouping dhcp-v4-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding dhcp-relay server-group]";
           type string {
             length "1 .. 64";
           }
         }
       }
       case case_2 {
         leaf local-server-group {
           description "Name of DHCP local server group when match is made";
           junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
           junos:must-message "Referenced group must be defined under [edit system services dhcp-local-server group]";
           type string {
             length "1 .. 64";
           }
         }
       }
       case case_3 {
         leaf drop {
           description "Discard when a match is made";
           type empty;
         }
       }
       case case_4 {
         leaf forward-only {
           description "Forward without subscriber services when a match is made";
           type empty;
         }
       }
     }
   }
   grouping dhcpv4-gbl-active-sg-type {
     leaf active-server-group {
       description "Name of DHCP server group";
       junos:must "(\".. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv4-gp-active-sg-type {
     leaf active-server-group {
       description "Name of DHCP server group";
       junos:must "(\".. .. .. server-group $$\")";
       junos:must-message "Referenced group must be defined under [edit forwarding-options dhcp-relay server-group]";
       type string {
         length "1 .. 64";
       }
     }
     leaf allow-server-change {
       description "Accept DHCP-ACK from any server in this group";
       type empty;
     }
   }
   grouping dhcpv6-relay-type {
     description "DHCPv6 relay configuration";
     uses apply-advanced;
     container authentication {
       description "DHCPv6 authentication";
       uses dhcpv6-authentication-type;
     }
     container persistent-storage {
       description "Trigger to enable flat file storage";
       leaf automatic {
         description "Trigger automatically";
         type empty;
       }
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
     leaf relay-agent-option-79 {
       description "Add the client MAC address to the Relay Forward header.";
       type empty;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     leaf forward-only-replies {
       description "Forward-only replies from server to appropriate logical-system:routing-instance based on options";
       type empty;
     }
     container forward-snooped-clients {
       junos:must "((!(\".. forward-only\") && (!(\".. forward-only-replies\") && !(any \".. group <*> forward-only\"))))";
       junos:must-message "forward-only and forward-only-replies cannot be configured when forward-snooped-clients is configured";
       description "Forward snooped (unicast) packets";
       choice interface-type {
         case case_1 {
           leaf configured-interfaces {
             description "Forward snooped (unicast) packets on configured interfaces";
             type empty;
           }
         }
         case case_2 {
           leaf non-configured-interfaces {
             description "Forward snooped (unicast) packets on non-configured interfaces";
             type empty;
           }
         }
         case case_3 {
           leaf all-interfaces {
             description "Forward snooped (unicast) packets on configured and non-configured interfaces";
             type empty;
           }
         }
       }
     }
     container route-suppression {
       description "Suppress access-internal and/or access route addition";
       uses dhcpv6-route-suppression-type;
     }
     list group {
       key name;
       ordered-by user;
       description "Define a DHCPv6 relay group";
       uses dhcpv6-relay-group;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container server-group {
       description "Define a DHCPv6 server group";
       uses v6-server-group-type;
     }
     container active-server-group {
       description "Name of DHCPv6 server group";
       uses dhcpv6-gbl-active-sg-type;
     }
     leaf server-response-time {
       description "Number of seconds in a period of activity between the last server response and an unaswered request";
       default "0";
       type union {
         type uint32;
         type string {
           pattern "<.*>|$.*";
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     leaf no-snoop {
       description "Do not snoop DHCPV6 packets";
       junos:must "(!(\"legacy-snooping\"))";
       junos:must-message "'no-snoop' statement cannot be included along with 'legacy-snooping' statement";
       type empty;
     }
     container leasequery {
       description "DHCPv6 leasequery configuration";
       presence "enable leasequery";
       junos:must "(\".. relay-agent-interface-id\")";
       junos:must-message "Must configure [relay-agent-interface-id] to insert interface-id";
       uses relay-leasequery-type;
     }
     container bulk-leasequery {
       description "DHCPv6 bulk leasequery configuration";
       presence "enable bulk-leasequery";
       junos:must "(\".. relay-agent-interface-id\")";
       junos:must-message "Must configure [relay-agent-interface-id] to insert interface-id";
       uses relay-bulk-leasequery-v6-type;
     }
     container active-leasequery {
       description "DHCPv6 active leasequery configuration";
       presence "enable active-leasequery";
       junos:must "(\".. bulk-leasequery\")";
       junos:must-message "Must configure bulk-leasequery";
       uses relay-active-leasequery-v6-type;
     }
     container remote-id-mismatch {
       description "DHCP client remote-id mismatch";
       presence "enable remote-id-mismatch";
       uses dhcp-remote-id-mismatch-type;
     }
     container duplicate-clients {
       description "Allow duplicate clients";
       uses dhcpv6-duplicate-clients-type;
     }
   }
   grouping dhcp-generic-v6-option {
     description "Generic DHCPv6 options processing";
     uses apply-advanced;
     leaf option-number {
       description "Option number";
       status deprecated;
       type enumeration {
         enum "15" {
           description "Option 15";
           status deprecated;
         }
         enum "16" {
           description "Option 16";
           status deprecated;
         }
       }
     }
     container equals {
       description "Generic option equals";
       status deprecated;
       uses relay-v6-option-ascii-hex;
     }
     container default-action {
       description "Generic option default action";
       status deprecated;
       uses dhcp-v6-option-default-action;
     }
     container starts-with {
       description "Generic option starts with";
       status deprecated;
       uses relay-v6-option-ascii-hex;
     }
     container option-15 {
       description "Add option 15 processing";
       presence "enable option-15";
       junos:must "(!(\"option-number\"))";
       junos:must-message "Cannot specify option-15  with option-number";
       uses dhcp-generic-v6-option-type;
     }
     container option-16 {
       description "Add option 16 processing";
       presence "enable option-16";
       junos:must "(!(\"option-number\"))";
       junos:must-message "Cannot specify option-16  with option-number";
       uses dhcp-generic-v6-option-type;
     }
     list option-order {
       key name;
       ordered-by user;
       description "Options precedence order";
       junos:must "(!(\"option-number\"))";
       junos:must-message "Cannot specify option-order  with option-number";
       leaf name {
         description "Option number";
         type enumeration {
           enum "15" {
             description "Option 15";
           }
           enum "16" {
             description "Option 16";
           }
         }
       }
       uses apply-advanced;
     }
   }
   grouping dhcp-generic-v6-option-type {
     uses apply-advanced;
     container equals {
       description "Generic option equals";
       uses relay-v6-option-ascii-hex;
     }
     container default-action {
       description "Generic option default action";
       uses dhcp-v6-option-default-action;
     }
     container starts-with {
       description "Generic option starts with";
       uses relay-v6-option-ascii-hex;
     }
   }
   grouping dhcp-v6-option-default-action {
     description "Default action";
     uses apply-advanced;
     choice server-group-choice {
       case case_1 {
         leaf relay-server-group {
           description "Name of DHCP relay server group when match is made";
           junos:must "((\".. .. .. .. .. .. server-group $$\" || (\".. .. .. .. .. server-group $$\" || (\".. .. .. .. server-group $$\" || \".. .. .. server-group $$\"))))";
           junos:must-message "Referenced group must be defined under [edit forwarding options dhcp-relay dhcpv6 server-group]";
           type string {
             length "1 .. 64";
           }
         }
       }
       case case_2 {
         leaf drop {
           description "Discard when a match is made";
           type empty;
         }
       }
       case case_3 {
         leaf forward-only {
           description "Forward without subscriber services when a match is made";
           type empty;
         }
       }
     }
   }
   grouping dhcpv6-authentication-type {
     description "DHCPv6 authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf client-id {
         description "Include client ID";
         type empty;
       }
       container relay-agent-remote-id {
         presence "enable relay-agent-remote-id";
         description "Include the relay agent remote ID";
         uses apply-advanced;
         choice relay-agent-remote-id-choice {
           case case_1 {
             leaf enterprise-id {
               description "Only use enterprise-id portion of option-37";
               status deprecated;
               type empty;
             }
           }
           case case_2 {
             leaf remote-id {
               description "Only use remote-id portion of option-37";
               status deprecated;
               type empty;
             }
           }
         }
       }
       leaf logical-system-name {
         description "Include logical system name";
         type empty;
       }
       leaf routing-instance-name {
         description "Include routing instance name";
         type empty;
       }
       leaf relay-agent-subscriber-id {
         description "Include the relay agent subscriber ID";
         type empty;
       }
       leaf relay-agent-interface-id {
         description "Include the relay agent interface ID";
         type empty;
       }
       leaf circuit-type {
         description "Include circuit type";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf vlan-tags {
         description "Include the vlan tag(s)";
         type empty;
       }
     }
   }
   grouping dhcpv6-duplicate-clients-type {
     description "Allow duplicate clients";
     choice distinguish-with {
       case case_1 {
         leaf incoming-interface {
           description "Allow duplicate clients on different underlying interfaces";
           type empty;
         }
       }
     }
   }
   grouping dhcpv6-gbl-active-sg-type {
     uses apply-advanced;
     leaf active-server-group {
       description "Name of DHCPv6 server group";
       junos:must "(\".. .. server-group $$\")";
       junos:must-message "Referenced group must be defined under [edit forwarding-options dhcp-relay dhcpv6 server-group]";
       type string {
         length "1 .. 64";
       }
     }
   }
   grouping dhcpv6-liveness-detection-type {
     description "DHCPv6 client liveness detection processing";
     uses apply-advanced;
     container failure-action {
       description "Liveness detection failure action options";
       uses dhcp-liveness-detection-failure-action-type;
     }
     container method {
       description "Liveness detection method options";
       uses apply-advanced;
       choice method-choice {
         case case_1 {
           container bfd {
             description "Bidirectional Forwarding Detection (BFD) options";
             uses dhcp-bfd-liveness-detection-type;
           }
         }
         case case_2 {
           container layer2-liveness-detection {
             description "Neighbor discovery options";
             uses dhcp-arp-nud-liveness-detection-type;
           }
         }
       }
     }
   }
   grouping dhcpv6-override-relay-type {
     description "DHCPv6 relay override processing";
     uses apply-advanced;
     choice allow-snooped-clients-choice {
       leaf allow-snooped-clients {
         description "Allow client creation from snooped PDUs";
         type empty;
       }
       leaf no-allow-snooped-clients {
         description "Don't allow client creation from snooped PDUs";
         type empty;
       }
     }
     leaf delay-authentication {
       description "Delay subscriber authentication in DHCP protocol processing until request packet";
       type empty;
     }
     leaf interface-client-limit {
       description "Limit the number of clients allowed on an interface";
       type union {
         type string {
           pattern "<.*>|$.*";
         }
         type uint32 {
           range "1 .. 500000";
         }
       }
     }
     leaf dual-stack {
       description "Dual stack group to use.";
       type string {
         length "1 .. 64";
       }
     }
     leaf no-bind-on-request {
       description "Do not bind if stray DHCPv6 RENEW, REBIND is received";
       type empty;
     }
     container client-negotiation-match {
       description "Use secondary match criteria for SOLICIT PDU";
       choice match-with {
         case case_1 {
           leaf incoming-interface {
             description "Use incoming interface";
             type empty;
           }
         }
       }
     }
     leaf send-release-on-delete {
       description "Always send RELEASE to the server when a binding is deleted";
       type empty;
     }
     leaf always-process-option-request-option {
       description "Always process option even after address allocation failure";
       type empty;
     }
     leaf relay-source {
       description "Interface for relay source";
       type union {
         type jt:interface-name;
         type string {
           pattern "<.*>|$.*";
         }
       }
     }
     leaf delete-binding-on-renegotiation {
       description "Delete binding on renegotiation";
       type empty;
     }
     leaf asymmetric-lease-time {
       description "Use a reduced lease time for the client. In seconds";
       units "seconds";
       type union {
         type string {
           pattern "<.*>|$.*";
         }
         type uint32 {
           range "600 .. 86400";
         }
       }
     }
     leaf asymmetric-prefix-lease-time {
       description "Use a reduced prefix lease time for the client. In seconds";
       units "seconds";
       type union {
         type string {
           pattern "<.*>|$.*";
         }
         type uint32 {
           range "600 .. 86400";
         }
       }
     }
   }
   grouping dhcpv6-relay-group {
     description "DHCPv6 groups";
     leaf name {
       description "Group name";
       type string {
         length "1 .. 64";
         junos:posix-pattern "^[A-Za-z0-9][_0-9A-Za-z-]*$";
         junos:pattern-message "Must be a non-reserved string of 64 characters or less";
       }
     }
     uses apply-advanced;
     container active-server-group {
       description "Name of DHCPv6 server group";
       uses dhcpv6-gp-active-sg-type;
     }
     list dual-stack-group {
       key name;
       description "Define a DHCP dual stack group";
       uses dhcp-dual-stack-group;
     }
     container authentication {
       description "DHCPv6 authentication";
       uses dhcpv6-authentication-type;
     }
     container liveness-detection {
       description "DHCPv6 client liveness detection processing";
       uses dhcpv6-liveness-detection-type;
     }
     container dynamic-profile {
       description "Dynamic profile to use";
       uses dynamic-profile-type;
     }
     leaf service-profile {
       description "Dynamic profile to use for default service activation";
       type string {
         length "1 .. 128";
       }
     }
     leaf access-profile {
       description "Access profile to use for AAA services";
       junos:must "(\"access profile $$\")";
       junos:must-message "Matching access profile must be defined";
       type string {
         length "1 .. 128";
       }
     }
     container short-cycle-protection {
       description "Short cycle lockout configuration";
       leaf lockout-min-time {
         description "Short cycle lockout time in seconds";
         type union {
           type string {
             pattern "<.*>|$.*";
           }
           type uint32 {
             range "1 .. 86400";
           }
         }
       }
       leaf lockout-max-time {
         description "Short cycle lockout time in seconds";
         type union {
           type string {
             pattern "<.*>|$.*";
           }
           type uint32 {
             range "1 .. 86400";
           }
         }
       }
     }
     container overrides {
       description "DHCPv6 override processing";
       presence "enable overrides";
       uses dhcpv6-override-relay-type;
     }
     container relay-option {
       description "DHCPv6 option processing";
       presence "enable relay-option";
       uses dhcp-generic-v6-option;
     }
     container vendor-specific-information {
       description "DHCPv6 option 17 vendor-specific processing";
       uses jdhcp-vendor-specific-type;
     }
     container forward-only {
       description "Forward DHCPv6 packets without creating binding";
       presence "enable forward-only";
       uses forward-only-to-rc-type;
     }
     container relay-agent-interface-id {
       description "DHCPv6 interface-id option processing";
       presence "enable relay-agent-interface-id";
       uses v6-relay-option-interface-id-type;
     }
     container relay-agent-remote-id {
       description "DHCPv6 remote-id option processing";
       presence "enable relay-agent-remote-id";
       uses v6-relay-option-remote-id-type;
     }
     container route-suppression {
       description "Suppress access-internal and/or access route addition";
       uses dhcpv6-route-suppression-type;
     }
     leaf relay-agent-option-79 {
       description "Add the client MAC address to the Relay Forward header.";
       type empty;
     }
     list interface {
       key name;
       description "One or more interfaces";
       leaf name {
         description "Interface name";
         junos:must "((unique \"forwarding-options dhcp-relay dhcpv6 group <*> interface $$\" && !(any \"system services dhcp-local-server dhcpv6 group <*> interface $$\")))";
         junos:must-message "Interface used in other relay or server group";
         type union {
           type jt:interface-name;
           type string {
             pattern "<.*>|$.*";
           }
         }
       }
       uses apply-advanced;
       leaf upto {
         description "Interface up to";
         junos:must "(!(\".. .. interface $$\"))";
         junos:must-message "Range end point must not equal start";
         type union {
           type jt:interface-name;
           type string {
             pattern "<.*>|$.*";
           }
         }
       }
       leaf exclude {
         description "Exclude this interface range";
         type empty;
       }
       leaf trace {
         description "Enable tracing for this interface";
         junos:must "(!(\".. exclude\"))";
         junos:must-message "Cannot specify tracing with exclude";
         type empty;
       }
       container overrides {
         description "DHCPv6 override processing";
         junos:must "(!(\".. exclude\"))";
         junos:must-message "Cannot specify overrides with exclude";
         uses dhcpv6-override-relay-type;
       }
       container dynamic-profile {
         description "Dynamic profile to use";
         junos:must "(!(\".. exclude\"))";
         junos:must-message "Cannot specify dynamic-profile with exclude";
         uses dynamic-profile-type;
       }
       leaf service-profile {
         description "Dynamic profile to use for default service activation";
         type string {
           length "1 .. 128";
         }
       }
       leaf access-profile {
         description "Access profile to use for AAA services";
         junos:must "(\"access profile $$\")";
         junos:must-message "Matching access profile must be defined";
         junos:must "(!(\".. exclude\"))";
         junos:must-message "Cannot specify overrides with exclude";
         type string {
           length "1 .. 128";
         }
       }
       container short-cycle-protection {
         description "Short cycle lockout configuration";
         leaf lockout-min-time {
           description "Short cycle lockout time in seconds";
           type union {
             type string {
               pattern "<.*>|$.*";
             }
             type uint32 {
               range "1 .. 86400";
             }
           }
         }
         leaf lockout-max-time {
           description "Short cycle lockout time in seconds";
           type union {
             type string {
               pattern "<.*>|$.*";
             }
             type uint32 {
               range "1 .. 86400";
             }
           }
         }
       }
     }
     container lease-time-validation {
       presence "enable lease-time-validation";
       description "Configure lease time violation validation";
       uses apply-advanced;
       leaf lease-time-threshold {
         description "Threshold for lease time violation in seconds";
         units "seconds";
         type union {
           type string {
             pattern "<.*>|$.*";
           }
           type uint32 {
             range "60 .. 2147483647";
           }
         }
       }
       container violation-action {
         description "Lease time validation violation action";
         leaf drop {
           description "Drop dhcpv6 advertise and reply packets";
           type empty;
         }
       }
     }
     container remote-id-mismatch {
       description "DHCP client remote-id mismatch";
       presence "enable remote-id-mismatch";
       uses dhcp-remote-id-mismatch-type;
     }
     container server-match {
       description "Server match processing";
       uses apply-advanced;
       container default-action {
         description "Server match default action";
         uses server-match-action-choice;
       }
       container duid {
         description "Match duid processing";
         uses apply-advanced;
         container equals {
           description "Duid equals";
           uses server-match-v6-ascii-hex;
         }
         container starts-with {
           description "Duid starts with";
           uses server-match-v6-ascii-hex;
         }
       }
       list address {
         key name;
         ordered-by user;
         description "Server ipv6 address";
         leaf name {
           description "Server ipv6 address for matching";
           type jt:ipv6prefix;
         }
         uses apply-advanced;
         choice server-match-action-choice {
           case case_1 {
             leaf forward-only {
               description "Forward without subscriber services when a match is made";
               type empty;
             }
           }
           case case_2 {
             leaf create-relay-entry {
               description "Create relay entry and allow subscriber services";
               type empty;
             }
           }
         }
       }
     }
   }
   grouping dhcpv6-gp-active-sg-type {
     uses apply-advanced;
     leaf active-server-group {
       description "Name of DHCPv6 server group";
       junos:must "(\".. .. .. server-group $$\")";
       junos:must-message "Referenced group must be defined under [edit forwarding-options dhcp-relay dhcpv6 server-group]";
       type string {
         length "1 .. 64";
       }
     }
   }
   grouping dhcpv6-route-suppression-type {
     description "Suppress access-internal and/or access route addition";
     leaf access {
       description "Suppress access route addition";
       type empty;
     }
     leaf access-internal {
       description "Suppress access-internal route addition";
       type empty;
     }
   }
   grouping dual-stack-authentication-type {
     description "DHCP dual stack authentication";
     uses apply-advanced;
     leaf password {
       description "Username password to use";
       type string {
         length "1 .. 64";
       }
     }
     container username-include {
       description "Add username options";
       uses apply-advanced;
       leaf delimiter {
         description "Change delimiter/separator character";
         type string {
           length 1;
         }
       }
       leaf domain-name {
         description "Add domain name";
         type string {
           length "1 .. 64";
         }
       }
       leaf user-prefix {
         description "Add user defined prefix";
         type string {
           length "1 .. 64";
         }
       }
       leaf mac-address {
         description "Include MAC address";
         type empty;
       }
       leaf relay-agent-remote-id {
         description "Include the relay agent remote ID";
         type empty;
       }
       leaf logical-system-name {
         description "Include logical system name";
         type empty;
       }
       leaf routing-instance-name {
         description "Include routing instance name";
         type empty;
       }
       leaf relay-agent-interface-id {
         description "Include the relay agent interface ID";
         type empty;
       }
       leaf interface-name {
         description "Include interface name";
         type empty;
       }
       leaf interface-description {
         description "Include interface description";
         type enumeration {
           enum "device" {
             description "Add the device interface description";
           }
           enum "logical" {
             description "Add the logical interface description";
           }
         }
       }
       leaf circuit-type {
         description "Include circuit type";
         type empty;
       }
       leaf vlan-tags {
         description "Include the vlan tag(s)";
         type empty;
       }
     }
   }
   grouping dynamic-profile-type {
     description "Dynamic profile to use";
     uses apply-advanced;
     leaf dynamic-profile {
       description "Dynamic profile to use";
       junos:must "(\"dynamic-profiles $$\")";
       junos:must-message "Dynamic profile must be defined";
       type string {
         length "1 .. 80";
       }
     }
     choice dynamic-profile-type-choice {
       case case_1 {
         leaf use-primary {
           description "Dynamic profile to use on the primary interface";
           junos:must "(\"dynamic-profiles $$\")";
           junos:must-message "Dynamic profile must be defined";
           type string {
             length "1 .. 80";
           }
         }
       }
       case case_2 {
         container aggregate-clients {
           presence "enable aggregate-clients";
           description "Aggregate client profiles";
           uses apply-advanced;
           choice aggregate-type {
             case case_1 {
               leaf merge {
                 description "Merge the client dynamic profiles";
                 type empty;
               }
             }
             case case_2 {
               leaf replace {
                 description "Replace client dynamic profiles";
                 type empty;
               }
             }
           }
         }
       }
     }
   }
   grouping forward-only-to-rc-type {
     description "Forward DHCP packets without creating binding";
     uses apply-advanced;
     leaf logical-system {
       default "current";
       type string;
     }
     leaf routing-instance {
       default "current";
       type string;
     }
   }
   grouping jdhcp-dual-stack-protocol-mstr-type {
     description "Select family as protocol master";
     choice addr-fam {
       case case_1 {
         leaf inet {
           description "INET family has protocol master behavior";
           type empty;
         }
       }
       case case_2 {
         leaf inet6 {
           description "INET6 family has protocol master behavior";
           type empty;
         }
       }
     }
   }
   grouping jdhcp-duplicate-clients-in-subnet-type {
     description "Allow duplicate clients in a subnet";
     choice distinguish-with {
       case case_1 {
         leaf incoming-interface {
           description "Allow duplicate clients on different interfaces in a subnet";
           type empty;
         }
       }
       case case_2 {
         leaf option-82 {
           description "Allow duplicate clients using different option-82 options in a subnet";
           type empty;
         }
       }
     }
   }
   grouping jdhcp-interface-traceoptions-type {
     description "Interface trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "Interface trace categories";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
         }
       }
     }
   }
   grouping jdhcp-security-type {
     description "DHCP access security configuration";
     uses apply-advanced;
     leaf no-dhcp-snooping {
       description "Disable dhcp snooping";
       junos:must "(!(\"switch-options no-arp-trap \"))";
       junos:must-message "Cannot enable ARP inspection with no-arp-trap";
       type empty;
     }
     leaf arp-inspection {
       description "Enable dynamic ARP inspection";
       type empty;
     }
     leaf ip-source-guard {
       description "Enable IP source guard";
       junos:must "(!(any \".. group <*> overrides untrusted\"))";
       junos:must-message "Ip-source-guard and dhcp-security overrides untrusted cannot be configured together";
       type empty;
     }
     leaf no-dhcpv6-snooping {
       description "Disable DHCPv6 snooping";
       type empty;
     }
     leaf neighbor-discovery-inspection {
       description "Enable neighbor discovery inspection";
       type empty;
     }
     leaf ipv6-source-guard {
       description "Enable IPv6 source guard";
       junos:must "(!(any \".. group <*> overrides untrusted\"))";
       junos:must-message "Ipv6-source-guard and dhcp-security overrides untrusted cannot be configured together";
       type empty;
     }
     leaf light-weight-dhcpv6-relay {
       description "Enable light weight dhcpv6 relay";
       type empty;
     }
     list group {
       key name;
       ordered-by user;
       description "Define a DHCP security group for overriding defaults";
       uses ds-group;
     }
     container option-82 {
       description "DHCP option-82 processing for snooped packets";
       presence "enable option-82";
       uses security-option-82-type;
     }
     container dhcpv6-options {
       description "DHCPv6 option processing for snooped packets";
       presence "enable dhcpv6-options";
       uses security-dhcpv6-options-type;
     }
   }
   grouping ds-group {
     description "DHCP security groups";
     leaf name {
       description "Group name";
       type string {
         length "1 .. 64";
         junos:posix-pattern "^[A-Za-z0-9][_0-9A-Za-z-]*$";
         junos:pattern-message "Must be a non-reserved string of 64 characters or less";
       }
     }
     uses apply-advanced;
     container overrides {
       description "DHCP override processing";
       presence "enable overrides";
       uses ds-override-type;
     }
     list interface {
       key name;
       description "One or more interfaces";
       leaf name {
         description "Interface name";
         type union {
           type jt:interface-name;
           type string {
             pattern "<.*>|$.*";
           }
         }
       }
       uses apply-advanced;
       list static-ip {
         key name;
         ordered-by user;
         description "Static IP address configuration";
         uses ip-mac-static;
       }
       list static-ipv6 {
         key name;
         ordered-by user;
         description "Static IPv6 address configuration";
         uses ipv6-mac-static;
       }
     }
   }
   grouping ds-override-type {
     description "Dynamic ARP Inspection override processing";
     uses apply-advanced;
     leaf trusted {
       description "Make this trusted group of interfaces";
       junos:must "(!(\".. untrusted\"))";
       junos:must-message "Trusted and untrusted cannot be configured together";
       type empty;
     }
     leaf untrusted {
       description "Make this untrusted group of interfaces";
       junos:must "(!(\".. trusted\"))";
       junos:must-message "Trusted and untrusted cannot be configured together";
       type empty;
     }
     leaf no-option82 {
       description "Make this group of interfaces not to add option82";
       type empty;
     }
     leaf no-option37 {
       description "Make this group of interfaces not to add option37";
       type empty;
     }
     leaf no-option18 {
       description "Make this group of interfaces not to add option18";
       type empty;
     }
     leaf no-option16 {
       description "Make this group of interfaces not to add option16";
       type empty;
     }
     leaf no-option79 {
       description "Make this group of interfaces not to add option79";
       type empty;
     }
     leaf no-dhcpv6-options {
       description "Make this group of interfaces not to add any DHCPv6 options";
       type empty;
     }
   }
   grouping ip-mac-static {
     leaf name {
       description "IP address";
       type jt:ipaddr;
     }
     leaf mac {
       description "MAC address";
       type jt:mac-addr;
     }
   }
   grouping ipv6-mac-static {
     leaf name {
       description "IP address";
       type jt:ipv6addr;
     }
     leaf mac {
       description "MAC address";
       type jt:mac-addr;
     }
   }
   grouping jdhcp-traceoptions-type {
     description "Trace options for DHCP";
     uses apply-advanced;
     leaf no-remote-trace {
       description "Disable remote tracing";
       junos:must "(\"system tracing\")";
       junos:must-message "'no-remote-trace' is valid only when [system tracing] is configured";
       type empty;
     }
     container file {
       description "Trace file information";
       leaf filename {
         description "Name of file in which to write trace information";
         type string {
           length "1 .. 1024";
           junos:posix-pattern "![/ %]";
           junos:pattern-message "Must not contain '/', % or a space";
         }
       }
       leaf size {
         description "Maximum trace file size";
         type string;
       }
       leaf files {
         description "Maximum number of trace files";
         default "3";
         type union {
           type string {
             pattern "<.*>|$.*";
           }
           type uint32 {
             range "2 .. 1000";
           }
         }
       }
       choice world-readable-choice {
         leaf world-readable {
           description "Allow any user to read the log file";
           type empty;
         }
         leaf no-world-readable {
           description "Don't allow any user to read the log file";
           type empty;
         }
       }
       leaf match {
         description "Regular expression for lines to be logged";
         type jt:regular-expression;
       }
     }
     list flag {
       key name;
       ordered-by user;
       description "DHCP operations to include in debugging trace";
       leaf name {
         type enumeration {
           enum "state" {
             description "State-transition operations";
           }
           enum "packet" {
             description "Packet-decoding operations";
           }
           enum "flow" {
             description "Flow-decoding operations";
           }
           enum "packet-option" {
             description "DHCP option-decoding operations";
           }
           enum "dhcpv6-state" {
             description "State-transition operations for dhcpv6";
           }
           enum "dhcpv6-packet" {
             description "Packet-decoding operations for dhcpv6";
           }
           enum "dhcpv6-packet-option" {
             description "DHCP option-decoding operations for dhcpv6";
           }
           enum "all" {
             description "All operations";
           }
           enum "database" {
             description "Database operations";
           }
           enum "persistent" {
             description "Persitent file operations";
           }
           enum "lockout-db" {
             description "Lockout database operations";
           }
           enum "interface" {
             description "Interface operations";
           }
           enum "rtsock" {
             description "Routing socket operations";
           }
           enum "flow-notify" {
             description "Flow notification operations";
           }
           enum "io" {
             description "I/O operations";
           }
           enum "ha" {
             description "High Availability-related operations";
           }
           enum "ui" {
             description "User Interface operations";
           }
           enum "general" {
             description "Miscellaneous operations";
           }
           enum "fwd" {
             description "Firewall process operations";
           }
           enum "rpd" {
             description "Routing Protocol process operations";
           }
           enum "auth" {
             description "Authentication operations";
           }
           enum "profile" {
             description "Profile operations";
           }
           enum "session-db" {
             description "Session database operations";
           }
           enum "performance" {
             description "Performance measurement operations";
           }
           enum "statistics" {
             description "Baseline statistics operations";
           }
           enum "dhcpv6-io" {
             description "I/O operations for dhcpv6";
           }
           enum "dhcpv6-rpd" {
             description "Routing Protocol process operations for dhcpv6";
           }
           enum "dhcpv6-session-db" {
             description "Session database operations for dhcpv6";
           }
           enum "dhcpv6-general" {
             description "Miscellaneous operations for dhcpv6";
           }
           enum "liveness-detection" {
             description "Liveness detection operations";
           }
           enum "security-persistence" {
             description "Liveness detection operations";
           }
           enum "mclag" {
             description "Multichassis LAG";
           }
           enum "ra-guard" {
             description "DHCP RA guard option for dhcpv6";
           }
         }
       }
     }
   }
   grouping jdhcp-vendor-specific-type {
     description "Add vendor-specific option processing";
     uses apply-advanced;
     leaf host-name {
       description "Add router host name";
       type empty;
     }
     leaf location {
       description "Add location information expressed as interface name format";
       type empty;
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
             junos:posix-pattern "![/ %]";
             junos:pattern-message "Must not contain '/', % or a space";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container host-outbound-traffic {
       description "Host generated protocol packets";
       uses apply-advanced;
       leaf forwarding-class {
         description "Forwarding class name";
         type string {
           junos:posix-pattern "^.{1,64}$";
           junos:pattern-message "Must be string of 64 characters or less";
         }
       }
       leaf dot1p {
         description "Dot1p bits";
         type union {
           type string {
             pattern "<.*>|$.*";
           }
           type uint32 {
             range "0 .. 7";
           }
         }
       }
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     leaf ignore-stp-topology-change {
       description "Don't process stp topology change";
       type empty;
     }
     container multichassis-lag-replicate-state {
       presence "enable multichassis-lag-replicate-state";
       description "Enable multichassis lag replication";
       uses apply-advanced;
       leaf suppress-report {
         description "Enable mclag report suppression";
         type empty;
       }
     }
     leaf nexthop-hold-time {
       description "Nexthop hold time in milliseconds";
       units "milliseconds";
       type union {
         type string {
           pattern "<.*>|$.*";
         }
         type uint32 {
           range "1 .. 1000";
         }
       }
     }
   }
   grouping juniper-protocols-vlan {
     description "VLANs switch-options configuration";
     uses apply-advanced;
     container mac-table-size {
       junos:must "(!((\".. .. .. protocols vpls\" && \".. .. ..  instance-type virtual-switch\")))";
       junos:must-message "mac-table-size needs to be specified under switch-options for a virtual-switch instance";
       junos:must "(!(\".. .. .. .. vlans ${vlan} private-vlan\"))";
       junos:must-message "Switch-options configuration is not allowed on secondary VLANs";
       description "Size of MAC address forwarding table";
       uses apply-advanced;
       leaf limit {
         description "Maximum number of MAC addresses";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
         }
       }
     }
     container mac-ip-table-size {
       junos:must "(!(((\".. .. .. protocols vpls\" || \".. .. .. protocols evpn\") && \".. .. ..  instance-type virtual-switch\")))";
       junos:must-message "mac-ip-table-size needs to be specified under switch-options for a virtual-switch instance";
       description "Size of MAC+IP bindings table";
       uses apply-advanced;
       leaf limit {
         description "Maximum number of MAC+IP bindings";
         type union {
           type string {
             pattern "<.*>|$.*";
           }
           type uint32;
         }
       }
     }
     container interface-mac-limit {
       junos:must "(!((\".. .. .. protocols vpls\" && \".. .. ..  instance-type virtual-switch\")))";
       junos:must-message "interface-mac-limit needs to be specified under switch-options for a virtual-switch instance";
       junos:must "(!(\".. .. .. .. vlans ${vlan} private-vlan\"))";
       junos:must-message "Switch-options configuration is not allowed on secondary VLANs";
       description "Maximum MAC address learned per interface";
       uses apply-advanced;
       leaf limit {
         description "Maximum number of MAC addresses per interface";
         type union {
           type string {
             pattern "<.*>|$.*";
           }
           type uint32;
         }
       }
       leaf packet-action {
         description "Action when MAC limit is reached";
         type enumeration {
           enum "none" {
             description "Forward the packet";
           }
           enum "drop" {
             description "Drop packets and do not learn. Default is forward";
           }
           enum "log" {
             description "Do not drop the packet but generate an alarm, an SNMP trap or a system log entry";
           }
           enum "shutdown" {
             description "Disable the interface and generate an alarm, an SNMP trap or a system log entry";
           }
           enum "drop-and-log" {
             description "Drop the packet and generate an alarm, an SNMP trap or a system log entry";
           }
         }
       }
     }
     container interface-mac-ip-limit {
       description "Maximum number of MAC+IP bindings learned on the interface";
       uses apply-advanced;
       leaf limit {
         description "Maximum number of MAC+IP bindings per interface";
         type union {
           type string {
             pattern "<.*>|$.*";
           }
           type uint32;
         }
       }
     }
     container mac-move-limit {
       presence "enable mac-move-limit";
       junos:must "(!(\".. .. .. .. vlans ${vlan} private-vlan\"))";
       junos:must-message "Switch-options configuration is not allowed on secondary VLANs";
       description "Number of MAC movements allowed on this VLAN";
       uses apply-advanced;
       leaf limit {
         description "Number of MAC movements allowed on this VLAN";
         type union {
           type string {
             pattern "<.*>|$.*";
           }
           type uint32 {
             range "1 .. 4294967295";
           }
         }
       }
       leaf packet-action {
         description "Action to be taken in case the MAC movement limit is exceeded";
         default "drop";
         type enumeration {
           enum "none" {
             description "Take no action";
           }
           enum "drop" {
             description "Drop the packet and do not generate an alarm";
           }
           enum "log" {
             description "Do not drop the packet but generate an alarm, an SNMP trap, or a system log entry.";
           }
           enum "shutdown" {
             description "Disable the interface and generate an alarm, an SNMP trap, or a system log entry.";
           }
           enum "drop-and-log" {
             description "Drop the packet and generate an alarm, an SNMP trap, or a system log entry.";
           }
           enum "vlan-member-shutdown" {
             description "Disable the interface of this VLAN";
           }
         }
       }
       list interface {
         key name;
         ordered-by user;
         description "Interface that connect this site to the VPN";
         leaf name {
           description "Interface name";
           type union {
             type jt:interface-name;
             type string {
               pattern "<.*>|$.*";
             }
           }
         }
         uses apply-advanced;
         leaf action-priority {
           description "Blocking priority of this interface on mac move detection";
           junos:must "(!(\".. .. .. .. .. vlans ${vlan} private-vlan\"))";
           junos:must-message "Switch-options configuration is not allowed on interfaces which are part of secondary VLANs";
           type union {
             type string {
               pattern "<.*>|$.*";
             }
             type uint32 {
               range "0 .. 7";
             }
           }
         }
       }
     }
     leaf mac-table-aging-time {
       description "Delay for discarding MAC address if no updates are received";
       units "seconds";
       type union {
         type string {
           pattern "<.*>|$.*";
         }
         type uint32;
       }
     }
     leaf no-mac-learning {
       description "Disable dynamic MAC address learning";
       junos:must "(!((\".. .. .. protocols vpls\" && \".. .. ..  instance-type virtual-switch\")))";
       junos:must-message "no-mac-learning needs to be specified under switch-options for a virtual-switch instance";
       junos:must "(!(\".. .. .. .. vlans ${vlan} private-vlan\"))";
       junos:must-message "Switch-options configuration is not allowed on secondary VLANs";
       type empty;
     }
     leaf no-normalization {
       description "Disable vlan id normalization for interfaces";
       type empty;
     }
     leaf mac-statistics {
       description "Enable MAC address statistics";
       junos:must "(!((\".. .. .. protocols vpls\" && \".. .. ..  instance-type virtual-switch\")))";
       junos:must-message "mac-statistics needs to be specified under switch-options for a virtual-switch instance";
       junos:must "(!(\".. .. .. .. vlans ${vlan} private-vlan\"))";
       junos:must-message "Switch-options configuration is not allowed on secondary VLANs";
       type empty;
     }
     container static-rvtep-mac {
       description "Configure Static MAC and remote VxLAN tunnel endpoint entries";
       uses apply-advanced;
       list mac {
         key "mac_addr remote-vtep";
         description "Unicast MAC address";
         leaf mac_addr {
           type jt:mac-unicast;
         }
         leaf remote-vtep {
           description "Configure static remote VXLAN tunnel endpoints";
           type jt:ipaddr;
         }
       }
     }
     list interface {
       key name;
       ordered-by user;
       description "Interface that connect this site to the VPN";
       junos:must "(!((\".. .. .. protocols vpls\" && \".. .. ..  instance-type virtual-switch\")))";
       junos:must-message "interface needs to be specified under switch-options for a virtual-switch instance";
       leaf name {
         description "Interface name";
         junos:must "(((\".. .. .. interface $$\" || (\".. .. .. .. .. interface $$\" || \"interfaces $$-IFL family ethernet-switching vlan\")) || \"interfaces $$-IFL family ethernet-switching\"))";
         junos:must-message "Interface must be part of this routing instance";
         junos:must "((\".. .. .. interface $$\" || (\".. .. .. .. .. interface $$\" || (\".. .. .. .. interface $$\" || \"interfaces $$-IFL family ethernet-switching\"))))";
         junos:must-message "Interface must be part of this routing instance";
         type union {
           type jt:interface-name;
           type string {
             pattern "<.*>|$.*";
           }
         }
       }
       uses apply-advanced;
       container interface-mac-limit {
         junos:must "(!(\".. .. .. .. .. vlans ${vlan} private-vlan\"))";
         junos:must-message "Switch-options configuration is not allowed on interfaces which are part of secondary VLANs";
         description "Maximum number of MAC addresses learned on the interface";
         uses apply-advanced;
         leaf limit {
           description "Maximum number of MAC addresses per interface";
           type union {
             type string {
               pattern "<.*>|$.*";
             }
             type uint32;
           }
         }
         leaf disable {
           description "Disable interface for interface-mac-limit";
           type empty;
         }
         leaf packet-action {
           description "Action when MAC limit is reached";
           type enumeration {
             enum "none" {
               description "Forward the packet";
             }
             enum "drop" {
               description "Drop packets and do not learn. Default is forward";
             }
             enum "log" {
               description "Do not drop the packet but generate an alarm, an SNMP trap or a system log entry";
             }
             enum "shutdown" {
               description "Disable the interface and generate an alarm, an SNMP trap or a system log entry";
             }
             enum "drop-and-log" {
               description "Drop the packet and generate an alarm, an SNMP trap or a system log entry";
             }
           }
         }
       }
       container vpws-service-id {
         presence "enable vpws-service-id";
         description "Service-id for EVPN VPWS routing instance";
         uses apply-advanced;
         leaf local {
           description "Local EVPN VPWS service id";
           junos:must "(unique \".. .. .. interface <*> vpws-service-id local $$\")";
           junos:must-message "Unique Local SID can only be configured ";
           type union {
             type string {
               pattern "<.*>|$.*";
             }
             type uint32 {
               range "1 .. 16777215";
             }
           }
         }
         leaf remote {
           description "Remote EVPN VPWS service id";
           junos:must "(unique \".. .. .. interface <*> vpws-service-id remote $$\")";
           junos:must-message "Unique Remote SID can only be configured ";
           type union {
             type string {
               pattern "<.*>|$.*";
             }
             type uint32 {
               range "1 .. 16777215";
             }
           }
         }
       }
       leaf protect-interface {
         description "Name of protect interface";
         junos:must "(\"interfaces $$\")";
         junos:must-message "Interface must be part of this routing instance";
         junos:must "(!(\"interfaces ${inter_name} esi\"))";
         junos:must-message "ESI can not be configured for protect interface";
         type union {
           type jt:interface-name;
           type string {
             pattern "<.*>|$.*";
           }
         }
       }
       leaf action-priority {
         description "Blocking priority of this interface on mac move detection";
         junos:must "(!(\".. .. .. .. .. vlans ${vlan} private-vlan\"))";
         junos:must-message "Switch-options configuration is not allowed on interfaces which are part of secondary VLANs";
         type union {
           type string {
             pattern "<.*>|$.*";
           }
           type uint32 {
             range "0 .. 8";
           }
         }
       }
       leaf remote-site-id {
         description "Site identifier associated with this interface";
         junos:must "(!(\".. .. .. .. .. l2vpn-id\"))";
         junos:must-message "Remote site identifier is not valid for FEC 129 VPWS instances";
         type union {
           type string {
             pattern "<.*>|$.*";
           }
           type uint32 {
             range "1 .. 65534";
           }
         }
       }
       leaf target-attachment-identifier {
         description "FEC 129 VPWS target attachment identifier";
         junos:must "(\".. .. source-attachment-identifier\")";
         junos:must-message "Source attachment identifier configuration required for the containing site";
         junos:must "(unique \".. .. interface <*> target-attachment-identifier $$\")";
         junos:must-message "All interface target attachment identifiers must be unique within a site";
         type string {
           junos:posix-pattern "^([[:digit:].]){1,15}$|^([[:digit:]]){0,10}:([[:digit:].]){0,15}:([[:digit:]]){1,10}$";
           junos:pattern-message "
	Use fec129 AII type 1 format with just <AC-ID> or    
	fec129 AII type 2 format <Global-ID>:<Prefix>:<AC-ID> where    
	<Global-ID> is a value between 0..4294967295,    
	<Prefix> is a value between 0..4294967295 or a valid IP address,    
	<AC-ID> is a value between 1..4294967295 (or a valid IP address for AII type 1).    
	e.g. 1, 0.0.0.1, 0:0:1, 1:2:3, 1:2.2.2.2:3, ::1, 1::2, :1:2";
         }
       }
       leaf flow-label-transmit {
         description "Advertise capability to push Flow Label in transmit direction to remote PE";
         junos:must "(\".. .. source-attachment-identifier\")";
         junos:must-message "Source attachment identifier configuration required for the containing site";
         type empty;
       }
       leaf flow-label-receive {
         description "Advertise capability to push Flow Label in receive direction to remote PE";
         junos:must "(\".. .. source-attachment-identifier\")";
         junos:must-message "Source attachment identifier configuration required for the containing site";
         type empty;
       }
       leaf encapsulation-type {
         description "Encapsulation type for VPN";
         type enumeration {
           enum "atm-aal5" {
             description "ATM AAL/5 encapsulation";
           }
           enum "atm-cell" {
             description "ATM port promiscuous mode cell encapsulation";
           }
           enum "atm-cell-port-mode" {
             description "ATM port promiscuous mode cell encapsulation";
           }
           enum "atm-cell-vp-mode" {
             description "ATM VP promiscuous mode cell encapsulation";
           }
           enum "atm-cell-vc-mode" {
             description "ATM non-promiscuous cell encapsulation";
           }
           enum "frame-relay" {
             description "Frame Relay encapsulation";
           }
           enum "ppp" {
             description "PPP encapsulation";
           }
           enum "cisco-hdlc" {
             description "Cisco-compatible HDLC encapsulation";
           }
           enum "ethernet-vlan" {
             description "Ethernet VLAN encapsulation";
           }
           enum "ethernet" {
             description "Ethernet encapsulation";
           }
           enum "interworking" {
             description "Layer 2.5 interworking VPN";
           }
           enum "frame-relay-port-mode" {
             description "Frame Relay port mode encapsulation";
           }
           enum "satop-t1" {
             description "SATOP-T1 based Layer 2 VPN";
           }
           enum "satop-e1" {
             description "SATOP-E1 based Layer 2 VPN";
           }
           enum "satop-t3" {
             description "SATOP-T3 based Layer 2 VPN";
           }
           enum "satop-e3" {
             description "SATOP-E3 based Layer 2 VPN";
           }
           enum "cesop" {
             description "CESOP based Layer 2 VPN";
           }
         }
       }
       leaf ignore-encapsulation-mismatch {
         description "Allow different encapsulation types on local and remote end";
         type empty;
       }
       leaf mtu {
         description "MTU to be advertised to the remote end";
         type union {
           type string {
             pattern "<.*>|$.*";
           }
           type uint16 {
             range "512 .. 65535";
           }
         }
       }
       leaf ignore-mtu-mismatch {
         description "Allow different MTU values on local and remote end";
         type empty;
       }
       choice cword {
         case case_1 {
           leaf control-word {
             description "Adds control-word to the Layer 2 encapsulation";
             type empty;
           }
         }
         case case_2 {
           leaf no-control-word {
             description "Disables control-word to the Layer 2 encapsulation";
             type empty;
           }
         }
       }
       leaf pseudowire-status-tlv {
         description "Send pseudowire status TLV";
         type empty;
       }
       container oam {
         description "OAM Configuration for VPN";
         uses apply-advanced;
         leaf ping-interval {
           description "Time interval between ping messages";
           default "60";
           units "seconds";
           type union {
             type string {
               pattern "<.*>|$.*";
             }
             type uint16 {
               range "30 .. 3600";
             }
           }
         }
         leaf ping-multiplier {
           description "Number of ping reply missed before declaring BFD down";
           type union {
             type string {
               pattern "<.*>|$.*";
             }
             type uint8 {
               range "1 .. 5";
             }
           }
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
         }
       }
       leaf community {
         description "Community associated with this interface";
         type string;
       }
       list static-mac {
         key name;
         ordered-by user;
         description "Static MAC addresses assigned to this interface";
         junos:must "(!(\".. .. .. .. .. vlans ${vlan} private-vlan\"))";
         junos:must-message "Switch-options configuration is not allowed on interfaces which are part of secondary VLANs";
         leaf name {
           description "MAC address";
           junos:must "((!(\".. .. .. .. vlan-id all\") || all \".. vlan-id <*>\"))";
           junos:must-message " Specify vlan-id for qualified learning ";
           type jt:mac-addr;
         }
         uses apply-advanced;
         list vlan-id {
           key name;
           ordered-by user;
           description "VLAN ID of learning VLAN";
           junos:must "(\".. .. .. .. vlan-id all\")";
           junos:must-message "'vlan-id all' has to be configured for the bridging domain";
           leaf name {
             description "Learning VLAN";
             type union {
               type string {
                 pattern "<.*>|$.*";
               }
               type uint32 {
                 range "0 .. 4094";
               }
             }
           }
           uses apply-advanced;
         }
       }
       container interface-mac-ip-limit {
         description "Maximum number of MAC+IP bindings learned on the interface";
         uses apply-advanced;
         leaf limit {
           description "Maximum number of MAC+IP bindings per interface";
           type union {
             type string {
               pattern "<.*>|$.*";
             }
             type uint32;
           }
         }
       }
       leaf no-mac-learning {
         description "Disable dynamic MAC address learning";
         junos:must "(!(\".. .. .. .. .. vlans ${vlan} private-vlan\"))";
         junos:must-message "Switch-options configuration is not allowed on interfaces which are part of secondary VLANs";
         type empty;
       }
       leaf mac-pinning {
         description "Enable MAC pinning";
         type empty;
       }
       leaf description {
         description "Text description";
         type string;
       }
       leaf persistent-learning {
         description "Enable persistent MAC learning on this interface";
         junos:must "(!(\"switch-options mac-table-aging-time \"))";
         junos:must-message "Persistent learning can not co-exist with mac-table-aging-time";
         type empty;
       }
     }
     container traceoptions {
       description "Trace options for this bridge domain";
       uses apply-advanced;
       leaf no-remote-trace {
         description "Disable remote tracing";
         junos:must "(\"system tracing\")";
         junos:must-message "'no-remote-trace' is valid only when [system tracing] is configured";
         type empty;
       }
       container file {
         description "Trace file information";
         leaf filename {
           description "Name of file in which to write trace information";
           type string {
             length "1 .. 1024";
             junos:posix-pattern "![/ %]";
             junos:pattern-message "Must not contain '/', % or a space";
           }
         }
         leaf size {
           description "Maximum trace file size";
           type string;
         }
         leaf files {
           description "Maximum number of trace files";
           default "3";
           type union {
             type string {
               pattern "<.*>|$.*";
             }
             type uint32 {
               range "2 .. 1000";
             }
           }
         }
         choice world-readable-choice {
           leaf world-readable {
             description "Allow any user to read the log file";
             type empty;
           }
           leaf no-world-readable {
             description "Don't allow any user to read the log file";
             type empty;
           }
         }
         leaf match {
           description "Regular expression for lines to be logged";
           type jt:regular-expression;
         }
       }
       leaf level {
         description "Level of debugging output";
         default "error";
         type enumeration {
           enum "error" {
             description "Match error conditions";
           }
           enum "warning" {
             description "Match warning messages";
           }
           enum "notice" {
             description "Match conditions that should be handled specially";
           }
           enum "info" {
             description "Match informational messages";
           }
           enum "verbose" {
             description "Match verbose messages";
           }
           enum "all" {
             description "Match all levels";
           }
         }
       }
       list flag {
         key name;
         ordered-by user;
         description "Type of operation or event to include in trace";
         leaf name {
           type enumeration {
             enum "configuration" {
               description "Configuration operations";
             }
             enum "routing-socket" {
               description "Routing socket operations";
             }
             enum "interface-device" {
               description "Interface device operations";
             }
             enum "interface-logical" {
               description "Logical interface operations";
             }
             enum "interface-family" {
               description "Interface family operations";
             }
             enum "learning-domain" {
               description "Learning domain operations";
             }
             enum "ipc" {
               description "Inter-process communications operations";
             }
             enum "mac-learning" {
               description "MAC address learning operations";
             }
             enum "initialization" {
               description "Initialization operations";
             }
             enum "flood-next-hop" {
               description "Flood next hop operations";
             }
             enum "storm-control" {
               description "Storm-control";
             }
             enum "unknown-unicast-forwarding" {
               description "Trace unknown unicast forwarding events";
             }
             enum "all" {
               description "All operations";
             }
           }
         }
       }
     }
   }
   grouping override-type {
     description "DHCP override processing";
     uses apply-advanced;
     leaf no-unicast-replies {
       description "Overwrite unicast bit in incoming packet, when present";
       junos:must "(!(\".. layer2-unicast-replies\"))";
       junos:must-message "no-unicast-replies cannot be configured with layer2-unicast-replies";
       type empty;
     }
     choice allow-snooped-clients-choice {
       leaf allow-snooped-clients {
         description "Allow client creation from snooped PDUs";
         type empty;
       }
       leaf no-allow-snooped-clients {
         description "Don't allow client creation from snooped PDUs";
         type empty;
       }
     }
     leaf allow-no-end-option {
       description "Allow packets without end-of-option";
       type empty;
     }
     leaf always-write-giaddr {
       description "Overwrite existing 'giaddr' field, when present";
       type empty;
     }
     container always-write-option-82 {
       description "Overwrite existing value of option 82, when present";
       presence "enable always-write-option-82";
       uses write-option-82-type;
     }
     leaf user-defined-option-82 {
       description "Set user defined description for option-82";
       type string {
         length "1 .. 252";
       }
     }
     leaf layer2-unicast-replies {
       description "Do not broadcast client responses";
       junos:must "(!(\".. no-unicast-replies\"))";
       junos:must-message "layer2-unicast-replies cannot be configured with no-unicast-replies";
       type empty;
     }
     leaf trust-option-82 {
       description "Trust options-82 option";
       type empty;
     }
     leaf delay-authentication {
       description "Delay subscriber authentication in DHCP protocol processing until request packet";
       type empty;
     }
     leaf disable-relay {
       description "Disable DHCP relay processing";
       type empty;
     }
     leaf no-bind-on-request {
       description "Do not bind if stray DHCP request is received";
       type empty;
     }
     leaf interface-client-limit {
       description "Limit the number of client allowed on an interface";
       type union {
         type string {
           pattern "<.*>|$.*";
         }
         type uint32 {
           range "1 .. 500000";
         }
       }
     }
     leaf no-arp {
       description "Disable DHCP ARP table population";
       status deprecated;
       junos:must "((!(\".. route-suppression destination\") && !(\".. route-suppression access-internal\")))";
       junos:must-message "Cannot specify route-suppression with overrides no-arp";
       type empty;
     }
     leaf bootp-support {
       description "Allows relay of bootp req and reply";
       type empty;
     }
     leaf dual-stack {
       description "Dual stack group to use.";
       type string {
         length "1 .. 64";
       }
     }
     container client-discover-match {
       presence "enable client-discover-match";
       description "Use secondary match criteria for DISCOVER PDU";
       choice match-with {
         case case_1 {
           leaf option60-and-option82 {
             description "Use option 60 and option 82";
             type empty;
           }
         }
         case case_2 {
           leaf incoming-interface {
             description "Use incoming interface";
             type empty;
           }
         }
       }
     }
     container proxy-mode {
       presence "enable proxy-mode";
       description "Put the relay in proxy mode";
     }
     leaf asymmetric-lease-time {
       description "Use a reduced lease time for the client. In seconds";
       units "seconds";
       type union {
         type string {
           pattern "<.*>|$.*";
         }
         type uint32 {
           range "600 .. 86400";
         }
       }
     }
     container replace-ip-source-with {
       description "Replace IP source address in request and release packets";
       choice replacement-type {
         case case_1 {
           leaf giaddr {
             description "Replace IP source address with giaddr";
             type empty;
           }
         }
       }
     }
     leaf send-release-on-delete {
       description "Always send RELEASE to the server when a binding is deleted";
       type empty;
     }
     leaf apply-secondary-as-giaddr {
       description "Enable DHCP relay to use secondary gateway ip for relay interfaces";
       type empty;
     }
     leaf relay-source {
       description "Interface for relay source";
       type union {
         type jt:interface-name;
         type string {
           pattern "<.*>|$.*";
         }
       }
     }
     leaf delete-binding-on-renegotiation {
       description "Delete binding on rengotiation";
       type empty;
     }
   }
   grouping relay-active-leasequery-v4-type {
     description "Configure active leasequery";
     uses apply-advanced;
     leaf topology-discover {
       description "Topology discovery";
       junos:must "(\".. peer-address\")";
       junos:must-message "Must configure [peer-address] to configure topology-discover";
       type empty;
     }
     list peer-address {
       key name;
       ordered-by user;
       description "Server ip address";
       leaf name {
         description "Peer ip address";
         type jt:ipaddr;
       }
       uses apply-advanced;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
   }
   grouping relay-active-leasequery-v6-type {
     description "Configure active leasequery";
     uses apply-advanced;
     leaf topology-discover {
       description "Topology discovery";
       junos:must "(\".. peer-address\")";
       junos:must-message "Must configure [peer-address] to configure topology-discover";
       type empty;
     }
     leaf timeout {
       description "Read/write timeout in seconds";
       default "120";
       units "seconds";
       type union {
         type string {
           pattern "<.*>|$.*";
         }
         type uint32 {
           range "10 .. 3600";
         }
       }
     }
     leaf idle-timeout {
       description "Idle timeout in seconds";
       default "60";
       units "seconds";
       type union {
         type string {
           pattern "<.*>|$.*";
         }
         type uint32 {
           range "10 .. 3600";
         }
       }
     }
     list peer-address {
       key name;
       ordered-by user;
       description "Peer ipv6 address";
       leaf name {
         description "Peer ipv6 address";
         type jt:ipv6addr;
       }
       uses apply-advanced;
     }
   }
   grouping relay-bulk-leasequery-v4-type {
     junos:must "(\".. overrides always-write-option-82\")";
     junos:must-message "Must configure [overrides always-write-option-82] to overwrite circuit-id for bulk-leasequery";
     junos:must "((\".. relay-option-82 circuit-id\" && !((\".. relay-option-82 circuit-id use-interface-description\" || \".. relay-option-82 circuit-id require-interface-description\"))))";
     junos:must-message "Must configure [relay-option-82 circuit-id] without description to insert circuit-id for bulk-leasequery";
     description "Configure bulk leasequery";
     uses apply-advanced;
     leaf attempts {
       description "Number of retry attempts";
       default "360";
       type union {
         type string {
           pattern "<.*>|$.*";
         }
         type uint32 {
           range "1 .. 720";
         }
       }
     }
     leaf timeout {
       description "Number of seconds";
       default "10";
       units "seconds";
       type union {
         type string {
           pattern "<.*>|$.*";
         }
         type uint32 {
           range "1 .. 10";
         }
       }
     }
   }
   grouping relay-bulk-leasequery-v6-type {
     junos:must "(\".. relay-agent-interface-id\")";
     junos:must-message "Must configure [relay-agent-interface-id] to insert interface-id for bulk-leasequery";
     description "Configure bulk leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
     container trigger {
       description "Trigger for bulk leasequery";
       leaf automatic {
         description "Trigger automatically";
         type empty;
       }
     }
   }
   grouping relay-leasequery-type {
     description "Configure leasequery";
     uses apply-advanced;
     leaf attempts {
       description "Number of retry attempts";
       default "6";
       type union {
         type string {
           pattern "<.*>|$.*";
         }
         type uint32 {
           range "1 .. 10";
         }
       }
     }
     leaf timeout {
       description "Number of seconds";
       default "10";
       units "seconds";
       type union {
         type string {
           pattern "<.*>|$.*";
         }
         type uint32 {
           range "1 .. 10";
         }
       }
     }
   }
   grouping relay-option-60-type-group {
     description "DHCP option-60 processing";
     uses apply-advanced;
     container vendor-option {
       description "Add vendor option";
       uses apply-advanced;
       container equals {
         description "Option 60 equals";
         uses relay-option-60-match-group;
       }
       container not-equals {
         description "Option 60 does not equal";
         status deprecated;
         uses relay-option-60-match-group;
       }
       container starts-with {
         description "Option 60 starts with";
         uses relay-option-60-match-group;
       }
       choice server-group-choice {
         case case_1 {
           leaf default-relay-server-group {
             description "Name of DHCP relay server group when match is not made";
             junos:must "(\".. .. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-group {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-60-type-top {
     description "DHCP option-60 processing";
     uses apply-advanced;
     container vendor-option {
       description "Add vendor option";
       uses apply-advanced;
       container equals {
         description "Option 60 equals";
         uses relay-option-60-match-top;
       }
       container not-equals {
         description "Option 60 does not equal";
         status deprecated;
         uses relay-option-60-match-top;
       }
       container starts-with {
         description "Option 60 starts with";
         uses relay-option-60-match-top;
       }
       choice server-group-choice {
         case case_1 {
           leaf default-relay-server-group {
             description "Name of DHCP relay server group when match is not made";
             junos:must "(\".. .. .. server-group $$\")";
             junos:must-message "Referenced group must be defined under [edit dhcp-relay server-group]";
             type string {
               length "1 .. 64";
             }
           }
         }
         case case_2 {
           leaf default-local-server-group {
             description "Name of DHCP local server group when match is not made";
             junos:must "(\".. .. .. .. .. system services dhcp-local-server group $$\")";
             junos:must-message "Referenced group must be defined under [edit system services dhcp-local-server group]";
             type string {
               length "1 .. 64";
             }
           }
         }
         case case_3 {
           leaf drop {
             description "Discard when a match is not made";
             type empty;
           }
         }
         case case_4 {
           leaf forward-only {
             description "Forward without subscriber services when a match is not made";
             type empty;
           }
         }
       }
     }
   }
   grouping relay-option-60-match-top {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "(\".. .. .. .. .. server-group $$\")";
             junos:must-message "Referenced group must be defined under [edit forwarding options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "(\".. .. .. .. .. server-group $$\")";
             junos:must-message "Referenced group must be defined under [edit forwarding-options dhcp-relay server-group]";
             type string {
               length "1 .. 64";
             }
           }
         }
         case case_2 {
           leaf local-server-group {
             description "Name of DHCP local server group when match is made";
             junos:must "(\".. .. .. .. .. .. .. system services dhcp-local-server group $$\")";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-option-82-type {
     description "DHCP option-82 processing";
     uses apply-advanced;
     container circuit-id {
       presence "enable circuit-id";
       description "Add circuit identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       container vlan-id-only {
         presence "enable vlan-id-only";
         junos:must "(!((\".. include-irb-and-l2\" || (\".. keep-incoming-circuit-id\" || (\".. user-defined\" || (\".. no-vlan-interface-name\" || (\".. use-interface-description\" || (\".. use-vlan-id\" || (\".. prefix\" || \".. require-interface-description\")))))))))";
         junos:must-message "Vlan-id-only cannot be clubbed along with any other option-82 knob";
         description "Use only VLAN id";
         uses apply-advanced;
       }
       leaf no-vlan-interface-name {
         description "Not include vlan or interface name";
         type empty;
       }
       leaf include-irb-and-l2 {
         description "Include IRB and L2 interface name";
         type empty;
       }
       leaf user-defined {
         description "Include user defined string";
         junos:must "(!((\".. include-irb-and-l2\" || (\".. keep-incoming-circuit-id\" || (\".. no-vlan-interface-name\" || (\".. use-interface-description\" || (\".. use-vlan-id\" || (\".. prefix\" || \".. require-interface-description\"))))))))";
         junos:must-message "The user defined description for option 82 must be defined in order to see the usage and doesnt coexist with prefix";
         type empty;
       }
       leaf keep-incoming-circuit-id {
         description "Keep incoming circuit identifier";
         type empty;
       }
     }
     container remote-id {
       presence "enable remote-id";
       description "Add remote identifier";
       uses apply-advanced;
       container prefix {
         description "Add prefix to circuit/interface-id or remote-id";
         uses apply-advanced;
         leaf host-name {
           description "Add router host name to circuit / interface-id or remote-id";
           type empty;
         }
         leaf logical-system-name {
           description "Add logical system name to circuit / interface-id or remote-id";
           type empty;
         }
         leaf routing-instance-name {
           description "Add routing instance name to circuit / interface-id or remote-id";
           type empty;
         }
       }
       leaf use-interface-description {
         description "Use interface description instead of circuit identifier";
         junos:must "(!(\".. require-interface-description\"))";
         junos:must-message "use-interface-description may not be set with require-interface-desciption";
         type enumeration {
           enum "logical" {
             description "Use the logical interface description";
           }
           enum "device" {
             description "Use the device interface description";
           }
         }
       }
       leaf use-vlan-id {
         description "Use VLAN id instead of name";
         junos:must "((!(\".. no-vlan-interface-name\") && (!(\".. use-interface-description\") && !(\".. require-interface-description\"))))";
         junos:must-message "Vlan-tag cannot be added as no-vlan-interface-name or interface-description is configured";
         type empty;
       }
       leaf no-vlan-interface-name {
         description "Not include vlan or interface name";
         type empty;
       }
       leaf include-irb-and-l2 {
         description "Include IRB and L2 interface name";
         type empty;
       }
       container hostname-only {
         presence "enable hostname-only";
         junos:must "(!((\".. include-irb-and-l2\" || (\".. keep-incoming-remote-id\" || (\".. no-vlan-interface-name\" || (\".. use-interface-description\" || (\".. use-vlan-id\" || (\".. prefix\" || \".. use-string\"))))))))";
         junos:must-message "Hostname-only cannot be clubbed with any other sub-option";
         description "Include hostname only";
         uses apply-advanced;
       }
       leaf keep-incoming-remote-id {
         description "Keep incoming remote identifier";
         type empty;
       }
       leaf use-string {
         description "Use raw string instead of the default remote id";
         junos:must "(!((\".. use-interface-description\" || (\".. require-interface-description\" || (\".. include-irb-and-l2\" || (\".. keep-incoming-circuit-id\" || (\".. no-vlan-interface-name\" || \".. use-vlan-id\")))))))";
         junos:must-message "use-string can only coexist with prefix";
         type string;
       }
     }
     leaf server-id-override {
       description "Add link-selection and server-id sub-options on packets to server";
       type empty;
     }
     container vendor-specific {
       description "Add vendor-specific information";
       uses jdhcp-vendor-specific-type;
     }
   }
   grouping relay-v4-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding dhcp-relay server-group]";
             type string {
               length "1 .. 64";
             }
           }
         }
         case case_2 {
           leaf local-server-group {
             description "Name of DHCP local server group when match is made";
             junos:must "((\".. .. .. .. .. .. .. .. system services dhcp-local-server group $$\" || (\".. .. .. .. .. .. .. system services dhcp-local-server group $$\" || (\".. .. .. .. .. .. system services dhcp-local-server group $$\" || \".. .. .. .. .. system services dhcp-local-server group $$\"))))";
             junos:must-message "Referenced group must be defined under [edit system services dhcp-local-server group]";
             type string {
               length "1 .. 64";
             }
           }
         }
         case case_3 {
           leaf drop {
             description "Discard when a match is made";
             type empty;
           }
         }
         case case_4 {
           leaf forward-only {
             description "Forward without subscriber services when a match is made";
             type empty;
           }
         }
       }
     }
   }
   grouping relay-v6-option-ascii-hex {
     uses apply-advanced;
     list ascii {
       key name;
       description "ASCII string";
       leaf name {
         description "ASCII string";
         type string {
           length "1 .. 256";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-group-choice {
         case case_1 {
           leaf relay-server-group {
             description "Name of DHCP relay server group when match is made";
             junos:must "((\".. .. .. .. .. .. server-group $$\" || (\".. .. .. .. .. server-group $$\" || (\".. .. .. .. server-group $$\" || \".. .. .. server-group $$\"))))";
             junos:must-message "Referenced group must be defined under [edit forwarding options dhcp-relay dhcpv6 server-group]";
             type string {
               length "1 .. 64";
             }
           }
         }
         case case_2 {
           leaf drop {
             description "Discard when a match is made";
             type empty;
           }
         }
         case case_3 {
           leaf forward-only {
             description "Forward without subscriber services when a match is made";
             type empty;
           }
         }
       }
     }
   }
   grouping security-dhcpv6-options-type {
     description "Configure DHCPv6 options";
     uses apply-advanced;
     container option-37 {
       presence "enable option-37";
       description "Configure DHCPv6 remote identifier option";
       uses apply-advanced;
       container prefix {
         description "Configure DHCPv6 remote identifier prefix";
         uses apply-advanced;
         leaf host-name {
           description "Prefix router host name to DHCPv6 remote identifier";
           type empty;
         }
         leaf logical-system-name {
           description "Prefix logical system name to DHCPv6 remote identifier";
           type empty;
         }
         leaf routing-instance-name {
           description "Prefix routing instance name to DHCPv6 remote identifier";
           type empty;
         }
         leaf vlan-name {
           description "Prefix vlan name to DHCPv6 remote identifier";
           type empty;
         }
         leaf vlan-id {
           description "Prefix vlan tag to DHCPv6 remote identifier";
           type empty;
         }
       }
       leaf use-interface-mac {
         description "Add incoming interface's MAC address to DHCPv6 remote identifier";
         type empty;
       }
       leaf use-interface-index {
         description "Add interface index to DHCPv6 remote identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 remote identifier";
         type enumeration {
           enum "logical" {
             description "Use the logical interface description";
           }
           enum "device" {
             description "Use the device interface description";
           }
         }
       }
       leaf use-string {
         description "Add custom string to DHCPv6 remote identifier";
         junos:must "(!(\".. use-interface-description\"))";
         junos:must-message "use-string and use-interface-description cannot be configured together";
         type string;
       }
     }
     container option-18 {
       presence "enable option-18";
       description "Configure DHCPv6 interface identifier option";
       uses apply-advanced;
       container prefix {
         description "Configure DHCPv6 interface identifier prefix";
         uses apply-advanced;
         leaf host-name {
           description "Prefix router host name to DHCPv6 interface identifier";
           type empty;
         }
         leaf logical-system-name {
           description "Prefix logical system name to DHCPv6 interface identifier";
           type empty;
         }
         leaf routing-instance-name {
           description "Prefix routing instance name to DHCPv6 interface identifier";
           type empty;
         }
         leaf vlan-name {
           description "Prefix vlan name to DHCPv6 interface identifier";
           type empty;
         }
         leaf vlan-id {
           description "Prefix vlan tag to DHCPv6 interface identifier";
           type empty;
         }
       }
       leaf use-interface-mac {
         description "Add incoming interface's MAC address to DHCPv6 circuit identifier";
         type empty;
       }
       leaf use-interface-index {
         description "Add interface index to DHCPv6 interface identifier";
         type enumeration {
           enum "logical" {
             description "Use the logical interface index";
           }
           enum "device" {
             description "Use the device interface index";
           }
         }
       }
       leaf use-interface-name {
         description "Add interface name to DHCPv6 remote identifier";
         type enumeration {
           enum "logical" {
             description "Use the logical interface name";
           }
           enum "device" {
             description "Use the device interface name";
           }
         }
       }
       leaf use-interface-description {
         description "Add interface description to DHCPv6 interface identifier";
         type enumeration {
           enum "logical" {
             description "Use the logical interface description";
           }
           enum "device" {
             description "Use the device interface description";
           }
         }
       }
       leaf use-string {
         description "Add custom string to DHCPv6 interface identifier";
         junos:must "(!(\".. use-interface-description\"))";
         junos:must-message "use-string and use-interface-description cannot be configured together";
         type string;
       }
     }
     container option-16 {
       presence "enable option-16";
       description "Configure DHCPv6 vendor class identifier option. Overwrite if exists";
       uses apply-advanced;
       leaf use-string {
         description "Add custom string to DHCPv6 vendor identifier";
         type string;
       }
     }
     leaf option-79 {
       description "Configure DHCPv6 client link layer address option";
       junos:must "(\".. .. light-weight-dhcpv6-relay\")";
       junos:must-message "Option-79 can be configured only on LDRAs";
       type empty;
     }
   }
   grouping security-option-82-type {
     description "DHCP option-82 processing";
     uses apply-advanced;
     container circuit-id {
       presence "enable circuit-id";
       description "Configure DHCP option 82 circuit id";
       uses apply-advanced;
       container prefix {
         description "Configure DHCP option 82 circuit id prefix";
         uses apply-advanced;
         leaf host-name {
           description "Add router host name to DHCP option-82 circuit id";
           type empty;
         }
         leaf logical-system-name {
           description "Add logical system name to DHCP option-82 circuit id";
           type empty;
         }
         leaf routing-instance-name {
           description "Add routing instance name to DHCP option-82 circuit id";
           type empty;
         }
       }
       leaf use-interface-description {
         description "Use interface description instead of circuit identifier";
         type enumeration {
           enum "logical" {
             description "Use the logical interface description";
           }
           enum "device" {
             description "Use the device interface description";
           }
         }
       }
       leaf use-vlan-id {
         description "Use VLAN id instead of name";
         type empty;
       }
     }
     container remote-id {
       presence "enable remote-id";
       description "Configure DHCP option 82 remote id";
       uses apply-advanced;
       leaf host-name {
         description "Add router host name to DHCP option-82 remote id";
         type empty;
       }
       leaf use-interface-description {
         description "Use interface description instead of interface name";
         type enumeration {
           enum "logical" {
             description "Use the logical interface description";
           }
           enum "device" {
             description "Use the device interface description";
           }
         }
       }
       leaf use-string {
         description "Use raw string instead of the default remote id";
         junos:must "(!(\".. use-interface-description\"))";
         junos:must-message "use-string and use-interface-description cannot be configured together";
         type string;
       }
       leaf mac {
         description "Add chassis MAC Address to DHCP option-82 remote id";
         type empty;
       }
     }
     container vendor-id {
       presence "enable vendor-id";
       description "Configure DHCP option 82 vendor id";
       uses apply-advanced;
       leaf use-string {
         description "Use raw string instead of the default vendor id";
         default "Juniper Networks";
         type string;
       }
     }
   }
   grouping server-group-type {
     uses apply-advanced;
     list server-group {
       key name;
       ordered-by user;
       description "One or more server groups";
       leaf name {
         description "Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping server-match-action-choice {
     uses apply-advanced;
     choice v4-action-choice {
       case case_1 {
         leaf forward-only {
           description "Forward without subscriber services";
           type empty;
         }
       }
       case case_2 {
         leaf create-relay-entry {
           description "Create relay entry and allow subscriber services";
           type empty;
         }
       }
     }
   }
   grouping server-match-v6-ascii-hex {
     uses apply-advanced;
     list ascii {
       key name;
       description "ASCII string";
       leaf name {
         description "ASCII string";
         type string {
           length "1 .. 256";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
     list hexadecimal {
       key name;
       description "Hexadecimal string";
       leaf name {
         description "Hexadecimal string";
         type string {
           length "1 .. 512";
           junos:posix-pattern "^[[:xdigit:]]+$";
           junos:pattern-message "Must be hexadecimal digits (0-9, a-f, A-F)";
         }
       }
       uses apply-advanced;
       choice server-match-action-choice {
         case case_1 {
           leaf forward-only {
             description "Forward without subscriber services when a match is made";
             type empty;
           }
         }
         case case_2 {
           leaf create-relay-entry {
             description "Create relay entry and allow subscriber services";
             type empty;
           }
         }
       }
     }
   }
   grouping v6-relay-option-interface-id-type {
     description "Interface ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 circuit-id for interface-id";
       presence "enable use-option-82";
       uses v6-relay-option-cid-rid-action;
     }
     container keep-incoming-interface-id {
       description "Keep incoming interface identifier";
       presence "enable keep-incoming-interface-id";
       uses v6-relay-option-cid-rid-action;
     }
   }
   grouping v6-relay-option-cid-rid-action {
     uses apply-advanced;
     leaf strict {
       description "Drop packet if id not present";
       type empty;
     }
   }
   grouping v6-relay-option-remote-id-type {
     description "Remote ID processing";
     uses apply-advanced;
     container prefix {
       description "Add prefix to circuit/interface-id or remote-id";
       uses apply-advanced;
       leaf host-name {
         description "Add router host name to circuit / interface-id or remote-id";
         type empty;
       }
       leaf logical-system-name {
         description "Add logical system name to circuit / interface-id or remote-id";
         type empty;
       }
       leaf routing-instance-name {
         description "Add routing instance name to circuit / interface-id or remote-id";
         type empty;
       }
     }
     leaf use-interface-description {
       description "Use interface description instead of circuit identifier";
       junos:must "(!(\".. require-interface-description\"))";
       junos:must-message "use-interface-description may not be set with require-interface-desciption";
       type enumeration {
         enum "logical" {
           description "Use the logical interface description";
         }
         enum "device" {
           description "Use the device interface description";
         }
       }
     }
     leaf use-vlan-id {
       description "Use VLAN id instead of name";
       junos:must "((!(\".. no-vlan-interface-name\") && (!(\".. use-interface-description\") && !(\".. require-interface-description\"))))";
       junos:must-message "Vlan-tag cannot be added as no-vlan-interface-name or interface-description is configured";
       type empty;
     }
     leaf no-vlan-interface-name {
       description "Not include vlan or interface name";
       type empty;
     }
     leaf include-irb-and-l2 {
       description "Include IRB and L2 interface name";
       type empty;
     }
     container use-option-82 {
       description "Use option-82 remote-id for v6 remote-id";
       presence "enable use-option-82";
       uses v6-relay-option-cid-rid-action;
     }
     leaf keep-incoming-remote-id {
       description "Keep incoming remote identifier";
       type empty;
     }
   }
   grouping v6-server-group-type {
     uses apply-advanced;
     list server-group {
       key name;
       ordered-by user;
       description "One or more server groups";
       leaf name {
         description "DHCPv6 Server group name";
         type string {
           length "1 .. 64";
           junos:posix-pattern "^[A-Za-z0-9][_0-9A-Za-z-]*$";
           junos:pattern-message "Must be a non-reserved string of 64 characters or less";
         }
       }
       uses apply-advanced;
       list address {
         key name;
         ordered-by user;
         description "IP Address of one or more DHCP servers";
         max-elements 32;
         leaf name {
           description "IP Address of DHCP server";
           type jt:ipaddr;
         }
         uses apply-advanced;
       }
     }
   }
   grouping write-option-82-type {
     uses apply-advanced;
   }
 }
