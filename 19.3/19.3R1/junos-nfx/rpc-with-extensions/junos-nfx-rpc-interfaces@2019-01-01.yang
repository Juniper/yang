/*
 * Copyright (c) 2019 Juniper Networks, Inc.
 * All rights reserved.
 */
 module junos-nfx-rpc-interfaces {
   namespace "http://yang.juniper.net/junos-nfx/rpc/interfaces";

   prefix interfaces;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for interfaces command(s)";

   revision 2019-01-01 {
     description "Junos: 19.3R1.8";
   }

   rpc get-interface-information {
     description "Show interface information";
     input {
       uses command-forwarding;
       leaf routing-instance {
         description "Name of routing instance";
         type string;
       }
       leaf satellite-device {
         description "Name of satellite device";
         type string;
       }
       leaf ifl-class {
         description "IFL classification";
         type enumeration {
           enum "rtsock" {
             description "Display rtsock ifls";
           }
           enum "flow" {
             description "Display flow ifls";
           }
         }
       }
       leaf aggregation-device {
         description "Aggregation device interface list";
         type empty;
       }
       leaf zone {
         description "Interface's zone";
         type empty;
       }
       leaf level {
         type enumeration {
           enum "extensive" {
             description "Display extensive output";
           }
           enum "statistics" {
             description "Display statistics and detailed output";
           }
           enum "media" {
             description "Display media information";
           }
           enum "brief" {
             description "Display brief output";
           }
           enum "detail" {
             description "Display detailed output";
           }
           enum "terse" {
             description "Display terse output";
           }
         }
       }
       leaf level-extra {
         type enumeration {
           enum "detail" {
             description "Display detailed output";
           }
           enum "terse" {
             description "Display terse output";
           }
           enum "brief" {
             description "Display brief output";
           }
           enum "descriptions" {
             description "Display interface description strings";
           }
           enum "prbs-stats" {
             description "Display PRBS Stats";
           }
         }
       }
       leaf snmp-index {
         description "SNMP index of interface";
         type union {
           type uint32;
           type string {
             pattern "<.*>|$.*";
           }
         }
       }
       leaf switch-port {
         description "Front end port number";
         type union {
           type string {
             pattern "<.*>|$.*";
           }
           type uint32 {
             range "0 .. 15";
           }
         }
       }
       leaf interface-name {
         description "Name of physical or logical interface";
         type string {
           junos:posix-pattern "^[a-zA-Z0-9/-]+$";
           junos:pattern-message "Interface name  must be a string of alphanumericals or dashes";
         }
       }
     }
     output {
       choice output_c {
         case output-tag {
           leaf output {
             type string;
           }
         }
         case actual-tag {
           anyxml interface-information;
         }
         case multichassis-tag {
           anyxml multi-routing-engine-results;
         }
       }
     }
   }
   rpc get-mc-ae-interface-information {
     description "Show MC-AE configured interface information";
     input {
       leaf id {
         description "MC-AE id";
         type union {
           type uint16;
           type string {
             pattern "<.*>|$.*";
           }
         }
       }
       leaf unit {
         description "Logical interface unit number";
         type union {
           type string {
             pattern "<.*>|$.*";
           }
           type uint32 {
             range "0 .. 16385";
           }
         }
       }
       leaf extensive {
         description "Show mcae information in detail";
         type empty;
       }
     }
     output {
       choice output_c {
         case output-tag {
           leaf output {
             type string;
           }
         }
         case actual-tag {
           anyxml mc-ae-status-information-list;
         }
         case multichassis-tag {
           anyxml multi-routing-engine-results;
         }
       }
     }
   }
   rpc get-mc-ae-revertive-information {
     description "Show mc-ae revertive information";
     input {
       leaf id {
         description "MC-AE id";
         type union {
           type uint16;
           type string {
             pattern "<.*>|$.*";
           }
         }
       }
     }
     output {
       choice output_c {
         case output-tag {
           leaf output {
             type string;
           }
         }
         case actual-tag {
           anyxml mc-ae-status-information-list;
         }
         case multichassis-tag {
           anyxml multi-routing-engine-results;
         }
       }
     }
   }
   rpc get-interfaces-summary {
     description "Display Logical Interfaces summary output";
     output {
       choice output_c {
         case output-tag {
           leaf output {
             type string;
           }
         }
         case actual-tag {
           anyxml interface-information;
         }
         case multichassis-tag {
           anyxml multi-routing-engine-results;
         }
       }
     }
   }
   rpc get-interface-controller-information {
     description "Show controller information";
     input {
       leaf interface-name {
         description "Name of controller";
         type string;
       }
     }
     output {
       choice output_c {
         case output-tag {
           leaf output {
             type string;
           }
         }
         case actual-tag {
           anyxml interface-information;
         }
         case multichassis-tag {
           anyxml multi-routing-engine-results;
         }
       }
     }
   }
   rpc get-interface-set-information {
     description "Show interface set information";
     input {
       leaf level {
         type enumeration {
           enum "terse" {
             description "Display terse output";
           }
           enum "detail" {
             description "Display detailed output";
           }
         }
       }
       leaf interface-set-name {
         description "Name of interface set";
         type string;
       }
     }
     output {
       choice output_c {
         case output-tag {
           leaf output {
             type string;
           }
         }
         case actual-tag {
           anyxml interface-information;
         }
         case multichassis-tag {
           anyxml multi-routing-engine-results;
         }
       }
     }
   }
   rpc get-interface-set-queue-information {
     description "Show queue statistics for this interface-set";
     input {
       leaf forwarding-class {
         description "Name of forwarding class";
         type string;
       }
       leaf traffic-direction {
         description "Show statistics for ingress, egress or both";
         default "both-ingress-egress";
         type enumeration {
           enum "ingress" {
             description "Display ingress queue statistics";
           }
           enum "egress" {
             description "Display egress queue statistics";
           }
           enum "both-ingress-egress" {
             description "Display both ingress and egress queue statistics";
           }
         }
       }
       leaf node-type {
         description "Show statistics for aggregate or remaining-traffic";
         default "aggregate";
         type enumeration {
           enum "aggregate" {
             description "Display aggregate queue statistics";
           }
           enum "remaining-traffic" {
             description "Display remaining-traffic queue statistics";
           }
         }
       }
       leaf interface-set-name {
         description "Name of interface set";
         type string;
       }
     }
     output {
       choice output_c {
         case output-tag {
           leaf output {
             type string;
           }
         }
         case actual-tag {
           anyxml interface-information;
         }
         case multichassis-tag {
           anyxml multi-routing-engine-results;
         }
       }
     }
   }
   rpc show-interfaces-interval {
     description "Show interval statistics";
     input {
       leaf interface-name {
         description "Name of physical interface";
         type string;
         mandatory true;
       }
     }
     output {
       choice output_c {
         case output-tag {
           leaf output {
             type string;
           }
         }
         case actual-tag {
           anyxml interfaces-interval;
         }
         case multichassis-tag {
           anyxml multi-routing-engine-results;
         }
       }
     }
   }
   rpc get-interface-transport-information {
     description "Show interface transport information";
     input {
       leaf interface-name {
         description "Name of physical interface";
         type string;
         mandatory true;
       }
     }
     output {
       choice output_c {
         case output-tag {
           leaf output {
             type string;
           }
         }
         case actual-tag {
           anyxml interface-transport-information;
         }
         case multichassis-tag {
           anyxml multi-routing-engine-results;
         }
       }
     }
   }
   rpc get-interface-transport-pm-information {
     description "Show interface transport performance monitoring (pm) information";
     output {
       choice output_c {
         case output-tag {
           leaf output {
             type string;
           }
         }
         case actual-tag {
           anyxml interface-transport-pm-information;
         }
         case multichassis-tag {
           anyxml multi-routing-engine-results;
         }
       }
     }
   }
   rpc get-interface-transport-pm-otn-information {
     description "Show interface transport otn pm information";
     output {
       choice output_c {
         case output-tag {
           leaf output {
             type string;
           }
         }
         case actual-tag {
           anyxml interface-transport-pm-otn-information;
         }
         case multichassis-tag {
           anyxml multi-routing-engine-results;
         }
       }
     }
   }
   rpc get-interface-transport-pm-otn-c-information {
     description "Show interface transport pm otn current information";
     input {
       leaf interface-name {
         description "Name of physical interface";
         type string;
         mandatory true;
       }
     }
     output {
       choice output_c {
         case output-tag {
           leaf output {
             type string;
           }
         }
         case actual-tag {
           anyxml interface-transport-pm-otn-c-information;
         }
         case multichassis-tag {
           anyxml multi-routing-engine-results;
         }
       }
     }
   }
   rpc get-interface-transport-pm-otn-c-all-information {
     description "Show interface transport pm otn current all information";
     output {
       choice output_c {
         case output-tag {
           leaf output {
             type string;
           }
         }
         case actual-tag {
           anyxml interface-transport-information;
         }
         case multichassis-tag {
           anyxml multi-routing-engine-results;
         }
       }
     }
   }
   rpc get-interface-transport-pm-otn-int-information {
     description "Show interface transport pm otn interval information";
     input {
       leaf interface-name {
         description "Name of physical interface";
         type string;
         mandatory true;
       }
     }
     output {
       choice output_c {
         case output-tag {
           leaf output {
             type string;
           }
         }
         case actual-tag {
           anyxml interface-transport-pm-otn-int-information;
         }
         case multichassis-tag {
           anyxml multi-routing-engine-results;
         }
       }
     }
   }
   rpc get-interface-transport-pm-otn-int-all-information {
     description "Show interface transport pm otn interval all information";
     output {
       choice output_c {
         case output-tag {
           leaf output {
             type string;
           }
         }
         case actual-tag {
           anyxml interface-transport-information;
         }
         case multichassis-tag {
           anyxml multi-routing-engine-results;
         }
       }
     }
   }
   rpc get-interface-transport-pm-otn-cday-information {
     description "Show interface transport pm otn current day information";
     input {
       leaf interface-name {
         description "Name of physical interface";
         type string;
         mandatory true;
       }
     }
     output {
       choice output_c {
         case output-tag {
           leaf output {
             type string;
           }
         }
         case actual-tag {
           anyxml interface-transport-pm-otn-cday-information;
         }
         case multichassis-tag {
           anyxml multi-routing-engine-results;
         }
       }
     }
   }
   rpc get-interface-transport-pm-otn-cday-all-information {
     description "Show interface transport pm otn current day all information";
     output {
       choice output_c {
         case output-tag {
           leaf output {
             type string;
           }
         }
         case actual-tag {
           anyxml interface-transport-information;
         }
         case multichassis-tag {
           anyxml multi-routing-engine-results;
         }
       }
     }
   }
   rpc get-interface-transport-pm-otn-pday-information {
     description "Show interface transport pm otn previous day information";
     input {
       leaf interface-name {
         description "Name of physical interface";
         type string;
         mandatory true;
       }
     }
     output {
       choice output_c {
         case output-tag {
           leaf output {
             type string;
           }
         }
         case actual-tag {
           anyxml interface-transport-pm-otn-pday-information;
         }
         case multichassis-tag {
           anyxml multi-routing-engine-results;
         }
       }
     }
   }
   rpc get-interface-transport-pm-otn-pday-all-information {
     description "Show interface transport pm otn previous day all information";
     output {
       choice output_c {
         case output-tag {
           leaf output {
             type string;
           }
         }
         case actual-tag {
           anyxml interface-transport-information;
         }
         case multichassis-tag {
           anyxml multi-routing-engine-results;
         }
       }
     }
   }
   rpc get-interface-transport-pm-otn-all-information {
     description "Show interface transport pm otn all information";
     input {
       leaf interface-name {
         description "Name of physical interface";
         type string;
         mandatory true;
       }
     }
     output {
       choice output_c {
         case output-tag {
           leaf output {
             type string;
           }
         }
         case actual-tag {
           anyxml interface-transport-pm-otn-all-information;
         }
         case multichassis-tag {
           anyxml multi-routing-engine-results;
         }
       }
     }
   }
   rpc get-interface-transport-pm-otn-all-all-information {
     description "Show interface transport pm otn all all information";
     output {
       choice output_c {
         case output-tag {
           leaf output {
             type string;
           }
         }
         case actual-tag {
           anyxml interface-transport-information;
         }
         case multichassis-tag {
           anyxml multi-routing-engine-results;
         }
       }
     }
   }
   rpc get-interface-transport-pm-optics-information {
     description "Show interface transport pm optics information";
     output {
       choice output_c {
         case output-tag {
           leaf output {
             type string;
           }
         }
         case actual-tag {
           anyxml interface-transport-pm-optics-information;
         }
         case multichassis-tag {
           anyxml multi-routing-engine-results;
         }
       }
     }
   }
   rpc get-interface-transport-pm-optics-c-information {
     description "Show interface transport pm optics current information";
     input {
       leaf interface-name {
         description "Name of physical interface";
         type string;
         mandatory true;
       }
     }
     output {
       choice output_c {
         case output-tag {
           leaf output {
             type string;
           }
         }
         case actual-tag {
           anyxml interface-transport-pm-optics-c-information;
         }
         case multichassis-tag {
           anyxml multi-routing-engine-results;
         }
       }
     }
   }
   rpc get-interface-transport-pm-optics-c-all-information {
     description "Show interface transport pm optics current all information";
     output {
       choice output_c {
         case output-tag {
           leaf output {
             type string;
           }
         }
         case actual-tag {
           anyxml interface-transport-information;
         }
         case multichassis-tag {
           anyxml multi-routing-engine-results;
         }
       }
     }
   }
   rpc get-interface-transport-pm-optics-int-information {
     description "Show interface transport pm optics interval information";
     input {
       leaf interface-name {
         description "Name of physical interface";
         type string;
         mandatory true;
       }
     }
     output {
       choice output_c {
         case output-tag {
           leaf output {
             type string;
           }
         }
         case actual-tag {
           anyxml interface-transport-pm-optics-int-information;
         }
         case multichassis-tag {
           anyxml multi-routing-engine-results;
         }
       }
     }
   }
   rpc get-interface-transport-pm-optics-int-all-information {
     description "Show interface transport pm optics interval all information";
     output {
       choice output_c {
         case output-tag {
           leaf output {
             type string;
           }
         }
         case actual-tag {
           anyxml interface-transport-information;
         }
         case multichassis-tag {
           anyxml multi-routing-engine-results;
         }
       }
     }
   }
   rpc get-interface-transport-pm-optics-cday-information {
     description "Show interface transport pm optics current day information";
     input {
       leaf interface-name {
         description "Name of physical interface";
         type string;
         mandatory true;
       }
     }
     output {
       choice output_c {
         case output-tag {
           leaf output {
             type string;
           }
         }
         case actual-tag {
           anyxml interface-transport-pm-optics-cday-information;
         }
         case multichassis-tag {
           anyxml multi-routing-engine-results;
         }
       }
     }
   }
   rpc get-interface-transport-pm-optics-cday-all-information {
     description "Show interface transport pm optics current day all information";
     output {
       choice output_c {
         case output-tag {
           leaf output {
             type string;
           }
         }
         case actual-tag {
           anyxml interface-transport-information;
         }
         case multichassis-tag {
           anyxml multi-routing-engine-results;
         }
       }
     }
   }
   rpc get-interface-transport-pm-optics-pday-information {
     description "Show interface transport pm optics previous day information";
     input {
       leaf interface-name {
         description "Name of physical interface";
         type string;
         mandatory true;
       }
     }
     output {
       choice output_c {
         case output-tag {
           leaf output {
             type string;
           }
         }
         case actual-tag {
           anyxml interface-transport-pm-optics-pday-information;
         }
         case multichassis-tag {
           anyxml multi-routing-engine-results;
         }
       }
     }
   }
   rpc get-interface-transport-pm-optics-pday-all-information {
     description "Show interface transport pm optics previous day all information";
     output {
       choice output_c {
         case output-tag {
           leaf output {
             type string;
           }
         }
         case actual-tag {
           anyxml interface-transport-information;
         }
         case multichassis-tag {
           anyxml multi-routing-engine-results;
         }
       }
     }
   }
   rpc get-interface-transport-pm-optics-all-information {
     description "Show interface transport pm optics all information";
     input {
       leaf interface-name {
         description "Name of physical interface";
         type string;
         mandatory true;
       }
     }
     output {
       choice output_c {
         case output-tag {
           leaf output {
             type string;
           }
         }
         case actual-tag {
           anyxml interface-transport-pm-optics-all-information;
         }
         case multichassis-tag {
           anyxml multi-routing-engine-results;
         }
       }
     }
   }
   rpc get-interface-transport-pm-optics-all-all-information {
     description "Show interface transport pm optics all all information";
     output {
       choice output_c {
         case output-tag {
           leaf output {
             type string;
           }
         }
         case actual-tag {
           anyxml interface-transport-information;
         }
         case multichassis-tag {
           anyxml multi-routing-engine-results;
         }
       }
     }
   }
   rpc get-interface-transport-pm-all-information {
     description "Show interface transport pm all information";
     output {
       choice output_c {
         case output-tag {
           leaf output {
             type string;
           }
         }
         case actual-tag {
           anyxml interface-transport-pm-all-information;
         }
         case multichassis-tag {
           anyxml multi-routing-engine-results;
         }
       }
     }
   }
   rpc get-interface-transport-pm-all-all-information {
     description "Show interface transport pm all all information";
     input {
       leaf interface-name {
         description "Name of physical interface";
         type string;
         mandatory true;
       }
     }
     output {
       choice output_c {
         case output-tag {
           leaf output {
             type string;
           }
         }
         case actual-tag {
           anyxml interface-transport-pm-all-all-information;
         }
         case multichassis-tag {
           anyxml multi-routing-engine-results;
         }
       }
     }
   }
   rpc get-interface-transport-pm-all-all-all-information {
     description "Show interface transport pm all all all information";
     output {
       choice output_c {
         case output-tag {
           leaf output {
             type string;
           }
         }
         case actual-tag {
           anyxml interface-transport-information;
         }
         case multichassis-tag {
           anyxml multi-routing-engine-results;
         }
       }
     }
   }
   rpc get-interface-transport-pm-all-c-information {
     description "Show interface transport pm all current information";
     input {
       leaf interface-name {
         description "Name of physical interface";
         type string;
         mandatory true;
       }
     }
     output {
       choice output_c {
         case output-tag {
           leaf output {
             type string;
           }
         }
         case actual-tag {
           anyxml interface-transport-pm-all-c-information;
         }
         case multichassis-tag {
           anyxml multi-routing-engine-results;
         }
       }
     }
   }
   rpc get-interface-transport-pm-all-c-all-information {
     description "Show interface transport pm all current all information";
     output {
       choice output_c {
         case output-tag {
           leaf output {
             type string;
           }
         }
         case actual-tag {
           anyxml interface-transport-information;
         }
         case multichassis-tag {
           anyxml multi-routing-engine-results;
         }
       }
     }
   }
   rpc get-interface-transport-pm-all-int-information {
     description "Show interface transport pm all interval information";
     input {
       leaf interface-name {
         description "Name of physical interface";
         type string;
         mandatory true;
       }
     }
     output {
       choice output_c {
         case output-tag {
           leaf output {
             type string;
           }
         }
         case actual-tag {
           anyxml interface-transport-pm-all-int-information;
         }
         case multichassis-tag {
           anyxml multi-routing-engine-results;
         }
       }
     }
   }
   rpc get-interface-transport-pm-all-int-all-information {
     description "Show interface transport pm all interval all information";
     output {
       choice output_c {
         case output-tag {
           leaf output {
             type string;
           }
         }
         case actual-tag {
           anyxml interface-transport-information;
         }
         case multichassis-tag {
           anyxml multi-routing-engine-results;
         }
       }
     }
   }
   rpc get-interface-transport-pm-all-cday-information {
     description "Show interface transport pm all currentday information";
     input {
       leaf interface-name {
         description "Name of physical interface";
         type string;
         mandatory true;
       }
     }
     output {
       choice output_c {
         case output-tag {
           leaf output {
             type string;
           }
         }
         case actual-tag {
           anyxml interface-transport-pm-all-cday-information;
         }
         case multichassis-tag {
           anyxml multi-routing-engine-results;
         }
       }
     }
   }
   rpc get-interface-transport-pm-all-cday-all-information {
     description "Show interface transport pm all currentday all information";
     output {
       choice output_c {
         case output-tag {
           leaf output {
             type string;
           }
         }
         case actual-tag {
           anyxml interface-transport-information;
         }
         case multichassis-tag {
           anyxml multi-routing-engine-results;
         }
       }
     }
   }
   rpc get-interface-transport-pm-all-pday-information {
     description "Show interface transport pm all previousday information";
     input {
       leaf interface-name {
         description "Name of physical interface";
         type string;
         mandatory true;
       }
     }
     output {
       choice output_c {
         case output-tag {
           leaf output {
             type string;
           }
         }
         case actual-tag {
           anyxml interface-transport-pm-all-pday-information;
         }
         case multichassis-tag {
           anyxml multi-routing-engine-results;
         }
       }
     }
   }
   rpc get-interface-transport-pm-all-pday-all-information {
     description "Show interface transport pm all previousday all information";
     output {
       choice output_c {
         case output-tag {
           leaf output {
             type string;
           }
         }
         case actual-tag {
           anyxml interface-transport-information;
         }
         case multichassis-tag {
           anyxml multi-routing-engine-results;
         }
       }
     }
   }
   rpc show-interfaces-far-end-interval {
     description "Show far end interval statistics";
     input {
       leaf interface-name {
         description "Name of physical interface";
         type string;
         mandatory true;
       }
     }
     output {
       choice output_c {
         case output-tag {
           leaf output {
             type string;
           }
         }
         case actual-tag {
           anyxml interfaces-far-end-interval;
         }
         case multichassis-tag {
           anyxml multi-routing-engine-results;
         }
       }
     }
   }
   rpc get-mac-database {
     description "Show media access control database information";
     input {
       leaf interface-name {
         description "Name of physical or logical interface";
         type string;
         mandatory true;
       }
       leaf mac-address {
         description "MAC address";
         type string;
       }
     }
     output {
       choice output_c {
         case output-tag {
           leaf output {
             type string;
           }
         }
         case actual-tag {
           anyxml interface-information;
         }
         case multichassis-tag {
           anyxml multi-routing-engine-results;
         }
       }
     }
   }
   rpc get-interface-queue-information {
     description "Show queue statistics for this interface";
     input {
       leaf forwarding-class {
         description "Name of forwarding class";
         type string;
       }
       leaf traffic-direction {
         description "Show statistics for ingress, egress or both";
         default "both-ingress-egress";
         type enumeration {
           enum "ingress" {
             description "Display ingress queue statistics";
           }
           enum "egress" {
             description "Display egress queue statistics";
           }
           enum "both-ingress-egress" {
             description "Display both ingress and egress queue statistics";
           }
         }
       }
       leaf node-type {
         description "Show statistics for aggregate or remaining-traffic";
         default "aggregate";
         type enumeration {
           enum "aggregate" {
             description "Display aggregate queue statistics";
           }
           enum "remaining-traffic" {
             description "Display remaining-traffic queue statistics";
           }
         }
       }
       leaf source-chassis {
         description "Source chassis name for which to show details";
         type string;
       }
       leaf source-fpc {
         description "Source FPC for which to show details";
         type union {
           type string {
             pattern "<.*>|$.*";
           }
           type int32 {
             range "0 .. 8";
           }
         }
       }
       leaf l2-statistics {
         description "Display layer-2 level queue stats for lsq interface";
         type empty;
       }
       leaf buffer-occupancy {
         description "Display interface egress queue buffer-occupancy";
         type empty;
       }
       leaf interface-name {
         description "Name of physical interface";
         type string;
       }
     }
     output {
       choice output_c {
         case output-tag {
           leaf output {
             type string;
           }
         }
         case actual-tag {
           anyxml interface-information;
         }
         case multichassis-tag {
           anyxml multi-routing-engine-results;
         }
       }
     }
   }
   rpc get-interface-priority-group-information {
     description "Show priority group statistics for this interface";
     input {
       leaf buffer-occupancy {
         description "Display interface ingress priority-group buffer-occupancy";
         type empty;
       }
       leaf interface-name {
         description "Name of physical interface";
         type string;
       }
     }
     output {
       choice output_c {
         case output-tag {
           leaf output {
             type string;
           }
         }
         case actual-tag {
           anyxml interface-information;
         }
         case multichassis-tag {
           anyxml multi-routing-engine-results;
         }
       }
     }
   }
   rpc get-interface-voq-information {
     description "Show VOQ drop statistics for this interface";
     input {
       leaf forwarding-class {
         description "Name of forwarding class";
         type string;
       }
       leaf source-fpc {
         description "Source FPC for which to show details";
         type union {
           type string {
             pattern "<.*>|$.*";
           }
           type int32 {
             range "0 .. 15";
           }
         }
       }
       leaf display-filter {
         description "Show VOQ statistics for stats-all or stats-non-zero counters";
         type enumeration {
           enum "non-zero" {
             description "Display only non-zero VOQ statistics counters";
           }
         }
       }
       leaf interface-name {
         description "Name of physical interface";
         type string;
       }
     }
     output {
       choice output_c {
         case output-tag {
           leaf output {
             type string;
           }
         }
         case actual-tag {
           anyxml interface-information;
         }
         case multichassis-tag {
           anyxml multi-routing-engine-results;
         }
       }
     }
   }
   rpc get-interface-fc-counters-information {
     description "Show forwarding-class statistics for this interface";
     input {
       leaf interface-name {
         description "Name of physical interface";
         type string;
       }
     }
     output {
       choice output_c {
         case output-tag {
           leaf output {
             type string;
           }
         }
         case actual-tag {
           anyxml interface-information;
         }
         case multichassis-tag {
           anyxml multi-routing-engine-results;
         }
       }
     }
   }
   rpc get-interface-filter-information {
     description "Show interface filters information";
     input {
       leaf interface-name {
         description "Name of physical or logical interface";
         type string;
       }
     }
     output {
       choice output_c {
         case output-tag {
           leaf output {
             type string;
           }
         }
         case actual-tag {
           anyxml interface-filter-information;
         }
         case multichassis-tag {
           anyxml multi-routing-engine-results;
         }
       }
     }
   }
   rpc get-interface-policer-information {
     description "Show interface policers information";
     input {
       leaf interface-name {
         description "Name of physical or logical interface";
         type string;
       }
     }
     output {
       choice output_c {
         case output-tag {
           leaf output {
             type string;
           }
         }
         case actual-tag {
           anyxml interface-policer-information;
         }
         case multichassis-tag {
           anyxml multi-routing-engine-results;
         }
       }
     }
   }
   rpc get-interface-optics-diagnostics-information {
     description "Show interface optics-diagnostics information";
     input {
       leaf interface-name {
         description "Name of physical interface";
         type string;
       }
     }
     output {
       choice output_c {
         case output-tag {
           leaf output {
             type string;
           }
         }
         case actual-tag {
           anyxml interface-information;
         }
         case multichassis-tag {
           anyxml multi-routing-engine-results;
         }
       }
     }
   }
   rpc show-interface-optics-diagnostics-satellite {
     description "Name of physical interface in satellite device";
     input {
       leaf fpc-slot {
         description "Satellite slot number";
         type union {
           type string {
             pattern "<.*>|$.*";
           }
           type uint32 {
             range "65 .. 254";
           }
         }
       }
       leaf device-alias {
         description "Device alias";
         type string;
       }
       leaf interface-name {
         description "Name of physical interface";
         type string;
       }
     }
     output {
       choice output_c {
         case output-tag {
           leaf output {
             type string;
           }
         }
         case multichassis-tag {
           anyxml multi-routing-engine-results;
         }
       }
     }
   }
   rpc get-destination-class-statistics {
     description "Show statistics for destination class";
     input {
       leaf class-name {
         description "Name of destination class";
         type string;
         mandatory true;
       }
       leaf interface-name {
         description "Name of logical interface";
         type string;
       }
     }
     output {
       choice output_c {
         case output-tag {
           leaf output {
             type string;
           }
         }
         case actual-tag {
           anyxml interface-information;
         }
         case multichassis-tag {
           anyxml multi-routing-engine-results;
         }
       }
     }
   }
   rpc get-all-destination-class-statistics {
     description "Display all destination class usage";
     output {
       choice output_c {
         case output-tag {
           leaf output {
             type string;
           }
         }
         case actual-tag {
           anyxml interface-information;
         }
         case multichassis-tag {
           anyxml multi-routing-engine-results;
         }
       }
     }
   }
   rpc get-source-class-statistics {
     description "Show statistics for source class";
     input {
       leaf class-name {
         description "Name of source class";
         type string;
         mandatory true;
       }
       leaf interface-name {
         description "Name of logical interface";
         type string;
       }
     }
     output {
       choice output_c {
         case output-tag {
           leaf output {
             type string;
           }
         }
         case actual-tag {
           anyxml interface-information;
         }
         case multichassis-tag {
           anyxml multi-routing-engine-results;
         }
       }
     }
   }
   rpc get-all-source-class-statistics {
     description "Display all source class usage";
     output {
       choice output_c {
         case output-tag {
           leaf output {
             type string;
           }
         }
         case actual-tag {
           anyxml interface-information;
         }
         case multichassis-tag {
           anyxml multi-routing-engine-results;
         }
       }
     }
   }
   rpc get-targeting-information {
     description "Show Distribution information of a bundle";
     input {
       leaf bundle-name {
         description "Name of the bundle";
         type string;
       }
     }
     output {
       choice output_c {
         case output-tag {
           leaf output {
             type string;
           }
         }
         case actual-tag {
           anyxml targeting-information;
         }
         case multichassis-tag {
           anyxml multi-routing-engine-results;
         }
       }
     }
   }
   rpc get-l2-vlan-info {
     description "Show l2 routing instance data structure";
     input {
       leaf routing-instance {
         description "Name of the routing-instance";
         type string;
         mandatory true;
       }
     }
     output {
       choice output_c {
         case output-tag {
           leaf output {
             type string;
           }
         }
         case actual-tag {
           anyxml l2-vlan-info;
         }
         case multichassis-tag {
           anyxml multi-routing-engine-results;
         }
       }
     }
   }
   rpc get-distribution-list-information {
     description "Show distribution list information of a bundle";
     input {
       leaf bundle-name {
         description "Name of the bundle";
         type string;
       }
     }
     output {
       choice output_c {
         case output-tag {
           leaf output {
             type string;
           }
         }
         case actual-tag {
           anyxml distribution-list-information;
         }
         case multichassis-tag {
           anyxml multi-routing-engine-results;
         }
       }
     }
   }
   rpc get-dcd-lib-client-data {
     description "Show library clients of DCD ";
     output {
       choice output_c {
         case output-tag {
           leaf output {
             type string;
           }
         }
         case actual-tag {
           anyxml dcd-lib-client-data;
         }
         case multichassis-tag {
           anyxml multi-routing-engine-results;
         }
       }
     }
   }
   rpc get-interface-flow-statistics {
     description "Show security flow counters and errors";
     input {
       leaf interface-name {
         description "Name of physical or logical interface";
         type string;
         mandatory true;
       }
     }
     output {
       choice output_c {
         case output-tag {
           leaf output {
             type string;
           }
         }
         case actual-tag {
           anyxml interface-information;
         }
         case multichassis-tag {
           anyxml multi-routing-engine-results;
         }
       }
     }
   }
   rpc get-interfaces-routing {
     description "Show routing status";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
         case fabric {
           leaf fabric {
             description "Internal fabric state";
             type empty;
           }
         }
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf level {
         default "brief";
         type enumeration {
           enum "brief" {
             description "Display brief output (default)";
           }
           enum "detail" {
             description "Display detailed output";
           }
           enum "summary" {
             description "Display summary output";
           }
         }
       }
       leaf interface-name {
         description "Name of interface";
         type union {
           type jt:interface-wildcard;
           type string {
             pattern "<.*>|$.*";
           }
         }
       }
     }
     output {
       choice output_c {
         case output-tag {
           leaf output {
             type string;
           }
         }
         case multichassis-tag {
           anyxml multi-routing-engine-results;
         }
       }
     }
   }
   rpc get-redundancy-status {
     description "Show redundancy status";
     input {
       leaf interface-name {
         description "Name of interface";
         type union {
           type jt:interface-wildcard;
           type string {
             pattern "<.*>|$.*";
           }
         }
       }
     }
     output {
       choice output_c {
         case output-tag {
           leaf output {
             type string;
           }
         }
         case actual-tag {
           anyxml interface-redundancy-information;
         }
         case multichassis-tag {
           anyxml multi-routing-engine-results;
         }
       }
     }
   }
   rpc get-redundancy-status-details {
     description "Show redundancy status details";
     input {
       leaf interface-name {
         description "Name of interface";
         type union {
           type jt:interface-wildcard;
           type string {
             pattern "<.*>|$.*";
           }
         }
       }
     }
     output {
       choice output_c {
         case output-tag {
           leaf output {
             type string;
           }
         }
         case actual-tag {
           anyxml interface-redundancy-detail-information;
         }
         case multichassis-tag {
           anyxml multi-routing-engine-results;
         }
       }
     }
   }
   rpc interface-load-balancing {
     description "Show load-balancing status";
     input {
       leaf interface-name {
         description "Name of interface";
         type union {
           type jt:interface-wildcard;
           type string {
             pattern "<.*>|$.*";
           }
         }
       }
       leaf detail {
         description "Show load-balancing status details";
         type empty;
       }
     }
     output {
       choice output_c {
         case output-tag {
           leaf output {
             type string;
           }
         }
         case actual-tag {
           anyxml interface-load-balancing-information;
         }
         case multichassis-tag {
           anyxml multi-routing-engine-results;
         }
       }
     }
   }
   rpc show-interface-anchor-group {
     description "Show information regarding anchoring pfe/fpc group";
     input {
       leaf interface-name {
         description "Name of interface";
         type union {
           type jt:interface-wildcard;
           type string {
             pattern "<.*>|$.*";
           }
         }
       }
       leaf verbosity_level {
         description "Verbosity of output.";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml aggregated-anchor-group-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
