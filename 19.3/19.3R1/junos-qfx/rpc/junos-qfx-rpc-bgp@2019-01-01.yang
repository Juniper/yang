/*
 * Copyright (c) 2019 Juniper Networks, Inc.
 * All rights reserved.
 */
 module junos-qfx-rpc-bgp {
   namespace "http://yang.juniper.net/junos-qfx/rpc/bgp";

   prefix bgp;

   import junos-common-types {
     prefix jt;
   }

   organization "Juniper Networks, Inc.";

   contact "yang-support@juniper.net";

   description "Junos RPC YANG module for bgp command(s)";

   revision 2019-01-01 {
     description "Junos: 19.3R1.8";
   }

   rpc get-bgp-summary-information {
     description "Show overview of BGP information";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf group {
         description "Show overview of bgp information for a particular group";
         type string;
       }
       leaf exact-instance {
         description "Show peer information for a particular instance";
         type string;
       }
       leaf instance {
         description "Show peer information for instances with this prefix";
         type string;
       }
     }
     output {
       choice output_c {
         case output-tag {
           leaf output {
             type string;
           }
         }
         case actual-tag {
           anyxml bgp-information;
         }
         case multichassis-tag {
           anyxml multi-routing-engine-results;
         }
       }
     }
   }
   rpc get-bgp-group-information {
     description "Show the BGP group database";
     input {
       choice daemon-select {
         case logical-system {
           leaf logical-system {
             description "Name of logical system, or 'all'";
             type string {
             }
           }
         }
         case rib-sharding {
           leaf rib-sharding {
             description "Name of rib shard";
             type string {
             }
           }
         }
       }
       leaf verbosity_level {
         default "brief";
         type enumeration {
           enum "summary" {
             description "Display summary output";
           }
           enum "brief" {
             description "Display brief output (default)";
           }
           enum "detail" {
             description "Display detailed output";
           }
         }
       }
       leaf exact-instance {
         description "Show peer information for a particular instance";
         type string;
       }
       leaf instance {
         description "Show peer information for instances with this prefix";
         type string;
       }
       leaf group-name {
         description "Show group information for a particular group";
         type string;
       }
     }
     output {
       choice output_c {
         case output-tag {
           leaf output {
             type string;
           }
         }
         case actual-tag {
           anyxml bgp-group-information;
         }
         case multichassis-tag {
           anyxml multi-routing-engine-results;
         }
       }
     }
   }
   rpc get-bgp-group-output-queue-information {
     description "Show BGP output queues by priority";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf group-name {
         description "Show group information for a particular group";
         type string;
       }
     }
     output {
       choice output_c {
         case output-tag {
           leaf output {
             type string;
           }
         }
         case actual-tag {
           anyxml bgp-group-information;
         }
         case multichassis-tag {
           anyxml multi-routing-engine-results;
         }
       }
     }
   }
   rpc get-bgp-rtf-information {
     description "Show route target filtering information";
     input {
       choice daemon-select {
         case rib-sharding {
           leaf rib-sharding {
             description "Name of rib shard";
             type string {
             }
           }
         }
         case logical-system {
           leaf logical-system {
             description "Name of logical system, or 'all'";
             type string {
             }
           }
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       choice output_c {
         case output-tag {
           leaf output {
             type string;
           }
         }
         case actual-tag {
           anyxml bgp-rtf-information;
         }
         case multichassis-tag {
           anyxml multi-routing-engine-results;
         }
       }
     }
   }
   rpc get-bgp-traffic-statistics-information {
     description "Show packet statistics for labeled BGP routes";
     input {
       choice daemon-select {
         case rib-sharding {
           leaf rib-sharding {
             description "Name of rib shard";
             type string {
             }
           }
         }
         case logical-system {
           leaf logical-system {
             description "Name of logical system, or 'all'";
             type string {
             }
           }
         }
         case fabric {
           leaf fabric {
             description "Internal fabric state";
             type empty;
           }
         }
       }
       leaf verbosity_level {
         default "brief";
         type enumeration {
           enum "brief" {
             description "Display brief output (default)";
           }
           enum "detail" {
             description "Display detailed output";
           }
         }
       }
       leaf group-name {
         description "Show group information for a particular group";
         type string;
       }
     }
     output {
       choice output_c {
         case output-tag {
           leaf output {
             type string;
           }
         }
         case actual-tag {
           anyxml bgp-traffic-statistics-information;
         }
         case multichassis-tag {
           anyxml multi-routing-engine-results;
         }
       }
     }
   }
   rpc get-bgp-traffic-stats-ingress-labeled-info {
     description "Show ingress labeled path statistics";
     input {
       choice daemon-select {
         case rib-sharding {
           leaf rib-sharding {
             description "Name of rib shard";
             type string {
             }
           }
         }
         case logical-system {
           leaf logical-system {
             description "Name of logical system, or 'all'";
             type string {
             }
           }
         }
         case fabric {
           leaf fabric {
             description "Internal fabric state";
             type empty;
           }
         }
       }
       leaf label {
         description "Top label of label stack";
         type union {
           type uint32;
           type string {
             pattern "<.*>|$.*";
           }
         }
       }
     }
     output {
       choice output_c {
         case output-tag {
           leaf output {
             type string;
           }
         }
         case actual-tag {
           anyxml bgp-traffic-stats-ingress-labeled-info;
         }
         case multichassis-tag {
           anyxml multi-routing-engine-results;
         }
       }
     }
   }
   rpc get-bgp-neighbor-information {
     description "Show the BGP neighbor database";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf exact-instance {
         description "Show peer information for a particular instance";
         type string;
       }
       leaf instance {
         description "Show peer information for instances with this prefix";
         type string;
       }
       leaf neighbor-address {
         description "Show the neighbor database for a particular neighbor";
         type string;
       }
     }
     output {
       choice output_c {
         case output-tag {
           leaf output {
             type string;
           }
         }
         case actual-tag {
           anyxml bgp-information;
         }
         case multichassis-tag {
           anyxml multi-routing-engine-results;
         }
       }
     }
   }
   rpc get-bgp-orf-information {
     description "Show outbound route filtering information";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf verbosity_level {
         default "brief";
         type enumeration {
           enum "brief" {
             description "Display brief output (default)";
           }
           enum "detail" {
             description "Display detailed output";
           }
         }
       }
       leaf instance {
         description "Show ORF information for instances with this prefix";
         type string;
       }
       leaf neighbor-address {
         description "Show ORF information for a particular neighbor";
         type string;
       }
     }
     output {
       choice output_c {
         case output-tag {
           leaf output {
             type string;
           }
         }
         case actual-tag {
           anyxml bgp-orf-information;
         }
         case multichassis-tag {
           anyxml multi-routing-engine-results;
         }
       }
     }
   }
   rpc get-bgp-output-queue-information {
     description "Show outbound routes queue depths by priority";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf instance {
         description "Show route queue depths for instances with this prefix";
         type string;
       }
       leaf neighbor-address {
         description "Show route queue depths for a particular neighbor";
         type string;
       }
     }
     output {
       choice output_c {
         case output-tag {
           leaf output {
             type string;
           }
         }
         case actual-tag {
           anyxml bgp-information;
         }
         case multichassis-tag {
           anyxml multi-routing-engine-results;
         }
       }
     }
   }
   rpc get-bgp-monitoring-protocol-statistics {
     description "Show BGP Monitoring Protocol information";
     input {
       choice daemon-select {
         case logical-system {
           leaf logical-system {
             description "Name of logical system, or 'all'";
             type string {
             }
           }
         }
         case rib-sharding {
           leaf rib-sharding {
             description "Name of rib shard";
             type string {
             }
           }
         }
       }
       leaf station-name {
         description "Show information for a particular station";
         type string;
       }
     }
     output {
       choice output_c {
         case output-tag {
           leaf output {
             type string;
           }
         }
         case actual-tag {
           anyxml bgp-information;
         }
         case multichassis-tag {
           anyxml multi-routing-engine-results;
         }
       }
     }
   }
   rpc get-bgp-output-queue-scheduler {
     description "Show BGP output queue scheduler configuration";
     input {
       choice daemon-select {
         case logical-system {
           leaf logical-system {
             description "Name of logical system, or 'all'";
             type string {
             }
           }
         }
         case fabric {
           leaf fabric {
             description "Internal fabric state";
             type empty;
           }
         }
         case rib-sharding {
           leaf rib-sharding {
             description "Name of rib shard";
             type string {
             }
           }
         }
       }
       leaf exact-instance {
         description "Show scheduler for a particular instance";
         type string;
       }
       leaf instance {
         description "Show scheduler for instances with this prefix";
         type string;
       }
     }
     output {
       choice output_c {
         case output-tag {
           leaf output {
             type string;
           }
         }
         case actual-tag {
           anyxml bgp-output-queue-scheduler;
         }
         case multichassis-tag {
           anyxml multi-routing-engine-results;
         }
       }
     }
   }
   rpc get-bgp-replication-information {
     description "BGP NSR replication state between master and backup";
     input {
       choice daemon-select {
         case rib-sharding {
           leaf rib-sharding {
             description "Name of rib shard";
             type string {
             }
           }
         }
         case logical-system {
           leaf logical-system {
             description "Name of logical system, or 'all'";
             type string {
             }
           }
         }
       }
     }
     output {
       choice output_c {
         case output-tag {
           leaf output {
             type string;
           }
         }
         case actual-tag {
           anyxml bgp-sync-information;
         }
         case multichassis-tag {
           anyxml multi-routing-engine-results;
         }
       }
     }
   }
   rpc get-bgp-route {
     description "Show BGP's view of the routes";
     input {
       choice daemon-select {
       }
       leaf destination {
         description "IP address and optional prefix length of destination";
         type jt:ipprefix-optional;
       }
       leaf table {
         description "Name of routing table";
         type string;
       }
     }
     output {
       choice output_c {
         case output-tag {
           leaf output {
             type string;
           }
         }
         case actual-tag {
           anyxml bgp-update-io-ribs;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
