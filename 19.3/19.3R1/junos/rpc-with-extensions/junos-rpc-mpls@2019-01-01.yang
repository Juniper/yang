/*
 * Copyright (c) 2019 Juniper Networks, Inc.
 * All rights reserved.
 */
 module junos-rpc-mpls {
   namespace "http://yang.juniper.net/junos/rpc/mpls";

   prefix mpls;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for mpls command(s)";

   revision 2019-01-01 {
     description "Junos: 19.3R1.8";
   }

   rpc get-mpls-traceroute-database-ldp {
     description "Show FECs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf fec {
         description "IP address and optional prefix length of FEC";
         type jt:ipprefix;
       }
       leaf detail {
         description "Display detailed output";
         type empty;
       }
       leaf no-resolve {
         description "Don't attempt to print addresses symbolically";
         type empty;
       }
       leaf routing-instance {
         description "Name of routing instance, or 'all'";
         type string {
           junos:posix-pattern "!^((__.*__)|(all)|(.*[ ].*)|(\"\")|(.{129,}))$";
           junos:pattern-message "Must be a non-reserved string of 128 characters or less with no spaces.";
         }
       }
     }
     output {
       choice output_c {
         case output-tag {
           leaf output {
             type string;
           }
         }
         case actual-tag {
           anyxml database;
         }
         case multichassis-tag {
           anyxml multi-routing-engine-results;
         }
       }
     }
   }
   rpc get-egress-protection-information {
     description "Show egress-protection information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml ep-operational-information;
         }
         case multichassis-tag {
           anyxml multi-routing-engine-results;
         }
       }
     }
   }
   rpc get-mpls-admin-group-information {
     description "Show MPLS administrative groups";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-admin-group-information;
         }
         case multichassis-tag {
           anyxml multi-routing-engine-results;
         }
       }
     }
   }
   rpc get-mpls-admin-group-extended-information {
     description "Show MPLS extended administrative groups";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-admin-group-extended-information;
         }
         case multichassis-tag {
           anyxml multi-routing-engine-results;
         }
       }
     }
   }
   rpc get-mpls-abstract-hop-membership-information {
     description "Show MPLS abstract hop membership tables";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf abstract-hop {
         description "Name of abstract hop";
         type string;
       }
     }
     output {
       choice output_c {
         case output-tag {
           leaf output {
             type string;
           }
         }
         case actual-tag {
           anyxml mpls-abstract-hop-membership-information;
         }
         case multichassis-tag {
           anyxml multi-routing-engine-results;
         }
       }
     }
   }
   rpc get-mpls-cspf-information {
     description "Show Constrained Shortest Path First statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-cspf-information;
         }
         case multichassis-tag {
           anyxml multi-routing-engine-results;
         }
       }
     }
   }
   rpc get-mpls-path-information {
     description "Show configured named paths";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf path {
         description "Name of label-switched path";
         type string;
       }
     }
     output {
       choice output_c {
         case output-tag {
           leaf output {
             type string;
           }
         }
         case actual-tag {
           anyxml mpls-path-information;
         }
         case multichassis-tag {
           anyxml multi-routing-engine-results;
         }
       }
     }
   }
   rpc get-mpls-diffserv-te-information {
     description "Show MPLS Differentiated Services traffic engineering global properties";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-diffserv-te-information;
         }
         case multichassis-tag {
           anyxml multi-routing-engine-results;
         }
       }
     }
   }
   rpc get-mpls-lsp-information {
     description "Show configured label-switched paths";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional LSPs";
           }
           enum "bidirectional" {
             description "Display bidirectional LSPs";
           }
           enum "p2mp" {
             description "Display point-to-multipoint LSPs";
           }
           enum "externally-controlled" {
             description "Display externally controlled LSPs";
           }
         }
       }
       leaf lsp-provisioning {
         type enumeration {
           enum "externally-provisioned" {
             description "Display externally provisioned LSPs";
           }
           enum "locally-provisioned" {
             description "Display locally provisioned LSPs";
           }
         }
       }
       leaf lsp-stat {
         type enumeration {
           enum "statistics" {
             description "Display packet statistics for LSPs";
           }
           enum "reverse-statistics" {
             description "Display packet statistics for reverse direction of LSPs";
           }
         }
       }
       leaf bypass-lsp {
         type enumeration {
           enum "bypass" {
             description "Display LSPs used for protecting other LSPs";
           }
         }
       }
       leaf activeroutes {
         type enumeration {
           enum "count-active-routes" {
             description "Show active routes for LSPs";
           }
         }
       }
       leaf regex {
         description "Regular expression for LSP names to match";
         type string;
       }
     }
     output {
       choice output_c {
         case output-tag {
           leaf output {
             type string;
           }
         }
         case actual-tag {
           anyxml mpls-lsp-information;
         }
         case multichassis-tag {
           anyxml multi-routing-engine-results;
         }
       }
     }
   }
   rpc get-mpls-lsp-defaults-information {
     description "Display LSP defaults";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-lsp-defaults-information;
         }
         case multichassis-tag {
           anyxml multi-routing-engine-results;
         }
       }
     }
   }
   rpc get-mpls-lsp-autobandwidth {
     description "Display autobandwidth statistics for LSPs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       choice output_c {
         case output-tag {
           leaf output {
             type string;
           }
         }
         case actual-tag {
           anyxml mpls-lsp-information;
         }
         case multichassis-tag {
           anyxml multi-routing-engine-results;
         }
       }
     }
   }
   rpc get-mpls-lsp-abstract-computation {
     description "Display abstract computation preprocessing for LSPs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf level {
         default "brief";
         type enumeration {
           enum "brief" {
             description "Display brief output (default)";
           }
           enum "detail" {
             description "Display detailed output";
           }
           enum "extensive" {
             description "Display extensive output";
           }
         }
       }
       leaf regex {
         description "Regular expression for LSP names to match";
         type string;
       }
     }
     output {
       choice output_c {
         case output-tag {
           leaf output {
             type string;
           }
         }
         case actual-tag {
           anyxml mpls-lsp-information;
         }
         case multichassis-tag {
           anyxml multi-routing-engine-results;
         }
       }
     }
   }
   rpc get-mpls-container-lsp-information {
     description "Show configured container-label-switched paths";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf lsp-type {
         type enumeration {
           enum "ingress" {
             description "Display LSPs originating at this router";
           }
           enum "egress" {
             description "Display LSPs ending at this router";
           }
           enum "transit" {
             description "Display LSPs transiting this router";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
       leaf lsp-state {
         type enumeration {
           enum "up" {
             description "Display active LSPs";
           }
           enum "down" {
             description "Display inactive LSPs";
           }
         }
       }
       leaf lsp-direction {
         type enumeration {
           enum "unidirectional" {
             description "Display unidirectional container LSPs";
           }
         }
       }
       leaf lsp-stat {
         type enumeration {
           enum "statistics" {
             description "Display packet statistics for LSPs";
           }
         }
       }
       leaf activeroutes {
         type enumeration {
           enum "count-active-routes" {
             description "Show active routes for LSPs";
           }
         }
       }
       leaf regex {
         description "Regular expression for LSP names to match";
         type string;
       }
     }
     output {
       choice output_c {
         case output-tag {
           leaf output {
             type string;
           }
         }
         case actual-tag {
           anyxml mpls-container-lsp-information;
         }
         case multichassis-tag {
           anyxml multi-routing-engine-results;
         }
       }
     }
   }
   rpc get-mpls-container-lsp-defaults-information {
     description "Display container LSP defaults";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml mpls-container-lsp-defaults-information;
         }
         case multichassis-tag {
           anyxml multi-routing-engine-results;
         }
       }
     }
   }
   rpc get-mpls-call-admission-control-information {
     description "Show CAC information for MPLS LSPs";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf lsp-name {
         description "Name of LSP";
         type string {
           length "1 .. 64";
         }
       }
       leaf instance {
         description "Name of routing instance";
         type string;
       }
     }
     output {
       choice output_c {
         case output-tag {
           leaf output {
             type string;
           }
         }
         case actual-tag {
           anyxml mpls-call-admission-control-information;
         }
         case multichassis-tag {
           anyxml multi-routing-engine-results;
         }
       }
     }
   }
   rpc get-mpls-context-identifier-information {
     description "Show configured egress protection context identifiers";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf context-type {
         type enumeration {
           enum "primary" {
             description "Display primary context identifier(s)";
           }
           enum "protector" {
             description "Display protector context identifier(s)";
           }
         }
       }
       leaf level {
         default "brief";
         type enumeration {
           enum "brief" {
             description "Display brief output (default)";
           }
           enum "detail" {
             description "Display detailed output";
           }
         }
       }
       leaf id {
         description "Identifier";
         type string;
       }
     }
     output {
       choice output_c {
         case output-tag {
           leaf output {
             type string;
           }
         }
         case actual-tag {
           anyxml mpls-context-identifier-information;
         }
         case multichassis-tag {
           anyxml multi-routing-engine-results;
         }
       }
     }
   }
   rpc get-mpls-srlg-information {
     description "Show MPLS SRLG";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
     }
     output {
       choice output_c {
         case output-tag {
           leaf output {
             type string;
           }
         }
         case actual-tag {
           anyxml mpls-srlg-information;
         }
         case multichassis-tag {
           anyxml multi-routing-engine-results;
         }
       }
     }
   }
   rpc get-mpls-association-path-information {
     description "Display all LSPs that share same path";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf path-name {
         description "Name of path";
         type string;
         mandatory true;
       }
     }
     output {
       choice output_c {
         case output-tag {
           leaf output {
             type string;
           }
         }
         case actual-tag {
           anyxml mpls-association-path;
         }
         case multichassis-tag {
           anyxml multi-routing-engine-results;
         }
       }
     }
   }
   rpc get-mpls-association-iif-information {
     description "Display all LSPs that share same incoming interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface-name {
         description "Name of incoming interface";
         type string;
         mandatory true;
       }
     }
     output {
       choice output_c {
         case output-tag {
           leaf output {
             type string;
           }
         }
         case actual-tag {
           anyxml mpls-association-iif;
         }
         case multichassis-tag {
           anyxml multi-routing-engine-results;
         }
       }
     }
   }
   rpc get-mpls-association-oif-information {
     description "Display all LSPs that share same outgoing interface";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface-name {
         description "Name of outgoing interface";
         type string;
         mandatory true;
       }
     }
     output {
       choice output_c {
         case output-tag {
           leaf output {
             type string;
           }
         }
         case actual-tag {
           anyxml mpls-association-oif;
         }
         case multichassis-tag {
           anyxml multi-routing-engine-results;
         }
       }
     }
   }
   rpc get-mpls-correlation-nexthop-information {
     description "Display MPLS LSP info for the owner of this nexthop";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf nhid {
         description "NH-ID";
         type union {
           type int32;
           type string {
             pattern "<.*>|$.*";
           }
         }
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
     output {
       choice output_c {
         case output-tag {
           leaf output {
             type string;
           }
         }
         case actual-tag {
           anyxml mpls-correlation-nhid;
         }
         case multichassis-tag {
           anyxml multi-routing-engine-results;
         }
       }
     }
   }
   rpc get-mpls-correlation-label-information {
     description "Display MPLS LSP info for the owner of this label";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf nhid {
         description "Label value";
         type union {
           type int32;
           type string {
             pattern "<.*>|$.*";
           }
         }
         mandatory true;
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
         }
       }
     }
     output {
       choice output_c {
         case output-tag {
           leaf output {
             type string;
           }
         }
         case actual-tag {
           anyxml mpls-correlation-label;
         }
         case multichassis-tag {
           anyxml multi-routing-engine-results;
         }
       }
     }
   }
   rpc get-mpls-interface-information {
     description "Show MPLS interfaces";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf verbosity_level {
         default "brief";
         type enumeration {
           enum "brief" {
             description "Display brief output (default)";
           }
           enum "detail" {
             description "Display detailed output";
           }
         }
       }
       leaf instance {
         description "Name of routing instance";
         type string;
       }
     }
     output {
       choice output_c {
         case output-tag {
           leaf output {
             type string;
           }
         }
         case actual-tag {
           anyxml mpls-interface-information;
         }
         case multichassis-tag {
           anyxml multi-routing-engine-results;
         }
       }
     }
   }
   rpc mpls-label-space {
     description "Mpls label space";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc mpls-label-history {
     description "Show MPLS label history";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml mpls-label-history;
         }
         case multichassis-tag {
           anyxml multi-routing-engine-results;
         }
       }
     }
   }
   rpc mpls-label-history-range {
     description "Show MPLS label history in range";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf label-history-range-start {
         description "Value of the start of label-range";
         type union {
           type string {
             pattern "<.*>|$.*";
           }
           type uint32 {
             range "1 .. 1048575";
           }
         }
         mandatory true;
       }
       leaf label-history-range-end {
         description "Value of the end of label-range";
         type union {
           type string {
             pattern "<.*>|$.*";
           }
           type uint32 {
             range "1 .. 1048575";
           }
         }
         mandatory true;
       }
     }
     output {
       choice output_c {
         case output-tag {
           leaf output {
             type string;
           }
         }
         case actual-tag {
           anyxml mpls-label-history-range;
         }
         case multichassis-tag {
           anyxml multi-routing-engine-results;
         }
       }
     }
   }
   rpc mpls-history-label-value {
     description "MPLS label value";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf label-history-value {
         description "Value of the label";
         type union {
           type string {
             pattern "<.*>|$.*";
           }
           type uint32 {
             range "1 .. 1048575";
           }
         }
         mandatory true;
       }
     }
     output {
       choice output_c {
         case output-tag {
           leaf output {
             type string;
           }
         }
         case actual-tag {
           anyxml mpls-label-value;
         }
         case multichassis-tag {
           anyxml multi-routing-engine-results;
         }
       }
     }
   }
   rpc mpls-label-space-usage {
     description "Show MPLS label space usage statistics";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml mpls-label-usage;
         }
         case multichassis-tag {
           anyxml multi-routing-engine-results;
         }
       }
     }
   }
   rpc mpls-label-space-usage-range {
     description "Show MPLS label space usage statistics in range";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf label-range-start {
         description "Value of the start of label-range";
         type union {
           type string {
             pattern "<.*>|$.*";
           }
           type uint32 {
             range "1 .. 1048575";
           }
         }
         mandatory true;
       }
       leaf label-range-end {
         description "Value of the end of label-range";
         type union {
           type string {
             pattern "<.*>|$.*";
           }
           type uint32 {
             range "1 .. 1048575";
           }
         }
         mandatory true;
       }
     }
     output {
       choice output_c {
         case output-tag {
           leaf output {
             type string;
           }
         }
         case actual-tag {
           anyxml mpls-label-usage;
         }
         case multichassis-tag {
           anyxml multi-routing-engine-results;
         }
       }
     }
   }
   rpc mpls-usage-label-value {
     description "MPLS label value";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf label-value {
         description "Value of the label";
         type union {
           type string {
             pattern "<.*>|$.*";
           }
           type uint32 {
             range "1 .. 1048575";
           }
         }
         mandatory true;
       }
     }
     output {
       choice output_c {
         case output-tag {
           leaf output {
             type string;
           }
         }
         case actual-tag {
           anyxml mpls-label-value;
         }
         case multichassis-tag {
           anyxml multi-routing-engine-results;
         }
       }
     }
   }
   rpc get-mpls-static-lsp-information {
     description "Show configured static label-switched paths";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of routing instance";
         type string;
       }
       leaf lsp-type {
         type enumeration {
           enum "bypass" {
             description "Display bypass LSPs originating at this router";
           }
           enum "ingress" {
             description "Display LSPs originating at this router";
           }
           enum "transit" {
             description "Display LSPs transiting this router";
           }
           enum "segment" {
             description "Display segment identifier (SID) labels";
           }
         }
       }
       leaf level {
         default "brief";
         type enumeration {
           enum "terse" {
             description "Display terse output";
           }
           enum "brief" {
             description "Display brief output (default)";
           }
           enum "detail" {
             description "Display detailed output";
           }
           enum "extensive" {
             description "Display extensive output";
           }
           enum "descriptions" {
             description "Display LSP description strings";
           }
           enum "statistics" {
             description "Display packet statistics for LSPs";
           }
         }
       }
       leaf lsp-state {
         type enumeration {
           enum "up" {
             description "Display active LSPs";
           }
           enum "down" {
             description "Display inactive LSPs";
           }
         }
       }
       leaf regex {
         description "Regular expression for LSP names to match";
         type string;
       }
     }
     output {
       choice output_c {
         case output-tag {
           leaf output {
             type string;
           }
         }
         case actual-tag {
           anyxml mpls-static-lsp-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
