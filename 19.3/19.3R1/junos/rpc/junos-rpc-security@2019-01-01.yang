/*
 * Copyright (c) 2019 Juniper Networks, Inc.
 * All rights reserved.
 */
 module junos-rpc-security {
   namespace "http://yang.juniper.net/junos/rpc/security";

   prefix security;

   import junos-common-types {
     prefix jt;
   }

   organization "Juniper Networks, Inc.";

   contact "yang-support@juniper.net";

   description "Junos RPC YANG module for security command(s)";

   revision 2019-01-01 {
     description "Junos: 19.3R1.8";
   }

   rpc get-security-alarm-information {
     description "Show active security alarm information";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       choice output_c {
         case output-tag {
           leaf output {
             type string;
           }
         }
         case actual-tag {
           anyxml security-alarm-information;
         }
         case multichassis-tag {
           anyxml multi-routing-engine-results;
         }
       }
     }
   }
   rpc get-security-log-information {
     description "Show auditable security log information";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       choice output_c {
         case output-tag {
           leaf output {
             type string;
           }
         }
         case actual-tag {
           anyxml security-log-information;
         }
         case multichassis-tag {
           anyxml multi-routing-engine-results;
         }
       }
     }
   }
   rpc get-pki-certificate-request {
     description "Show PKCS-10 certificate request information";
     input {
       uses command-forwarding;
       choice daemon-select {
         case logical-system {
         }
       }
       leaf certificate-id {
         description "Certificate identifier";
         type string {
           length "1 .. 32";
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-ca-certificate {
     description "Show certificate-authority certificate information";
     input {
       uses command-forwarding;
       choice daemon-select {
         case logical-system {
         }
       }
       choice ca-cert-choice {
         case ca-profile {
           leaf ca-profile {
             description "Certificate authority profile";
             type string {
               length "1 .. 32";
             }
           }
         }
         case ca-profile-group {
           leaf ca-profile-group {
             description "Show CA profile group";
             type string {
               length "1 .. 32";
             }
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-local-certificate {
     description "Show router certificate information";
     input {
       uses command-forwarding;
       choice daemon-select {
         case logical-system {
         }
       }
       choice certificate-choice {
         case certificate-id {
           leaf certificate-id {
             description "Certificate identifier";
             type string {
               length "1 .. 32";
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-crl {
     description "Show certificate revocation list information";
     input {
       uses command-forwarding;
       choice daemon-select {
         case logical-system {
         }
       }
       leaf ca-profile {
         description "Certificate authority profile";
         type string {
           length "1 .. 32";
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pkid-crl-information-list;
         }
         case multichassis-tag {
           anyxml multi-routing-engine-results;
         }
       }
     }
   }
   rpc get-idp-application-system-cache {
     description "Show IDP application system cache";
     output {
       choice output_c {
         case output-tag {
           leaf output {
             type string;
           }
         }
         case actual-tag {
           anyxml idp-application-system-cache-information;
         }
         case multichassis-tag {
           anyxml multi-routing-engine-results;
         }
       }
     }
   }
   rpc get-idp-active-policy {
     description "Show active IDP policy";
     status deprecated;
     output {
       choice output_c {
         case output-tag {
           leaf output {
             type string;
           }
         }
         case actual-tag {
           anyxml idp-version-information;
         }
         case multichassis-tag {
           anyxml multi-routing-engine-results;
         }
       }
     }
   }
   rpc get-idp-policy-commit-status {
     description "Show the status of ongoing policy compilation and load";
     input {
       uses command-forwarding;
       choice re-selector-idpd {
         case re0 {
         }
         case re1 {
         }
       }
       leaf clear {
         description "Clears the policy commit status";
         type empty;
       }
     }
     output {
       choice output_c {
         case output-tag {
           leaf output {
             type string;
           }
         }
         case actual-tag {
           anyxml idp-policy-commit-status;
         }
         case multichassis-tag {
           anyxml multi-routing-engine-results;
         }
       }
     }
   }
   rpc get-idp-security-package-proxy-information {
     description "Show proxy profile details";
     output {
       choice output_c {
         case output-tag {
           leaf output {
             type string;
           }
         }
         case actual-tag {
           anyxml idp-security-package-proxy-profile;
         }
         case multichassis-tag {
           anyxml multi-routing-engine-results;
         }
       }
     }
   }
   rpc get-idp-security-package-information {
     description "Show the version of currently installed security-package";
     input {
       uses command-forwarding;
       choice re-selector-idpd {
         case re0 {
         }
         case re1 {
         }
       }
     }
     output {
       choice output_c {
         case output-tag {
           leaf output {
             type string;
           }
         }
         case actual-tag {
           anyxml idp-security-package-information;
         }
         case multichassis-tag {
           anyxml multi-routing-engine-results;
         }
       }
     }
   }
   rpc get-idp-recent-security-package-information {
     description "List ten most recent security package versions";
     input {
       uses command-forwarding;
       choice re-selector-idpd {
         case re0 {
         }
         case re1 {
         }
       }
     }
     output {
       choice output_c {
         case output-tag {
           leaf output {
             type string;
           }
         }
         case actual-tag {
           anyxml idp-recent-security-package-information;
         }
         case multichassis-tag {
           anyxml multi-routing-engine-results;
         }
       }
     }
   }
   rpc get-idp-memory-information {
     description "Show IDP data plane memory statistics";
     output {
       choice output_c {
         case output-tag {
           leaf output {
             type string;
           }
         }
         case actual-tag {
           anyxml idp-memory-information;
         }
         case multichassis-tag {
           anyxml multi-routing-engine-results;
         }
       }
     }
   }
   rpc get-idp-subscriber-policy-list {
     description "Show the list of currently installed policies";
     input {
       uses command-forwarding;
       choice lsys {
         case logical-system {
         }
       }
     }
     output {
       choice output_c {
         case output-tag {
           leaf output {
             type string;
           }
         }
         case actual-tag {
           anyxml idp-subscriber-policy-list;
         }
         case multichassis-tag {
           anyxml multi-routing-engine-results;
         }
       }
     }
   }
   rpc get-idp-policy-template-information {
     description "Show available policy templates";
     output {
       choice output_c {
         case output-tag {
           leaf output {
             type string;
           }
         }
         case actual-tag {
           anyxml idp-policy-template-information;
         }
         case multichassis-tag {
           anyxml multi-routing-engine-results;
         }
       }
     }
   }
   rpc get-idp-status-information {
     description "Show IDP status";
     output {
       choice output_c {
         case output-tag {
           leaf output {
             type string;
           }
         }
         case actual-tag {
           anyxml idp-status-information;
         }
         case multichassis-tag {
           anyxml multi-routing-engine-results;
         }
       }
     }
   }
   rpc get-idp-detail-status-information {
     description "Show IDP detail status";
     output {
       choice output_c {
         case output-tag {
           leaf output {
             type string;
           }
         }
         case actual-tag {
           anyxml idp-detail-status-information;
         }
         case multichassis-tag {
           anyxml multi-routing-engine-results;
         }
       }
     }
   }
   rpc get-idp-predefined-attack-groups {
     description "Show predefined attack groups";
     output {
       choice output_c {
         case output-tag {
           leaf output {
             type string;
           }
         }
         case actual-tag {
           anyxml idp-predefined-attack-groups;
         }
         case multichassis-tag {
           anyxml multi-routing-engine-results;
         }
       }
     }
   }
   rpc get-idp-predefined-attack-group-filters {
     description "Configure filters";
     input {
       uses command-forwarding;
       choice re-selector-idpd {
         case re0 {
         }
         case re1 {
         }
       }
       leaf category {
         description "Category of attack group";
         type string;
       }
     }
     output {
       choice output_c {
         case output-tag {
           leaf output {
             type string;
           }
         }
         case actual-tag {
           anyxml idp-predefined-attack-group-filters;
         }
         case multichassis-tag {
           anyxml multi-routing-engine-results;
         }
       }
     }
   }
   rpc get-idp-predefined-attacks {
     description "Show predefined attacks";
     output {
       choice output_c {
         case output-tag {
           leaf output {
             type string;
           }
         }
         case actual-tag {
           anyxml idp-predefined-attacks;
         }
         case multichassis-tag {
           anyxml multi-routing-engine-results;
         }
       }
     }
   }
   rpc get-idp-predefined-attack-filters {
     description "Configure filters";
     input {
       uses command-forwarding;
       choice re-selector-idpd {
         case re0 {
         }
         case re1 {
         }
       }
       leaf category {
         description "Category of attack";
         type string;
       }
       leaf severity {
         description "Severity of attack";
         type enumeration {
           enum "info" {
             description "Provide information of attack when it matches";
           }
           enum "warning" {
             description "The attack is a minor one";
           }
           enum "minor" {
             description "The attack is a minor one";
           }
           enum "major" {
             description "The attack is a major one";
           }
           enum "critical" {
             description "The attack is a critical one";
           }
         }
       }
       leaf direction {
         description "Direction of attack";
         type enumeration {
           enum "client-to-server" {
             description "Select attacks from client to server";
           }
           enum "server-to-client" {
             description "Select attacks from server to client";
           }
           enum "any" {
             description "Select attacks which can occur in either direction";
           }
           enum "exclude-client-to-server" {
             description "Filter out attacks from client to server";
           }
           enum "exclude-server-to-client" {
             description "Filter out attacks from server to client";
           }
           enum "exclude-any" {
             description "Filter out attacks which are in any direction";
           }
         }
       }
     }
     output {
       choice output_c {
         case output-tag {
           leaf output {
             type string;
           }
         }
         case actual-tag {
           anyxml idp-predefined-attack-filters;
         }
         case multichassis-tag {
           anyxml multi-routing-engine-results;
         }
       }
     }
   }
   rpc get-idp-counter-information {
     description "Show IDP counters";
     output {
       choice output_c {
         case output-tag {
           leaf output {
             type string;
           }
         }
         case actual-tag {
           anyxml idp-counter-information;
         }
         case multichassis-tag {
           anyxml multi-routing-engine-results;
         }
       }
     }
   }
   rpc get-idp-counters-packet {
     description "Show IDP Packet counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-tcp-reass {
     description "Show IDP Reassembler counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-ips {
     description "Show IPS counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-flow {
     description "Show IDP Flow counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-dfa {
     description "Show IDP DFA counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-log {
     description "Show IDP Log counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-pol-mngr {
     description "Show IDP Policy counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-packet-log {
     description "Show IDP Packet capture counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-appid {
     description "Show Application Identification counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-memory {
     description "Show IDP memory counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-action {
     description "Show IDP policy action counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-pdf-decoder {
     description "Show the PDF decoder counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-counters-http-decoder {
     description "Show the HTTP decoder counters";
     input {
       uses command-forwarding;
       choice lsys {
         case logical-system {
         }
       }
     }
     output {
       choice output_c {
         case output-tag {
           leaf output {
             type string;
           }
         }
         case multichassis-tag {
           anyxml multi-routing-engine-results;
         }
       }
     }
   }
   rpc get-idp-applications-information {
     description "Show IDP application statistics";
     output {
       choice output_c {
         case output-tag {
           leaf output {
             type string;
           }
         }
         case actual-tag {
           anyxml idp-applications-information;
         }
         case multichassis-tag {
           anyxml multi-routing-engine-results;
         }
       }
     }
   }
   rpc get-idp-attack-table-information {
     description "Show IDP attack table";
     input {
       uses command-forwarding;
       choice lsys {
         case logical-system {
         }
       }
     }
     output {
       choice output_c {
         case output-tag {
           leaf output {
             type string;
           }
         }
         case actual-tag {
           anyxml idp-attack-table-information;
         }
         case multichassis-tag {
           anyxml multi-routing-engine-results;
         }
       }
     }
   }
   rpc get-idp-attack-deprecated-list-information {
     description "Show IDP attack deprecated-list";
     output {
       choice output_c {
         case output-tag {
           leaf output {
             type string;
           }
         }
         case actual-tag {
           anyxml idp-attack-deprecated-list-information;
         }
         case multichassis-tag {
           anyxml multi-routing-engine-results;
         }
       }
     }
   }
   rpc get-idp-policy-deprecated-attack-information {
     description "Show IDP attack deprecated-list for the configured policy";
     input {
       leaf policy {
         description "IDP policy name";
         type string;
       }
     }
     output {
       choice output_c {
         case output-tag {
           leaf output {
             type string;
           }
         }
         case actual-tag {
           anyxml idp-policy-deprecated-attack-information;
         }
         case multichassis-tag {
           anyxml multi-routing-engine-results;
         }
       }
     }
   }
   rpc get-idp-attack-description-information {
     description "Show description of specified attack";
     input {
       leaf attack-name {
         description "Attack name";
         type string;
         mandatory true;
       }
     }
     output {
       choice output_c {
         case output-tag {
           leaf output {
             type string;
           }
         }
         case actual-tag {
           anyxml idp-attack-description-information;
         }
         case multichassis-tag {
           anyxml multi-routing-engine-results;
         }
       }
     }
   }
   rpc get-idp-attack-detail-information {
     description "Show details of specified attack";
     input {
       leaf attack-name {
         description "Attack name";
         type string;
         mandatory true;
       }
     }
     output {
       choice output_c {
         case output-tag {
           leaf output {
             type string;
           }
         }
         case actual-tag {
           anyxml idp-attack-detail-information;
         }
         case multichassis-tag {
           anyxml multi-routing-engine-results;
         }
       }
     }
   }
   rpc get-idp-attack-group-entry-detail-information {
     description "Show detail of all attack and group";
     input {
       leaf offset {
         description "Offset value to start with (0 to any number)";
         type union {
           type uint32;
           type string {
             pattern "<.*>|$.*";
           }
         }
       }
       leaf limit {
         description "Number of entries to display";
         type union {
           type string {
             pattern "<.*>|$.*";
           }
           type int32 {
             range "1 .. 50";
           }
         }
       }
     }
     output {
       choice output_c {
         case output-tag {
           leaf output {
             type string;
           }
         }
         case actual-tag {
           anyxml idp-attack-group-entry-detail-information;
         }
         case multichassis-tag {
           anyxml multi-routing-engine-results;
         }
       }
     }
   }
   rpc get-idp-attack-group-entry-filters-information {
     description "Show detail of all attack and group which match the provided filters";
     input {
       leaf-list category {
         ordered-by user;
         description "Category of attack";
         type string;
       }
       leaf-list type-attack {
         ordered-by user;
         description "Type of attack";
         type enumeration {
           enum "0" {
             description "Static attack";
           }
           enum "1" {
             description "Dynamic attack";
           }
         }
       }
       leaf-list recommended-action {
         ordered-by user;
         description "Recommended action";
         type enumeration {
           enum "0" {
             description "None";
           }
           enum "1" {
             description "Close client and server";
           }
           enum "2" {
             description "Close client";
           }
           enum "3" {
             description "Close server";
           }
           enum "4" {
             description "Ignore";
           }
           enum "5" {
             description "Drop";
           }
           enum "6" {
             description "Drop packet";
           }
         }
       }
       leaf-list attack-type {
         ordered-by user;
         description "Attack type";
         type enumeration {
           enum "0" {
             description "Attack type - signature";
           }
           enum "1" {
             description "Attack type - anomaly";
           }
           enum "2" {
             description "Attack type - chain";
           }
         }
       }
       leaf-list performance {
         ordered-by user;
         description "Performance category type";
         type enumeration {
           enum "0" {
             description "Performance 0 - unknown";
           }
           enum "1" {
             description "Performance 1 - low";
           }
           enum "5" {
             description "Performance 5 - medium ";
           }
           enum "9" {
             description "Performance 9 - high";
           }
         }
       }
       leaf-list severity {
         ordered-by user;
         description "Severity of attack";
         type enumeration {
           enum "0" {
             description "Info attack";
           }
           enum "1" {
             description "Warning attack";
           }
           enum "2" {
             description "Minor attack";
           }
           enum "3" {
             description "Major attack";
           }
           enum "4" {
             description "Critical attack`";
           }
         }
       }
       leaf-list direction {
         ordered-by user;
         description "Direction of attack";
         type enumeration {
           enum "0" {
             description "Select attacks from client to server";
           }
           enum "1" {
             description "Select attacks from server to client";
           }
           enum "2" {
             description "Select attacks which can occur in either direction";
           }
         }
       }
       leaf-list recommended {
         ordered-by user;
         description "Recommended attack or not";
         type enumeration {
           enum "0" {
             description "Non recommended attack";
           }
           enum "1" {
             description "Recommended attack";
           }
         }
       }
       leaf-list group-name {
         ordered-by user;
         description "Group name";
         type string;
       }
       leaf-list group-type {
         ordered-by user;
         description "Group type";
         type enumeration {
           enum "0" {
             description "Predefined group";
           }
           enum "1" {
             description "Custom attack";
           }
           enum "2" {
             description "Custom attack group";
           }
           enum "3" {
             description "Predefined attack";
           }
         }
       }
       leaf-list service {
         ordered-by user;
         description "Attack service type";
         type string;
       }
       leaf-list cve-id {
         ordered-by user;
         description "Cve identifier";
         type string;
       }
       leaf-list certificate {
         ordered-by user;
         description "Certificate identifier";
         type string;
       }
       leaf-list bug-id {
         ordered-by user;
         description "Bug identifier";
         type string;
       }
       leaf-list false-positive {
         ordered-by user;
         description "Attack falsepositive type";
         type enumeration {
           enum "0" {
             description "Falsepositive category - unknown";
           }
           enum "1" {
             description "Falsepositive category - occassionally";
           }
           enum "2" {
             description "Falsepositive category - frequently";
           }
           enum "3" {
             description "Falsepositive category - rarely";
           }
         }
       }
       leaf limit {
         description "Number of entries to display";
         type union {
           type string {
             pattern "<.*>|$.*";
           }
           type int32 {
             range "1 .. 50";
           }
         }
       }
       leaf offset {
         description "Offset to start with (0 to any number)";
         type union {
           type uint32;
           type string {
             pattern "<.*>|$.*";
           }
         }
       }
     }
     output {
       choice output_c {
         case output-tag {
           leaf output {
             type string;
           }
         }
         case actual-tag {
           anyxml idp-attack-group-entry-filters-information;
         }
         case multichassis-tag {
           anyxml multi-routing-engine-results;
         }
       }
     }
   }
   rpc get-idp-group-attacklist-information {
     description "Shows list of all attacks present in the attack group specified";
     input {
       choice filter-choice {
         case predefined-group {
           leaf predefined-group {
             description "Predefined group name";
             type string;
           }
         }
         case custom-group {
           leaf custom-group {
             description "Custom group name";
             type string;
           }
         }
         case dynamic-group {
           leaf dynamic-group {
             description "Dynamic group name";
             type string;
           }
         }
         case policy {
           leaf policy {
             description "IDP policy name";
             type string;
           }
         }
       }
     }
     output {
       choice output_c {
         case output-tag {
           leaf output {
             type string;
           }
         }
         case actual-tag {
           anyxml idp-group-attacklist-information;
         }
         case multichassis-tag {
           anyxml multi-routing-engine-results;
         }
       }
     }
   }
   rpc get-idp-group-forattack-information {
     description "Shows list of predefined attack-groups to which the predefined-attack belongs";
     input {
       leaf attack-name {
         description "Attack name";
         type string;
         mandatory true;
       }
     }
     output {
       choice output_c {
         case output-tag {
           leaf output {
             type string;
           }
         }
         case actual-tag {
           anyxml idp-group-forattack-information;
         }
         case multichassis-tag {
           anyxml multi-routing-engine-results;
         }
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml hakr-keychain-information;
         }
         case multichassis-tag {
           anyxml multi-routing-engine-results;
         }
       }
     }
   }
   rpc get-mka-session-information {
     description "Show MKA sessions information";
     input {
       leaf verbosity_level {
         default "brief";
         type enumeration {
           enum "summary" {
             description "Display summary output";
           }
           enum "brief" {
             description "Display brief output (default)";
           }
           enum "detail" {
             description "Display detailed output";
           }
         }
       }
     }
     output {
       choice output_c {
         case output-tag {
           leaf output {
             type string;
           }
         }
         case actual-tag {
           anyxml mka-session-information;
         }
         case multichassis-tag {
           anyxml multi-routing-engine-results;
         }
       }
     }
   }
   rpc get-mka-session-interface-information {
     description "Show MKA session on this interface";
     input {
       leaf verbosity_level {
         default "brief";
         type enumeration {
           enum "summary" {
             description "Display summary output";
           }
           enum "brief" {
             description "Display brief output (default)";
           }
           enum "detail" {
             description "Display detailed output";
           }
         }
       }
       leaf interface-name {
         description "Show MKA session for this interface";
         default "all";
         type string {
         }
       }
     }
     output {
       choice output_c {
         case output-tag {
           leaf output {
             type string;
           }
         }
         case actual-tag {
           anyxml mka-session-information;
         }
         case multichassis-tag {
           anyxml multi-routing-engine-results;
         }
       }
     }
   }
   rpc get-mka-statistics {
     description "Show MKA statistics";
     output {
       choice output_c {
         case output-tag {
           leaf output {
             type string;
           }
         }
         case actual-tag {
           anyxml mka-statistics;
         }
         case multichassis-tag {
           anyxml multi-routing-engine-results;
         }
       }
     }
   }
   rpc get-mka-interface-statistics {
     description "Show MKA statistics on this interface";
     input {
       leaf interface-name {
         description "Show MKA statistics for this interface";
         default "all";
         type string {
         }
       }
     }
     output {
       choice output_c {
         case output-tag {
           leaf output {
             type string;
           }
         }
         case actual-tag {
           anyxml mka-statistics;
         }
         case multichassis-tag {
           anyxml multi-routing-engine-results;
         }
       }
     }
   }
   rpc get-macsec-connection-information {
     description "Show MAC Security connections information";
     output {
       choice output_c {
         case output-tag {
           leaf output {
             type string;
           }
         }
         case actual-tag {
           anyxml macsec-connection-information;
         }
         case multichassis-tag {
           anyxml multi-routing-engine-results;
         }
       }
     }
   }
   rpc get-macsec-connection-interface-information {
     description "Show MAC security connections on this interface";
     input {
       leaf interface-name {
         description "Show MAC security connections for this interface";
         default "all";
         type string {
         }
       }
     }
     output {
       choice output_c {
         case output-tag {
           leaf output {
             type string;
           }
         }
         case actual-tag {
           anyxml macsec-connection-information;
         }
         case multichassis-tag {
           anyxml multi-routing-engine-results;
         }
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml macsec-statistics;
         }
         case multichassis-tag {
           anyxml multi-routing-engine-results;
         }
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type string {
         }
       }
     }
     output {
       choice output_c {
         case output-tag {
           leaf output {
             type string;
           }
         }
         case actual-tag {
           anyxml macsec-statistics;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
