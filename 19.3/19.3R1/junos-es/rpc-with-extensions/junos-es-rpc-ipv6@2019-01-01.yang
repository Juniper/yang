/*
 * Copyright (c) 2019 Juniper Networks, Inc.
 * All rights reserved.
 */
 module junos-es-rpc-ipv6 {
   namespace "http://yang.juniper.net/junos-es/rpc/ipv6";

   prefix ipv6;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for ipv6 command(s)";

   revision 2019-01-01 {
     description "Junos: 19.3R1.8";
   }

   rpc get-ipv6-nd-information {
     description "Show IPv6 neighbor cache information";
     input {
       leaf host {
         description "Neighbor host IPV6 address";
         type string;
       }
       leaf interface {
         description "Name of the interface";
         type string;
       }
       leaf logical-system {
         description "Name of logical system";
         type string;
       }
       leaf vpn {
         description "Name of VPN routing table";
         type string;
       }
       leaf reference-count {
         description "Next hop reference count";
         type empty;
       }
       leaf flags {
         description "Next hop flags";
         type empty;
       }
       leaf tenant {
         description "Name of tenant";
         type string {
           junos:posix-pattern "^[a-zA-Z0-9-]{1,63}$";
           junos:pattern-message "Tenant name is a string consisting of up to 63 letters, numbers and dashes";
         }
       }
     }
     output {
       choice output_c {
         case output-tag {
           leaf output {
             type string;
           }
         }
         case actual-tag {
           anyxml ipv6-nd-information;
         }
         case multichassis-tag {
           anyxml multi-routing-engine-results;
         }
       }
     }
   }
   rpc get-ipv6-ra-information {
     description "Show IPv6 router advertisement information";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf interface {
         description "Name of interface";
         type string;
       }
       leaf conflicts {
         description "Display conflicting information";
         type empty;
       }
       leaf prefix {
         description "Prefix and optional prefix length";
         type jt:ipv6prefix;
       }
       leaf virtual-router {
         description "Display only virtual-interface information";
         type empty;
       }
     }
     output {
       choice output_c {
         case output-tag {
           leaf output {
             type string;
           }
         }
         case actual-tag {
           anyxml ipv6-ra-information;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
