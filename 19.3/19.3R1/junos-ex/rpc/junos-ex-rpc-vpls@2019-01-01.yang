/*
 * Copyright (c) 2019 Juniper Networks, Inc.
 * All rights reserved.
 */
 module junos-ex-rpc-vpls {
   namespace "http://yang.juniper.net/junos-ex/rpc/vpls";

   prefix vpls;

   import junos-common-types {
     prefix jt;
   }

   organization "Juniper Networks, Inc.";

   contact "yang-support@juniper.net";

   description "Junos RPC YANG module for vpls command(s)";

   revision 2019-01-01 {
     description "Junos: 19.3R1.8";
   }

   rpc get-vpls-connection-information {
     description "Show VPLS connections information";
     input {
       choice daemon-select {
         case logical-system {
           leaf logical-system {
             description "Name of logical system, or 'all'";
             type string {
             }
           }
         }
       }
       leaf instance {
         description "Name of VPLS instance";
         default "all";
         type string;
       }
       leaf local-site {
         description "Name or ID of VPLS local site";
         default "all";
         type string;
       }
       leaf remote-site {
         description "ID of VPLS remote site";
         default "all";
         type string;
       }
       leaf state {
         default "up-down";
         type enumeration {
           enum "down" {
             description "Display nonoperational connections";
           }
           enum "up" {
             description "Display operational connections";
           }
           enum "up-down" {
             description "Display both non- and operational connections (default)";
           }
         }
       }
       leaf level {
         default "status";
         type enumeration {
           enum "brief" {
             description "Display one-line version of output";
           }
           enum "extensive" {
             description "Display connection status and history";
           }
           enum "history" {
             description "Display connection history";
           }
           enum "instance-history" {
             description "Display instance history";
           }
           enum "status" {
             description "Display connection and circuit status (default)";
           }
           enum "summary" {
             description "Display summary output";
           }
         }
       }
     }
     output {
       choice output_c {
         case output-tag {
           leaf output {
             type string;
           }
         }
         case actual-tag {
           anyxml vpls-connection-information;
         }
         case multichassis-tag {
           anyxml multi-routing-engine-results;
         }
       }
     }
   }
   rpc get-vpls-statistics-information {
     description "Show VPLS statistics information";
     input {
       choice daemon-select {
         case logical-system {
           leaf logical-system {
             description "Name of logical system, or 'all'";
             type string {
             }
           }
         }
       }
       leaf instance {
         description "Name of VPLS instance";
         default "all";
         type string;
       }
     }
     output {
       choice output_c {
         case output-tag {
           leaf output {
             type string;
           }
         }
         case actual-tag {
           anyxml vpls-statistics-information;
         }
         case multichassis-tag {
           anyxml multi-routing-engine-results;
         }
       }
     }
   }
   rpc get-vpls-mac-table {
     description "Show media access control table";
     input {
       leaf instance {
         description "Display information for a specified vpls";
         default "all";
         type string;
       }
       leaf logical-system {
         description "Name of logical system, or 'all'";
         default "all";
         type string {
         }
       }
       leaf vlan-id {
         description "Display MAC address learned on a specified VLAN";
         type string;
       }
       leaf isid {
         description "Display Information for specified ISID or all ISID(s)";
         type string;
       }
       leaf address {
         description "MAC address";
         default "all";
         type jt:mac-addr;
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       choice output_c {
         case output-tag {
           leaf output {
             type string;
           }
         }
         case actual-tag {
           anyxml l2ald-rtb-macdb;
         }
         case multichassis-tag {
           anyxml multi-routing-engine-results;
         }
       }
     }
   }
   rpc get-vpls-interface-mac-table {
     description "Display MAC table for a specified interface";
     input {
       choice interface-choice {
         case interface-name {
           leaf interface-name {
             description "Name of interface for which to display table";
             type string;
           }
         }
         case all {
           leaf all {
             description "Display MAC table for all the interfaces";
             type empty;
           }
         }
       }
       leaf show-choice {
         default "brief";
         type enumeration {
           enum "detail" {
             description "Display detailed output";
           }
           enum "brief" {
             description "Display brief output";
           }
           enum "extensive" {
             description "Display extensive output";
           }
           enum "count" {
             description "Display count only";
           }
           enum "age" {
             description "Display age of a single mac-address";
           }
           enum "summary" {
             description "Display summary output";
           }
         }
       }
     }
     output {
       choice output_c {
         case output-tag {
           leaf output {
             type string;
           }
         }
         case actual-tag {
           anyxml l2ald-interface-macdb;
         }
         case multichassis-tag {
           anyxml multi-routing-engine-results;
         }
       }
     }
   }
   rpc get-vpls-flood-information {
     description "Show VPLS flooding information";
     input {
       leaf logical-system {
         description "Name of logical system, or 'all'";
         default "all";
         type string {
         }
       }
       leaf instance {
         description "Display information for a specified vpls";
         default "all";
         type string;
       }
       leaf verbosity {
         default "detail";
         type enumeration {
           enum "detail" {
             description "Display detailed output";
           }
           enum "brief" {
             description "Display brief output";
           }
           enum "extensive" {
             description "Display extensive output";
           }
         }
       }
     }
     output {
       choice output_c {
         case output-tag {
           leaf output {
             type string;
           }
         }
         case actual-tag {
           anyxml l2ald-vpls-flood-instance;
         }
         case multichassis-tag {
           anyxml multi-routing-engine-results;
         }
       }
     }
   }
   rpc get-vpls-ce-flood-route-information {
     description "Show customer edge flood route";
     input {
       leaf interface {
         description "Interface for which to show CE flood route";
         type union {
           type jt:interface-unit;
           type string {
             pattern "<.*>|$.*";
           }
         }
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-vpls-all-ce-flood-route-information {
     description "Show route for flooding traffic to all CE routers";
     input {
       leaf logical-system {
         description "Name of logical system";
         type string {
         }
       }
       leaf instance {
         description "Display information for a specified vpls";
         type string;
         mandatory true;
       }
     }
     output {
       choice output_c {
         case output-tag {
           leaf output {
             type string;
           }
         }
         case actual-tag {
           anyxml l2ald-vpls-flood-route-information;
         }
         case multichassis-tag {
           anyxml multi-routing-engine-results;
         }
       }
     }
   }
   rpc get-vpls-event-queue-information {
     description "Show queue of pending VPLS flood events";
     output {
       choice output_c {
         case output-tag {
           leaf output {
             type string;
           }
         }
         case actual-tag {
           anyxml l2ald-vpls-flood-event-queue;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
