/*
 * Copyright (c) 2020 Juniper Networks, Inc.
 * All rights reserved.
 */
 module junos-ex-rpc-ping {
   namespace "http://yang.juniper.net/junos-ex/rpc/ping";

   prefix ping;

   import junos-common-ddl-extensions {
     prefix junos;
     revision-date 2019-01-01;
   }

   import junos-common-odl-extensions {
     prefix junos-odl;
     revision-date 2019-01-01;
   }

   import junos-common-types {
     prefix jt;
     revision-date 2019-01-01;
   }

   organization "Juniper Networks, Inc.";

   contact "yang-support@juniper.net";

   description "Junos RPC YANG module for ping command(s)";

   revision 2019-01-01 {
     description "Junos: 20.1R1.11";
   }

   rpc ping {
     description "Ping remote target";
     input {
       leaf count {
         description "Number of ping requests to send";
         units "packets";
         type union {
           type string {
             pattern "<.*>|$.*";
           }
           type uint32 {
             range "1 .. 2000000000";
           }
         }
       }
       leaf wait {
         description "Maximum wait time after sending final packet";
         units "seconds";
         type union {
           type uint32;
           type string {
             pattern "<.*>|$.*";
           }
         }
       }
       leaf no-resolve {
         description "Don't attempt to print addresses symbolically";
         type empty;
       }
       leaf rapid {
         description "Send requests rapidly (default count of 5)";
         type empty;
       }
       leaf record-route {
         description "Record and report packet's path (IPv4)";
         type empty;
       }
       leaf brief {
         status deprecated;
         type empty;
       }
       leaf detail {
         description "Display incoming interface of received packet";
         type empty;
       }
       leaf do-not-fragment {
         description "Don't fragment echo request packets (IPv4)";
         type empty;
       }
       leaf-list loose-source {
         ordered-by user;
         description "Intermediate loose source route entry (IPv4)";
         type string;
       }
       leaf interface {
         description "Source interface (multicast, all-ones, unrouted packets)";
         type string;
       }
       leaf interval {
         description "Delay between ping requests";
         units "seconds";
         type string;
       }
       leaf source {
         description "Source address of echo request";
         type string;
       }
       leaf pattern {
         description "Hexadecimal fill pattern";
         type string;
       }
       leaf size {
         description "Size of request packets";
         units "bytes";
         type union {
           type string {
             pattern "<.*>|$.*";
           }
           type uint32 {
             range "0 .. 65468";
           }
         }
       }
       leaf strict {
         description "Use strict source route option (IPv4)";
         type empty;
       }
       leaf-list strict-source {
         ordered-by user;
         description "Intermediate strict source route entry (IPv4)";
         type string;
       }
       leaf ttl {
         description "IP time-to-live value (IPv6 hop-limit value)";
         units "hops";
         type union {
           type string {
             pattern "<.*>|$.*";
           }
           type uint32 {
             range "1 .. 255";
           }
         }
       }
       leaf verbose {
         description "Display detailed output";
         type empty;
       }
       leaf tos {
         description "IP type-of-service value";
         type union {
           type string {
             pattern "<.*>|$.*";
           }
           type uint32 {
             range "0 .. 255";
           }
         }
       }
       leaf bypass-routing {
         description "Bypass routing table, use specified interface";
         type empty;
       }
       leaf inet {
         description "Force ping to IPv4 destination";
         type empty;
       }
       leaf inet6 {
         description "Force ping to IPv6 destination";
         type empty;
       }
       leaf routing-instance {
         description "Routing instance for ping attempt";
         type string;
       }
       leaf mac-address {
         description "MAC address of the nexthop in xx:xx:xx:xx:xx:xx format";
         type jt:mac-unicast;
       }
       leaf host {
         description "Hostname or IP address of remote host";
         type string;
         mandatory true;
       }
       leaf logical-system {
         description "Name of logical system";
         type string {
           junos:posix-pattern "^[a-zA-Z0-9_-]{1,63}$";
           junos:pattern-message "Logical-system name is a string consisting of up to 63 letters, numbers, dashes and underscores";
         }
       }
     }
     output {
       choice output_c {
         case output-tag {
           leaf output {
             type string;
           }
         }
         case actual-tag {
           anyxml ping-results;
         }
         case multichassis-tag {
           anyxml multi-routing-engine-results;
         }
       }
     }
   }
   rpc request-ping-ethernet {
     description "Ping to an ethernet host by unicast mac address";
     input {
       leaf wait {
         description "Delay after sending last packet";
         units "seconds";
         type union {
           type string {
             pattern "<.*>|$.*";
           }
           type int32 {
             range "1 .. 255";
           }
         }
       }
       leaf size {
         description "Size of data TLV in request packets";
         units "bytes";
         type union {
           type string {
             pattern "<.*>|$.*";
           }
           type int32 {
             range "1 .. 1400";
           }
         }
       }
       leaf count {
         description "Number of ping requests to send";
         type union {
           type string {
             pattern "<.*>|$.*";
           }
           type int32 {
             range "1 .. 65535";
           }
         }
       }
       leaf maintenance-domain {
         description "Name of maintenance domain";
         type string {
           length "1 .. 45";
         }
         mandatory true;
       }
       leaf maintenance-association {
         description "Name of maintenance association";
         type string {
           length "1 .. 45";
         }
         mandatory true;
       }
       leaf host {
         description "MAC address of remote host in xx:xx:xx:xx:xx:xx format";
         type jt:mac-addr;
       }
       leaf mep {
         description "MEP identifier of remote host (default 1)";
         type union {
           type string {
             pattern "<.*>|$.*";
           }
           type int32 {
             range "1 .. 8191";
           }
         }
       }
       leaf local-mep {
         description "MEP identifier of local host";
         type union {
           type string {
             pattern "<.*>|$.*";
           }
           type int32 {
             range "1 .. 8191";
           }
         }
       }
       leaf priority {
         description "Frame priority (802.1p) value";
         type union {
           type string {
             pattern "<.*>|$.*";
           }
           type int32 {
             range "0 .. 7";
           }
         }
       }
       leaf rapid {
         description "Send requests rapidly ";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml ethping-results;
         }
         case multichassis-tag {
           anyxml multi-routing-engine-results;
         }
       }
     }
   }
   rpc request-ping-ce-ip {
     input {
       leaf ip {
         description "IPv4/IPv6 address or prefix of CE to be pinged";
         type string;
         mandatory true;
       }
       leaf instance {
         description "VPLS or EVPN instance name";
         type string;
         mandatory true;
       }
       leaf source-ip {
         description "Source IP address";
         type jt:ipv4addr;
         mandatory true;
       }
       leaf count {
         description "Number of ping requests to send";
         default "1000000";
         units "packets";
         type union {
           type string {
             pattern "<.*>|$.*";
           }
           type uint32 {
             range "1 .. 1000000";
           }
         }
       }
       leaf vni {
         description "VXLAN Network Identifier";
         type union {
           type string {
             pattern "<.*>|$.*";
           }
           type uint32 {
             range "1 .. 16777214";
           }
         }
       }
     }
     output {
       choice output_c {
         case output-tag {
           leaf output {
             type string;
           }
         }
         case actual-tag {
           anyxml lsping-results;
         }
         case multichassis-tag {
           anyxml multi-routing-engine-results;
         }
       }
     }
   }
   rpc request-ping-rsvp-lsp {
     description "Ping RSVP-signaled LSP";
     input {
       leaf lsp-name {
         description "Name of LSP";
         type string {
           length "1 .. 64";
         }
         mandatory true;
       }
       leaf standby {
         description "Name of standby path";
         type string;
       }
       leaf multipoint {
         description "Probe multipoint LSP";
         type empty;
       }
       leaf egress {
         description "Request only a specific multipoint egress to respond";
         type jt:ipv4addr;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
     }
     output {
       choice output_c {
         case output-tag {
           leaf output {
             type string;
           }
         }
         case actual-tag {
           anyxml lsping-results;
         }
         case multichassis-tag {
           anyxml multi-routing-engine-results;
         }
       }
     }
   }
   rpc request-ping-rsvp-dynamic-bypass-lsp {
     description "Dynamically created LSP, used for protecting other LSPs";
     input {
       leaf lsp-name {
         description "Name of dynamic bypass LSP";
         type string {
           length "1 .. 64";
         }
         mandatory true;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-rsvp-manual-bypass-lsp {
     description "Manually configured LSP, used for protecting other LSPs";
     input {
       leaf lsp-name {
         description "Name of manual bypass LSP";
         type string {
           length "1 .. 64";
         }
         mandatory true;
       }
       leaf interface {
         description "Name of the interface, which is protected by this bypass";
         type union {
           type jt:interface-name;
           type string {
             pattern "<.*>|$.*";
           }
         }
         mandatory true;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-ldp-lsp {
     description "Ping LDP-signaled LSP";
     input {
       leaf fec {
         description "IP prefix/length of forwarding equivalence class";
         type jt:ipprefix;
         mandatory true;
       }
       leaf instance {
         description "Routing-instance name";
         type string;
       }
       leaf stitched-protocol {
         description "Protocol  stitched on intermidiate node";
         type enumeration {
           enum "ospf" {
             description "OSPF protocol";
           }
           enum "isis" {
             description "ISIS protocol";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-ldp-p2mp-lsp {
     description "Ping LDP-signaled P2MP LSP";
     input {
       leaf root-addr {
         description "IP address of p2mp lsp root";
         type jt:ipv4addr;
         mandatory true;
       }
       leaf lsp-id {
         description "LSP ID of p2mp lsp";
         type union {
           type string {
             pattern "<.*>|$.*";
           }
           type uint32 {
             range "1 .. 4294967295";
           }
         }
         mandatory true;
       }
       leaf egress {
         description "Request only a specific multipoint egress to respond";
         type jt:ipv4addr;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-ospf-lsp {
     description "Ping L-OSPF prefix";
     input {
       leaf fec {
         description "IP prefix/length of forwarding equivalence class";
         type jt:ipprefix;
         mandatory true;
       }
       leaf instance {
         description "Routing-instance name";
         type string;
       }
       leaf stitched-protocol {
         description "Protocol  stitched on intermediate node";
         type enumeration {
           enum "ldp" {
             description "LDP protocol";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-isis-lsp {
     description "Ping L-ISIS prefix";
     input {
       leaf fec {
         description "IP prefix/length of forwarding equivalence class";
         type jt:ipprefix;
         mandatory true;
       }
       leaf instance {
         description "Routing-instance name";
         type string;
       }
       leaf stitched-protocol {
         description "Protocol  stitched on intermidiate node";
         type enumeration {
           enum "ldp" {
             description "LDP protocol";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-segment-routing-egress-ip {
     description "Ping to/install IP address to use when sending probes";
     input {
       leaf egress-ip {
         description "To/Install IP address";
         type jt:ipprefix;
         mandatory true;
       }
       leaf color {
         description "Color identifier for the tunnel end-point";
         type union {
           type string {
             pattern "<.*>|$.*";
           }
           type uint32 {
             range "1 .. 4294967295";
           }
         }
       }
       leaf tunnel-source {
         description "Source protocol used to create tunnel";
         type enumeration {
           enum "static" {
             description "Static configuration";
           }
           enum "bgp-sr-te" {
             description "BGP-SR-TE configuration";
           }
         }
       }
       leaf skip-fec-validation {
         description "Skip fec validation";
         type empty;
       }
       leaf active {
         description "Use forwarding path/nexthops from the RIB table";
         type empty;
       }
       leaf secondary {
         description "Use configured secondary segment list for the given SR path";
         type empty;
       }
       leaf segment-list {
         description "Segment list to use when sending probes";
         type string {
           length "1 .. 64";
         }
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-segment-source-routing-path {
     description "Ping Source Path routing to use when sending probes";
     input {
       leaf lsp-name {
         description "Source path routing name";
         type string {
           length "1 .. 64";
         }
         mandatory true;
       }
       leaf tunnel-source {
         description "Source protocol used to create tunnel";
         type enumeration {
           enum "static" {
             description "Static configuration";
           }
           enum "pcep" {
             description "PCEP configuration";
           }
         }
       }
       leaf skip-fec-validation {
         description "Skip fec validation";
         type empty;
       }
       leaf active {
         description "Use forwarding path/nexthops from the RIB table";
         type empty;
       }
       leaf secondary {
         description "Use configured secondary segment list for the given SR path";
         type empty;
       }
       leaf egress-ip {
         description "To/Install address to use when sending probes";
         type jt:ipprefix;
       }
       leaf color {
         description "Color identifier for the tunnel end-point";
         type union {
           type string {
             pattern "<.*>|$.*";
           }
           type uint32 {
             range "1 .. 4294967295";
           }
         }
       }
       leaf segment-list {
         description "Segment list to use when sending probes";
         type string {
           length "1 .. 64";
         }
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-label-stack {
     description "Label stack for ping packets";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
       leaf-list labels {
         ordered-by user;
         description "Labels in label stack - [ label1, label2 ... label(top)]";
         type union {
           type string {
             pattern "<.*>|$.*";
           }
           type uint32 {
             range "16 .. 1048575";
           }
         }
       }
       leaf nexthop-interface {
         description "Outgoing interface for the traceroute packet";
         type string;
         mandatory true;
       }
       leaf nexthop-address {
         description "Nexthop IP address for the traceroute packet";
         type jt:ipaddr;
         mandatory true;
       }
       leaf egress {
         description "Eress IP address";
         type jt:ipaddr;
       }
       leaf detail {
         description "Display detailed output";
         type empty;
       }
     }
     output {
       choice output_c {
         case output-tag {
           leaf output {
             type string;
           }
         }
         case actual-tag {
           anyxml lsping-results;
         }
         case multichassis-tag {
           anyxml multi-routing-engine-results;
         }
       }
     }
   }
   rpc request-ping-bgp-lsp {
     description "Ping BGP-signaled LSP";
     input {
       leaf fec {
         description "IP prefix/length of forwarding equivalence class";
         type jt:ipprefix;
         mandatory true;
       }
       leaf bottom-label-ttl {
         description "Time to live for the bottom label in the label stack";
         type union {
           type string {
             pattern "<.*>|$.*";
           }
           type uint32 {
             range "1 .. 255";
           }
         }
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l3vpn {
     description "Ping LSP to Layer 3 VPN prefix";
     input {
       leaf l3vpn-name {
         description "Name of Layer 3 VPN";
         type string;
         mandatory true;
       }
       leaf prefix {
         description "IP prefix/length of Layer 3 VPN";
         type jt:ipprefix;
         mandatory true;
       }
       leaf bottom-label-ttl {
         description "Time to live for the bottom label in the label stack";
         type union {
           type string {
             pattern "<.*>|$.*";
           }
           type uint32 {
             range "1 .. 255";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2vpn-interface {
     description "Locate LSP using interface name";
     input {
       leaf interface-name {
         description "Interface name";
         type union {
           type jt:interface-name;
           type string {
             pattern "<.*>|$.*";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2vpn-instance {
     description "Instance to which this connection belongs";
     input {
       leaf instance-name {
         description "Layer 2 VPN name";
         type string;
         mandatory true;
       }
       leaf local-site-id {
         description "Layer 2 VPN local site identifier";
         type union {
           type string {
             pattern "<.*>|$.*";
           }
           type uint32 {
             range "1 .. 65534";
           }
         }
         mandatory true;
       }
       leaf remote-site-id {
         description "Layer 2 VPN remote site identifier";
         type union {
           type string {
             pattern "<.*>|$.*";
           }
           type uint32 {
             range "1 .. 65534";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2vpn-fec129-interface {
     description "Locate Pseudowire using interface name";
     input {
       leaf interface-name {
         description "Interface name";
         type union {
           type jt:interface-name;
           type string {
             pattern "<.*>|$.*";
           }
         }
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2vpn-fec129-instance {
     description "Instance to which this connection belongs";
     input {
       leaf instance-name {
         description "Layer 2 VPN name";
         type string;
         mandatory true;
       }
       leaf local-id {
         description "Layer 2 VPN Source Attachment Individual Identifier (SAII)";
         type string {
           junos:posix-pattern "^([[:digit:].]){0,15}$|^([[:digit:]]){0,10}:([[:digit:].]){0,15}:([[:digit:]]){1,10}$";
           junos:pattern-message "Invalid Local-id";
         }
         mandatory true;
       }
       leaf remote-id {
         description "Layer 2 VPN Target Attachment Individual Identifier (TAII)";
         type string {
           junos:posix-pattern "^([[:digit:].]){0,15}$|^([[:digit:]]){0,10}:([[:digit:].]){0,15}:([[:digit:]]){1,10}$";
           junos:pattern-message "Invalid Remode-id";
         }
         mandatory true;
       }
       leaf remote-pe-address {
         description "Layer 2 Remote PE address";
         type jt:ipv4addr;
         mandatory true;
       }
       leaf bottom-label-ttl {
         description "Time to live for the bottom label in the label stack";
         type union {
           type string {
             pattern "<.*>|$.*";
           }
           type uint32 {
             range "1 .. 255";
           }
         }
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2circuit-interface {
     description "Locate LSP from interface name";
     input {
       leaf v1 {
         description "Ping using Layer 2 circuit TLV (type 9)";
         type empty;
       }
       leaf interface-name {
         description "Interface name";
         type union {
           type jt:interface-name;
           type string {
             pattern "<.*>|$.*";
           }
         }
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-l2circuit-virtual-circuit {
     description "Locate LSP from virtual circuit information";
     input {
       leaf v1 {
         description "Ping using Layer 2 circuit TLV (type 9)";
         type empty;
       }
       leaf neighbor {
         description "Address of remote neighbor";
         type jt:ipprefix;
         mandatory true;
       }
       leaf virtual-circuit-id {
         description "Layer 2 circuit identifier";
         type union {
           type string {
             pattern "<.*>|$.*";
           }
           type uint32 {
             range "1 .. 4294967295";
           }
         }
         mandatory true;
       }
       leaf reply-mode {
         description "Reply mode for ping request";
         type enumeration {
           enum "no-reply" {
             description "Do not reply";
           }
           enum "ip-udp" {
             description "Reply via an IPv4 or IPv6 UDP packet";
           }
           enum "application-level-control-channel" {
             description "Reply via application level control channel";
           }
         }
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-lsp-end-point {
     description "Ping end point of LSP";
     input {
       leaf prefix {
         description "IP prefix/length of end point";
         type jt:ipprefix;
         mandatory true;
       }
       leaf instance {
         description "Routing-instance name";
         type string;
       }
       leaf count {
         description "Number of ping requests to send";
         units "packets";
         type union {
           type string {
             pattern "<.*>|$.*";
           }
           type uint32 {
             range "1 .. 1000000";
           }
         }
       }
       leaf source {
         description "IP source address of echo request";
         type jt:ipprefix;
       }
       leaf destination {
         description "IP address of destination for echo request";
         type jt:ipprefix;
       }
       leaf exp {
         description "Forwarding class";
         type union {
           type string {
             pattern "<.*>|$.*";
           }
           type uint32 {
             range "0 .. 7";
           }
         }
       }
       leaf detail {
         description "Display detailed output";
         type empty;
       }
       leaf size {
         description "Size of lsp ping request packet";
         units "bytes";
         type union {
           type string {
             pattern "<.*>|$.*";
           }
           type uint32 {
             range "1 .. 65468";
           }
         }
       }
       leaf sweep {
         description "Incremental ping to find MTU";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-vpls-instance {
     description "Instance to which this VPLS connection belongs";
     input {
       leaf instance-name {
         description "Layer 2 VPLS name";
         type string;
         mandatory true;
       }
       leaf destination-mac {
         description "Destination MAC address";
         type jt:mac-addr;
         mandatory true;
       }
       leaf source-ip {
         description "Source IP address";
         type jt:ipv4addr;
         mandatory true;
       }
       leaf learning-vlan-id {
         description "Learning VLAN identifier";
         type union {
           type string {
             pattern "<.*>|$.*";
           }
           type int32 {
             range "0 .. 4094";
           }
         }
       }
       leaf control-plane-response {
         description "Request VPLS OAM responses using the control plane ";
         type empty;
       }
       leaf bd-name {
         description "Name of bridge domain";
         type string;
       }
       leaf count {
         description "Number of ping requests to send";
         units "packets";
         type union {
           type string {
             pattern "<.*>|$.*";
           }
           type uint32 {
             range "1 .. 1000000";
           }
         }
       }
       leaf detail {
         description "Display detailed output";
         type empty;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml lsping-results;
         }
         case multichassis-tag {
           anyxml multi-routing-engine-results;
         }
       }
     }
   }
   rpc request-ping-overlay {
     description "Ping overlay path";
     input {
       leaf tunnel-type {
         description "Tunnel type";
         default "vxlan";
         type enumeration {
           enum "vxlan" {
             description "Vxlan tunnel-type";
           }
         }
       }
       leaf vni {
         description "Value of the vni that identifies the overlay segment";
         type union {
           type string {
             pattern "<.*>|$.*";
           }
           type uint32 {
             range "1 .. 16777215";
           }
         }
         mandatory true;
       }
       leaf tunnel-src {
         description "Source VTEP IP address";
         type jt:ipv4addr;
         mandatory true;
       }
       leaf tunnel-dst {
         description "Remote VTEP IP address";
         type jt:ipv4addr;
         mandatory true;
       }
       choice address {
         case mac {
           leaf mac {
             description "Validate MAC address";
             type jt:mac-unicast;
           }
         }
       }
       leaf count {
         description "Number of pings to send";
         default "5";
         type union {
           type string {
             pattern "<.*>|$.*";
           }
           type uint32 {
             range "1 .. 65535";
           }
         }
       }
       leaf ttl {
         description "TTL to use in the ping packets";
         default "255";
         type union {
           type string {
             pattern "<.*>|$.*";
           }
           type uint32 {
             range "1 .. 255";
           }
         }
       }
       leaf hash-input-interface {
         type union {
           type jt:interface-device;
           type string {
             pattern "<.*>|$.*";
           }
         }
       }
       leaf hash-source-mac {
         type jt:mac-unicast;
       }
       leaf hash-destination-mac {
         type jt:mac-unicast;
       }
       leaf hash-protocol {
         type union {
           type string {
             pattern "<.*>|$.*";
           }
           type uint32 {
             range "1 .. 255";
           }
         }
       }
       leaf hash-source-address {
         type jt:ipv4addr;
       }
       leaf hash-destination-address {
         type jt:ipv4addr;
       }
       leaf hash-source-port {
         type union {
           type string {
             pattern "<.*>|$.*";
           }
           type uint32 {
             range "1 .. 65535";
           }
         }
       }
       leaf hash-destination-port {
         type union {
           type string {
             pattern "<.*>|$.*";
           }
           type uint32 {
             range "1 .. 65535";
           }
         }
       }
       leaf hash-vlan {
         type union {
           type string {
             pattern "<.*>|$.*";
           }
           type uint32 {
             range "1 .. 4094";
           }
         }
       }
     }
     output {
       choice output_c {
         case output-tag {
           leaf output {
             type string;
           }
         }
         case actual-tag {
           anyxml ping-overlay-results;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
