/*
 * Copyright (c) 2019 Juniper Networks, Inc.
 * All rights reserved.
 */
 module junos-rpc-request {
   namespace "http://yang.juniper.net/junos/rpc/request";

   prefix request;

   import junos-common-ddl-extensions {
     prefix junos;
   }

   import junos-common-odl-extensions {
     prefix junos-odl;
   }

   import junos-common-types {
     prefix jt;
   }

   organization "Juniper Networks, Inc.";

   contact "yang-support@juniper.net";

   description "Junos RPC YANG module for request command(s)";

   revision 2019-01-01 {
     description "Junos: 19.2R1.8";
   }

   rpc request-commit-server-cleanup {
     description "Commit queue clean up operations";
     input {
       choice queue-selector {
         case id {
           leaf id {
             description "Clean up queue id";
             type union {
               type uint32;
               type string {
                 pattern "<.*>|$.*";
               }
             }
           }
         }
         case job-status {
           leaf job-status {
             description "Clean up all entries with specified status";
             type enumeration {
               enum "error" {
                 description "Remove jobs that had errors";
               }
               enum "pending" {
                 description "Remove jobs that are pending";
               }
               enum "success" {
                 description "Remove jobs that succeeded";
               }
             }
           }
         }
       }
     }
     output {
       choice output_c {
         case output-tag {
           leaf output {
             type string;
           }
         }
         case actual-tag {
           anyxml commit-server-delete-results;
         }
         case multichassis-tag {
           anyxml multi-routing-engine-results;
         }
       }
     }
   }
   rpc request-commit-server-pause {
     description "Pause the commit server";
     output {
       choice output_c {
         case output-tag {
           leaf output {
             type string;
           }
         }
         case actual-tag {
           anyxml commit-server-information;
         }
         case multichassis-tag {
           anyxml multi-routing-engine-results;
         }
       }
     }
   }
   rpc request-commit-server-start {
     description "Start the commit server";
     output {
       choice output_c {
         case output-tag {
           leaf output {
             type string;
           }
         }
         case actual-tag {
           anyxml commit-server-information;
         }
         case multichassis-tag {
           anyxml multi-routing-engine-results;
         }
       }
     }
   }
   rpc request-delta-exporter-initialize {
     description "Initialize delta exporter database";
     output {
       choice output_c {
         case output-tag {
           leaf output {
             type string;
           }
         }
         case multichassis-tag {
           anyxml multi-routing-engine-results;
         }
       }
     }
   }
   rpc request-yang-add {
     description "Add YANG module(s) and action/translation script(s)";
     input {
       leaf package {
         description "Unique ID for future op - delete/update";
         type string;
         mandatory true;
       }
       leaf-list module {
         ordered-by user;
         description "YANG module(s) path";
         type jt:filename;
       }
       leaf-list action-script {
         ordered-by user;
         description "Action script path";
         type jt:filename;
       }
       leaf-list translation-script {
         ordered-by user;
         description "Translation script path";
         type jt:filename;
       }
       leaf-list deviation-module {
         ordered-by user;
         description "Deviation module path";
         type jt:filename;
       }
       leaf proxy-xml {
         description "XML proxy YANG module(s)";
         type empty;
       }
       leaf snmp {
         description "Add custom MIB in YANG format";
         type empty;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-delete {
     description "Remove YANG package";
     input {
       leaf package {
         description "ID to be removed";
         type string;
         mandatory true;
       }
       choice re-choice {
         case re0 {
           leaf re0 {
             description "Add/Delete YANG module(s) on RE0";
             type empty;
           }
         }
         case re1 {
           leaf re1 {
             description "Add/Delete YANG module(s) on RE1";
             type empty;
           }
         }
         case other-routing-engine {
           leaf other-routing-engine {
             description "Add/Delete YANG module(s) on other RE";
             type empty;
           }
         }
       }
     }
     output {
       choice output_c {
         case output-tag {
           leaf output {
             type string;
           }
         }
         case multichassis-tag {
           anyxml multi-routing-engine-results;
         }
       }
     }
   }
   rpc request-yang-enable {
     description "Enable YANG package to JUNOS translation";
     input {
       leaf package {
         description "ID";
         type string;
         mandatory true;
       }
     }
     output {
       choice output_c {
         case output-tag {
           leaf output {
             type string;
           }
         }
         case multichassis-tag {
           anyxml multi-routing-engine-results;
         }
       }
     }
   }
   rpc request-yang-disable {
     description "Disable YANG package to JUNOS translation";
     input {
       leaf package {
         description "ID";
         type string;
         mandatory true;
       }
     }
     output {
       choice output_c {
         case output-tag {
           leaf output {
             type string;
           }
         }
         case multichassis-tag {
           anyxml multi-routing-engine-results;
         }
       }
     }
   }
   rpc request-yang-validate {
     description "Validate YANG module(s) and action/translation script(s)";
     input {
       leaf-list module {
         ordered-by user;
         description "Name of the YANG module to be validated";
         type jt:filename;
       }
       leaf-list translation-script {
         ordered-by user;
         description "Name of the translation-script to be validated";
         type jt:filename;
       }
       leaf-list action-script {
         ordered-by user;
         description "Name of the action-script to be validated";
         type jt:filename;
       }
       leaf proxy-xml {
         description "XML proxy YANG module";
         type empty;
       }
       leaf snmp {
         description "Validate custom MIB in YANG format";
         type empty;
       }
     }
     output {
       choice output_c {
         case output-tag {
           leaf output {
             type string;
           }
         }
         case multichassis-tag {
           anyxml multi-routing-engine-results;
         }
       }
     }
   }
   rpc request-yang-update {
     description "Update YANG module(s) and action/translation script(s)";
     input {
       leaf package {
         description "ID";
         type string;
         mandatory true;
       }
       leaf-list module {
         ordered-by user;
         description "YANG module(s) path";
         type jt:filename;
       }
       leaf-list translation-script {
         ordered-by user;
         description "Translation script path";
         type jt:filename;
       }
       leaf-list deviation-module {
         ordered-by user;
         description "Deviation module path";
         type jt:filename;
       }
       leaf-list action-script {
         ordered-by user;
         description "Action script path";
         type jt:filename;
       }
       leaf proxy-xml {
         description "XML proxy YANG module(s)";
         type empty;
       }
       leaf snmp {
         description "Update custom MIBs in YANG format";
         type empty;
       }
     }
     output {
       choice output_c {
         case output-tag {
           leaf output {
             type string;
           }
         }
         case multichassis-tag {
           anyxml multi-routing-engine-results;
         }
       }
     }
   }
   rpc reload-event-scripts {
     description "Reload all existing event-scripts";
     output {
       choice output_c {
         case output-tag {
           leaf output {
             type string;
           }
         }
         case actual-tag {
           anyxml event-scripts-reload;
         }
         case multichassis-tag {
           anyxml multi-routing-engine-results;
         }
       }
     }
   }
   rpc request-scripts-package-add {
     description "Add or upgrade jais package";
     input {
       leaf no-copy {
         description "Don't save copy of jais package file";
         type empty;
       }
       leaf unlink {
         description "Remove the package after successful installation";
         type empty;
       }
       leaf package-name {
         description "URL or pathname of package";
         type jt:filename;
         mandatory true;
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case master {
           leaf master {
             description "Run command on master";
             type empty;
           }
         }
         case backup {
           leaf backup {
             description "Run command on backup";
             type empty;
           }
         }
       }
     }
     output {
       choice output_c {
         case output-tag {
           leaf output {
             type string;
           }
         }
         case multichassis-tag {
           anyxml multi-routing-engine-results;
         }
       }
     }
   }
   rpc request-scripts-package-delete {
     description "Remove jais package";
     output {
       choice output_c {
         case output-tag {
           leaf output {
             type string;
           }
         }
         case multichassis-tag {
           anyxml multi-routing-engine-results;
         }
       }
     }
   }
   rpc request-scripts-package-rollback {
     description "Attempt to roll back to last jais package";
     output {
       choice output_c {
         case output-tag {
           leaf output {
             type string;
           }
         }
         case multichassis-tag {
           anyxml multi-routing-engine-results;
         }
       }
     }
   }
   rpc request-script-refresh-from {
     description "Refresh script from a given base URL";
     input {
       leaf type {
         type enumeration {
           enum "commit" {
             description "Refresh commit script from a given base URL";
           }
           enum "op" {
             description "Refresh op script from a given base URL";
           }
           enum "event" {
             description "Refresh event script from a given base URL";
           }
           enum "snmp" {
             description "Refresh snmp script from a given base URL";
           }
           enum "extension-service" {
             description "Refresh extension-services app from a given base URL";
           }
         }
         mandatory true;
       }
       leaf file {
         description "Local script file name";
         type string {
           junos:posix-pattern "!/";
           junos:pattern-message "File name cannot contain a '/'";
         }
       }
       leaf url {
         description "URL from where the content will be retrieved";
         type string;
       }
       leaf routing-instance {
         description "Specify the routing-instance name";
         type string;
       }
       leaf sync {
         description "Refresh script and synchronize with other RE";
         type empty;
       }
     }
     output {
       choice output_c {
         case output-tag {
           leaf output {
             type string;
           }
         }
         case multichassis-tag {
           anyxml multi-routing-engine-results;
         }
       }
     }
   }
   rpc request-scripts-synchronize {
     description "Push the scripts to other RE";
     input {
       leaf type {
         type enumeration {
           enum "commit" {
             description "Push commit script to other RE";
           }
           enum "op" {
             description "Push op script to other RE";
           }
           enum "event" {
             description "Push event script to other RE";
           }
           enum "snmp" {
             description "Push snmp script to other RE";
           }
           enum "jet" {
             description "Push jet app to other RE";
           }
           enum "lib" {
             description "Push lib script to other RE";
           }
           enum "all" {
             description "Push all the scripts to other RE";
           }
         }
         mandatory true;
       }
       leaf file {
         description "Local script file name";
         type string;
       }
       leaf newer-than {
         description "Push script to other RE if newer than this time (YYYY-MM-DD.HH:MM:SS)";
         type jt:time;
       }
     }
     output {
       choice output_c {
         case output-tag {
           leaf output {
             type string;
           }
         }
         case multichassis-tag {
           anyxml multi-routing-engine-results;
         }
       }
     }
   }
   rpc resize-configuraion-database {
     description "Resize the configuration database";
     input {
       uses command-forwarding;
       leaf force {
         description "Resize the configuration database even if modified";
         type empty;
       }
     }
     output {
       choice output_c {
         case output-tag {
           leaf output {
             type string;
           }
         }
         case multichassis-tag {
           anyxml multi-routing-engine-results;
         }
       }
     }
   }
   rpc request-save-rescue-configuration {
     description "Save committed configuration as rescue configuration";
     output {
       choice output_c {
         case output-tag {
           leaf output {
             type string;
           }
         }
         case actual-tag {
           anyxml rescue-management-results;
         }
         case multichassis-tag {
           anyxml multi-routing-engine-results;
         }
       }
     }
   }
   rpc request-delete-rescue-configuration {
     description "Delete the rescue configuration";
     output {
       choice output_c {
         case output-tag {
           leaf output {
             type string;
           }
         }
         case actual-tag {
           anyxml rescue-management-results;
         }
         case multichassis-tag {
           anyxml multi-routing-engine-results;
         }
       }
     }
   }
   rpc request-package-add {
     description "Add extension or upgrade package";
     input {
       leaf force {
         description "Force addition of package (ignore warnings)";
         type empty;
       }
       leaf reboot {
         description "Reboot system after adding package";
         type empty;
       }
       leaf force-host {
         description "Force addition of host os package (ignore version check)";
         type empty;
       }
       leaf on-primary {
         description "Install image on primary partition while booted on secondary partition";
         type empty;
       }
       leaf no-auto-reboot {
         description "Do not reboot system automatically after adding package";
         type empty;
       }
       leaf delay-restart {
         description "Don't restart processes";
         type empty;
       }
       leaf no-copy {
         description "Don't save copies of package files";
         type empty;
       }
       leaf dualroot {
         description "Install Dual-Root image for Zeroization";
         type empty;
       }
       choice validate_choice {
         case no-validate {
           leaf no-validate {
             description "Don't check compatibility with current configuration";
             type empty;
           }
         }
         case validate {
           leaf validate {
             description "Check compatibility with current configuration";
             type empty;
           }
         }
         case validate-on-host {
           leaf validate-on-host {
             description "Remote host or user@host for configuration validation";
             type string;
           }
         }
         case validate-on-routing-engine {
           leaf validate-on-routing-engine {
             description "Routing engine for configuration validation";
             type string;
           }
         }
       }
       leaf best-effort-load {
         description "Load succeeds if at least one statement is valid";
         type empty;
       }
       leaf unlink {
         description "Remove the package after successful installation";
         type empty;
       }
       choice re-choice {
         case re0 {
           leaf re0 {
             description "Install package on RE0";
             type empty;
           }
         }
         case re1 {
           leaf re1 {
             description "Install package on RE1";
             type empty;
           }
         }
         case both-routing-engines {
           leaf both-routing-engines {
             description "Simultaneous upgrade on both the RE's";
             type empty;
           }
         }
       }
       choice chassis {
         case scc {
           leaf scc {
             description "Install package on SCC";
             type empty;
           }
         }
         case lcc {
           leaf lcc {
             description "Install package on an LCC";
             type union {
               type string {
                 pattern "<.*>|$.*";
               }
               type uint32;
             }
           }
         }
         case sfc {
           leaf sfc {
             description "Install package on SFC";
             type empty;
           }
         }
         case member {
           leaf member {
             description "Install package on member";
             type union {
               type string {
                 pattern "<.*>|$.*";
               }
               type uint32;
             }
           }
         }
         case dont-forward {
           leaf dont-forward {
             type empty;
           }
         }
         case service-node {
           leaf service-node {
             description "Install package on Service Node";
             type union {
               type string {
                 pattern "<.*>|$.*";
               }
               type uint32 {
                 range "0 .. 1";
               }
             }
           }
         }
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
       leaf issu-internal {
         description "Internally executed by mgd, to allow software adds during issu";
         type empty;
       }
       leaf-list upgrade-with-config {
         ordered-by user;
         description "Additional configs ('text/xml' format) to be applied on upgrade";
         type jt:filename;
       }
       choice package-options {
         case set {
           leaf-list set {
             ordered-by user;
             description "List of URLs or pathnames corresponding to packages";
             type jt:filename;
           }
         }
         case package-name {
           leaf package-name {
             description "URL or pathname of package";
             type jt:filename;
           }
         }
         case version {
           leaf version {
             description "Version of satellite package";
             type string;
           }
         }
       }
     }
     output {
       choice output_c {
         case output-tag {
           leaf output {
             type string;
           }
         }
         case multichassis-tag {
           anyxml multi-routing-engine-results;
         }
       }
     }
   }
   rpc abort-in-service-upgrade {
     description "Abort in-service software upgrade";
     output {
       choice output_c {
         case output-tag {
           leaf output {
             type string;
           }
         }
         case multichassis-tag {
           anyxml multi-routing-engine-results;
         }
       }
     }
   }
   rpc request-package-in-service-upgrade {
     description "In-service software upgrade";
     input {
       leaf reboot {
         description "Reboot system after adding package";
         type empty;
       }
       choice package-options {
         case set {
           leaf-list set {
             ordered-by user;
             description "List of URLs or pathnames corresponding to packages for ISSU";
             type jt:filename;
           }
         }
         case package-name {
           leaf package-name {
             description "URL or pathname of package";
             type jt:filename;
           }
         }
       }
       leaf no-old-master-upgrade {
         description "Don't upgrade the old master after switchover";
         type empty;
       }
       leaf verbose {
         description "Enable detailed output";
         type empty;
       }
       leaf no-copy {
         description "Don't save copies of package files";
         type empty;
       }
       leaf unlink {
         description "Remove the package after successful installation";
         type empty;
       }
       choice issu_internal {
       }
     }
     output {
       choice output_c {
         case output-tag {
           leaf output {
             type string;
           }
         }
         case multichassis-tag {
           anyxml multi-routing-engine-results;
         }
       }
     }
   }
   rpc request-package-nonstop-upgrade {
     description "Nonstop software upgrade";
     input {
       leaf force-host {
         description "Force addition of host os package (ignore version check)";
         type empty;
       }
       leaf no-auto-recovery {
         description "Will not recover in case of NSSU failure";
         type empty;
       }
       choice package-options {
         case set {
           leaf-list set {
             ordered-by user;
             description "List of URLs or pathnames corresponding to packages";
             type jt:filename;
           }
         }
         case package-name {
           leaf package-name {
             description "URL or pathname of package";
             type jt:filename;
           }
         }
       }
       leaf no-copy {
         description "Don't save copies of package files";
         status deprecated;
         type empty;
       }
       leaf unlink {
         description "Remove the package after successful installation";
         status deprecated;
         type empty;
       }
       leaf no-validate {
         description "Don't check compatibility with current configuration";
         type empty;
       }
     }
     output {
       choice output_c {
         case output-tag {
           leaf output {
             type string;
           }
         }
         case multichassis-tag {
           anyxml multi-routing-engine-results;
         }
       }
     }
   }
   rpc request-package-delete {
     description "Remove extension or upgrade package";
     input {
       leaf force {
         description "Force removal of package (ignore warnings)";
         type empty;
       }
       choice package-options {
         case set {
           leaf-list set {
             ordered-by user;
             description "List of package name";
             type string;
           }
         }
         case package-name {
           leaf package-name {
             description "Name of package";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
       choice re-choice {
         case re0 {
           leaf re0 {
             description "Delete package on RE0";
             type empty;
           }
         }
         case re1 {
           leaf re1 {
             description "Delete package on RE1";
             type empty;
           }
         }
       }
       choice chassis {
         case scc {
           leaf scc {
             description "Delete package on SCC";
             type empty;
           }
         }
         case lcc {
           leaf lcc {
             description "Delete package on an LCC";
             type union {
               type string {
                 pattern "<.*>|$.*";
               }
               type uint32 {
                 range "0 .. 3";
               }
             }
           }
         }
         case sfc {
           leaf sfc {
             description "Delete package on SFC";
             type empty;
           }
         }
         case member {
           leaf member {
             description "Delete package on VC Member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-package-rollback {
     description "Attempt to roll back to previous set of packages";
     input {
       uses command-forwarding;
       leaf reboot {
         description "Reboot system after rollback";
         type empty;
       }
       leaf force {
         description "Force rollback of packages (ignore warnings)";
         type empty;
       }
       choice satellite-arg {
         case upgrade-group {
           leaf upgrade-group {
             description "Satellite upgrade group name";
             type string;
           }
         }
         case satellite {
           leaf satellite {
             description "FPC slot of satellite system";
             type union {
               type int32;
               type string {
                 pattern "<.*>|$.*";
               }
             }
           }
         }
         case device-alias {
           leaf device-alias {
             description "Device alias of satellite system";
             type string;
           }
         }
       }
     }
     output {
       choice output_c {
         case output-tag {
           leaf output {
             type string;
           }
         }
         case multichassis-tag {
           anyxml multi-routing-engine-results;
         }
       }
     }
   }
   rpc request-package-validate {
     description "Verify package compatibility with current configuration";
     input {
       leaf-list upgrade-with-config {
         ordered-by user;
         description "Additional configs ('text/xml' format) to be validated";
         type jt:filename;
       }
       choice package-options {
         case set {
           leaf-list set {
             ordered-by user;
             description "List of URLs or pathnames corresponding to packages";
             type jt:filename;
           }
         }
         case package-name {
           leaf package-name {
             description "URL or pathname of package";
             type jt:filename;
           }
         }
       }
       choice chassis {
         case scc {
           leaf scc {
             description "Validate package on SCC";
             type empty;
           }
         }
         case lcc {
           leaf lcc {
             description "Validate package on an LCC";
             type union {
               type string {
                 pattern "<.*>|$.*";
               }
               type uint32;
             }
           }
         }
         case sfc {
           leaf sfc {
             description "Validate package on SFC";
             type empty;
           }
         }
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc check-in-service-upgrade {
     description "Check in-service software upgrade";
     input {
       choice package-options {
         case set {
           leaf-list set {
             ordered-by user;
             description "List of URLs or pathnames corresponding to packages for ISSU";
             type jt:filename;
           }
         }
         case package-name {
           leaf package-name {
             description "URL or pathname of package";
             type jt:filename;
           }
         }
       }
     }
     output {
       choice output_c {
         case output-tag {
           leaf output {
             type string;
           }
         }
         case multichassis-tag {
           anyxml multi-routing-engine-results;
         }
       }
     }
   }
   rpc request-package-delete-backup {
     description "Delete old system software packages";
     output {
       choice output_c {
         case output-tag {
           leaf output {
             type string;
           }
         }
         case multichassis-tag {
           anyxml multi-routing-engine-results;
         }
       }
     }
   }
   rpc request-logout-user {
     description "Forcibly end user's CLI login session";
     input {
       uses command-forwarding;
       leaf all {
         description "Logout all sessions owned by user";
         type empty;
       }
       leaf user {
         description "Name of user";
         type string {
           junos:posix-pattern "^[[:alnum:]_]{1,}[.]{0,1}[[:alnum:]_-]{0,}[.]{0,1}[[:alnum:]_-]{0,}$";
           junos:pattern-message "Must contain characters (alphanumerics, underscores or hyphens) beginning with an alphanumeric or an underscore character.";
         }
       }
       leaf terminal {
         description "Terminal user is logged in to";
         type string {
           junos:posix-pattern "[a-z][0-9a-z]";
           junos:pattern-message "Must start with a letter followed by alphanumeric character";
         }
       }
       leaf pid {
         description "Management process ID for user";
         type union {
           type uint32;
           type string {
             pattern "<.*>|$.*";
           }
         }
       }
     }
     output {
       choice output_c {
         case output-tag {
           leaf output {
             type string;
           }
         }
         case actual-tag {
           anyxml logout-user;
         }
         case multichassis-tag {
           anyxml multi-routing-engine-results;
         }
       }
     }
   }
   rpc request-license-add {
     description "Add license keys from file, local or from server";
     input {
       leaf filename {
         description "Filename (URL, local, remote, or floppy)";
         type string;
       }
       leaf key-data {
         description "License key data";
         type string;
       }
     }
     output {
       choice output_c {
         case output-tag {
           leaf output {
             type string;
           }
         }
         case actual-tag {
           anyxml add-license-results;
         }
         case multichassis-tag {
           anyxml multi-routing-engine-results;
         }
       }
     }
   }
   rpc request-license-delete {
     description "Delete license keys";
     input {
       choice delete-choice {
         case all {
           leaf all {
             description "Delete all license keys";
             type empty;
           }
         }
         case license-identifier {
           leaf license-identifier {
             description "Identifier of installed license key";
             type string;
           }
         }
         case license-identifier-list {
           leaf-list license-identifier-list {
             ordered-by user;
             description "Identifier of installed license key";
             type string;
           }
         }
       }
     }
     output {
       choice output_c {
         case output-tag {
           leaf output {
             type string;
           }
         }
         case multichassis-tag {
           anyxml multi-routing-engine-results;
         }
       }
     }
   }
   rpc request-license-save {
     description "Save license keys to file, local or to server";
     input {
       leaf filename {
         description "Filename (URL, local, remote, or floppy)";
         type string;
         mandatory true;
       }
     }
     output {
       choice output_c {
         case output-tag {
           leaf output {
             type string;
           }
         }
         case multichassis-tag {
           anyxml multi-routing-engine-results;
         }
       }
     }
   }
   rpc request-license-update {
     description "Start autoupdate license keys from LMS servers";
     input {
       leaf trial {
         description "Start autoupdate trial license keys from LMS servers";
         type empty;
       }
     }
     output {
       choice output_c {
         case output-tag {
           leaf output {
             type string;
           }
         }
         case actual-tag {
           anyxml inform;
         }
         case multichassis-tag {
           anyxml multi-routing-engine-results;
         }
       }
     }
   }
   rpc license-revoke-licenses {
     description "Revoke licenses in the Authorization key";
     status deprecated;
     input {
       leaf filename {
         description "Filename (URL, local, remote, or floppy)";
         type string;
         mandatory true;
       }
     }
     output {
       choice output_c {
         case output-tag {
           leaf output {
             type string;
           }
         }
         case multichassis-tag {
           anyxml multi-routing-engine-results;
         }
       }
     }
   }
   rpc enable-unified-services-chassis-mode {
     description "Enable unified services chassis mode";
     output {
       choice output_c {
         case output-tag {
           leaf output {
             type string;
           }
         }
         case multichassis-tag {
           anyxml multi-routing-engine-results;
         }
       }
     }
   }
   rpc disable-unified-services-chassis-mode {
     description "Disable unified services chassis mode";
     output {
       choice output_c {
         case output-tag {
           leaf output {
             type string;
           }
         }
         case multichassis-tag {
           anyxml multi-routing-engine-results;
         }
       }
     }
   }
   rpc fips-selftest {
     description "Execute FIPS known answer tests (KATs)";
     output {
       choice output_c {
         case output-tag {
           leaf output {
             type string;
           }
         }
         case multichassis-tag {
           anyxml multi-routing-engine-results;
         }
       }
     }
   }
   rpc request-personality-file-generate {
     description "Generate the personality-file tarball for the device";
     input {
       leaf personality-file-create {
         description "Url containing the remote server alongwith the name of the tarball";
         type string;
         mandatory true;
       }
     }
     output {
       choice output_c {
         case output-tag {
           leaf output {
             type string;
           }
         }
         case multichassis-tag {
           anyxml multi-routing-engine-results;
         }
       }
     }
   }
   rpc request-personality-file-retrieve {
     description "Retrieve the personality-file tarball of the device";
     input {
       leaf personality-file-retrieve {
         description "Url containing the remote server alongwith the name of the tarball";
         type string;
         mandatory true;
       }
       leaf retrieve-location {
         description "Path on the local device where the personality-file will be retrieved";
         type string;
         mandatory true;
       }
     }
     output {
       choice output_c {
         case output-tag {
           leaf output {
             type string;
           }
         }
         case multichassis-tag {
           anyxml multi-routing-engine-results;
         }
       }
     }
   }
   rpc transfer-control {
     description "Control transfers of core and log files";
     input {
       leaf operation {
         description "Transfer control operation";
         type enumeration {
           enum "abort" {
             description "Abort a transfer";
           }
           enum "pause" {
             description "Pause a transfer";
           }
           enum "restart" {
             description "Restart a transfer";
           }
         }
         mandatory true;
       }
       choice arg-type {
         case component {
         }
         case transfer-id {
           leaf transfer-id {
             description "Transfer identifier";
             type union {
               type int32;
               type string {
                 pattern "<.*>|$.*";
               }
             }
           }
         }
       }
     }
     output {
       choice output_c {
         case output-tag {
           leaf output {
             type string;
           }
         }
         case actual-tag {
           anyxml transfer-control-diagnostics;
         }
         case multichassis-tag {
           anyxml multi-routing-engine-results;
         }
       }
     }
   }
   rpc request-log {
     description "Create an archive of all system logs";
     output {
       choice output_c {
         case output-tag {
           leaf output {
             type string;
           }
         }
         case actual-tag {
           anyxml system-logfiles;
         }
         case multichassis-tag {
           anyxml multi-routing-engine-results;
         }
       }
     }
   }
   rpc request-system-storage-cleanup {
     description "Clean up temporary files and rotate logs";
     input {
       uses command-forwarding;
       leaf dry-run {
         description "Only list the cleanup candidates, do not remove them";
         type empty;
       }
       leaf no-confirm {
         description "Do not ask for confirmation";
         type empty;
       }
     }
     output {
       choice output_c {
         case output-tag {
           leaf output {
             type string;
           }
         }
         case actual-tag {
           anyxml system-storage-cleanup-information;
         }
         case multichassis-tag {
           anyxml multi-routing-engine-results;
         }
       }
     }
   }
   rpc request-system-storage-cleanup-satellite {
     description "Clean up temporary and core files on satellite device";
     input {
       leaf fpc-slot {
         description "Satellite slot number";
         type union {
           type string {
             pattern "<.*>|$.*";
           }
           type uint32 {
             range "65 .. 254";
           }
         }
       }
       leaf device-alias {
         description "Device alias";
         type string;
       }
       leaf dry-run {
         description "Only list the cleanup candidates, do not remove them";
         type empty;
       }
     }
     output {
       choice output_c {
         case output-tag {
           leaf output {
             type string;
           }
         }
         case multichassis-tag {
           anyxml multi-routing-engine-results;
         }
       }
     }
   }
   rpc request-system-storage-expand-user {
     description "Manage size of user disk";
     input {
       leaf operation {
         description "Expand user disk or revert to default";
         type enumeration {
           enum "expand" {
             description "Expand user disk to maximum available size";
           }
           enum "restore" {
             description "Restore user disk to default setting";
           }
         }
         mandatory true;
       }
     }
     output {
       choice output_c {
         case output-tag {
           leaf output {
             type string;
           }
         }
         case multichassis-tag {
           anyxml multi-routing-engine-results;
         }
       }
     }
   }
   rpc request-boot-media {
     description "Setup permanent boot media for subsequent reboots";
     input {
       leaf media {
         description "Media to be setup as boot device";
         type enumeration {
           enum "primary" {
             description "Boot from primary Junos partition";
           }
           enum "alternate" {
             description "Boot from alternate Junos partition";
           }
           enum "external" {
             description "Boot from external USB device";
           }
         }
         mandatory true;
       }
     }
     output {
       choice output_c {
         case output-tag {
           leaf output {
             type string;
           }
         }
         case multichassis-tag {
           anyxml multi-routing-engine-results;
         }
       }
     }
   }
   rpc request-reboot {
     description "Reboot the system";
     input {
       uses command-forwarding;
       leaf hypervisor {
         description "Reboot both Junos and Hypervisor";
         type empty;
       }
       leaf fast-boot {
         description "Enable fast reboot";
         status deprecated;
         type empty;
       }
       leaf media {
         description "Boot media for next boot";
         type enumeration {
           enum "disk" {
             description "Boot off hard disk";
           }
           enum "compact-flash" {
             description "Standard boot off flash device";
           }
           enum "usb" {
             description "Boot off USB device";
           }
           enum "usb0" {
             description "Boot off USB0 device";
           }
           enum "usb1" {
             description "Boot off USB1 device";
           }
           enum "removable-compact-flash" {
             description "Boot off removable compact flash device";
           }
           enum "external" {
             description "Boot from external storage device";
           }
           enum "internal" {
             description "Boot from internal flash";
           }
           enum "nand-flash0" {
             description "Boot off nand-flash0";
           }
           enum "nand-flash1" {
             description "Boot off nand-flash1";
           }
         }
       }
       leaf at {
         description "Time at which to perform the operation";
         default "now";
         type string;
       }
       leaf in {
         description "Number of minutes to delay before operation";
         default "now";
         type string;
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case actual-tag {
           anyxml request-reboot-results;
         }
         case multichassis-tag {
           anyxml multi-routing-engine-results;
         }
       }
     }
   }
   rpc request-reboot-in-service {
     description "Reboot with minimal traffic disruption";
     output {
       choice output_c {
         case output-tag {
           leaf output {
             type string;
           }
         }
         case multichassis-tag {
           anyxml multi-routing-engine-results;
         }
       }
     }
   }
   rpc request-halt {
     description "Halt the system";
     input {
       uses command-forwarding;
       leaf media {
         description "Boot media for next boot";
         type enumeration {
           enum "disk" {
             description "Boot off hard disk";
           }
           enum "compact-flash" {
             description "Standard boot off flash device";
           }
           enum "usb" {
             description "Boot off USB device";
           }
           enum "usb0" {
             description "Boot off USB0 device";
           }
           enum "usb1" {
             description "Boot off USB1 device";
           }
           enum "removable-compact-flash" {
             description "Boot off removable compact flash device";
           }
           enum "external" {
             description "Boot from external storage device";
           }
           enum "internal" {
             description "Boot from internal flash";
           }
           enum "nand-flash0" {
             description "Boot off nand-flash0";
           }
           enum "nand-flash1" {
             description "Boot off nand-flash1";
           }
         }
       }
       leaf at {
         description "Time at which to perform the operation";
         default "now";
         type string;
       }
       leaf in {
         description "Number of minutes to delay before operation";
         default "now";
         type string;
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-power-off {
     description "Power off the software on RE";
     input {
       uses command-forwarding;
       leaf media {
         description "Boot media for next boot";
         type enumeration {
           enum "disk" {
             description "Boot off hard disk";
           }
           enum "compact-flash" {
             description "Standard boot off flash device";
           }
           enum "usb" {
             description "Boot off USB device";
           }
           enum "usb0" {
             description "Boot off USB0 device";
           }
           enum "usb1" {
             description "Boot off USB1 device";
           }
           enum "removable-compact-flash" {
             description "Boot off removable compact flash device";
           }
           enum "external" {
             description "Boot from external storage device";
           }
           enum "internal" {
             description "Boot from internal flash";
           }
           enum "nand-flash0" {
             description "Boot off nand-flash0";
           }
           enum "nand-flash1" {
             description "Boot off nand-flash1";
           }
         }
       }
       leaf at {
         description "Time at which to perform the operation";
         default "now";
         type string;
       }
       leaf in {
         description "Number of minutes to delay before operation";
         default "now";
         type string;
       }
       leaf message {
         description "Message to display to all users";
         type string;
       }
       leaf power-off {
         description "Power-off the software on RE";
         type enumeration {
           enum "fpc" {
             description "Power off FPCs";
           }
         }
       }
       leaf slice {
         description "Partition on boot media to boot from";
         type enumeration {
           enum "alternate" {
             description "Boot from alternate partition";
           }
           enum "1" {
             description "Boot from first partition";
           }
           enum "2" {
             description "Boot from second partition";
           }
         }
       }
     }
     output {
       choice output_c {
         case output-tag {
           leaf output {
             type string;
           }
         }
         case multichassis-tag {
           anyxml multi-routing-engine-results;
         }
       }
     }
   }
   rpc request-process-terminate {
     description "Terminate the process";
     input {
       leaf process-id {
         description "Process ID";
         type union {
           type string {
             pattern "<.*>|$.*";
           }
           type uint32 {
             range "1 .. 99999";
           }
         }
         mandatory true;
       }
     }
     output {
       choice output_c {
         case output-tag {
           leaf output {
             type string;
           }
         }
         case multichassis-tag {
           anyxml multi-routing-engine-results;
         }
       }
     }
   }
   rpc request-system-zeroize {
     description "Erase all data, including configuration and log files";
     input {
       leaf media {
         description "Overwrite media";
         type empty;
       }
       leaf local {
         description "Zeroize just this Routing Engine";
         type empty;
       }
     }
     output {
       choice output_c {
         case output-tag {
           leaf output {
             type string;
           }
         }
         case multichassis-tag {
           anyxml multi-routing-engine-results;
         }
       }
     }
   }
   rpc request-snapshot {
     description "Archive data and executable areas";
     input {
       uses command-forwarding;
       leaf partition {
         description "Partition the media";
         type empty;
       }
       leaf factory {
         description "Include only files shipped from factory in snapshot";
         type empty;
       }
       leaf as-primary {
         description "Setup snapshot to be used in the primary boot device";
         type empty;
       }
       leaf swap-size {
         description "Size of the swap partition";
         type string;
       }
       leaf config-size {
         description "Size of the config partition";
         type string;
       }
       leaf root-size {
         description "Size of the root partition";
         type string;
       }
       leaf data-size {
         description "Size of the data partition";
         type string;
       }
       leaf slice {
         description "Write snapshot to specified partition";
         type enumeration {
           enum "alternate" {
             description "Write snapshot to alternate partition";
           }
         }
       }
       leaf media {
         description "Media to snapshot to";
         default "compact-flash";
         type enumeration {
           enum "removable-compact-flash" {
             description "Write snapshot to removable compact flash";
           }
           enum "compact-flash" {
             description "Write snapshot to compact flash";
           }
           enum "usb" {
             description "Write snapshot to device connected to USB port";
           }
           enum "usb0" {
             description "Write snapshot to device connected to USB0 port";
           }
           enum "usb1" {
             description "Write snapshot to device connected to USB1 port";
           }
           enum "hard-disk" {
             description "Write snapshot to hard disk";
           }
           enum "internal" {
             description "Write snapshot to internal flash";
           }
           enum "external" {
             description "Write snapshot to external storage device";
           }
         }
       }
       leaf root-partition {
         description "Write snapshot of root partition alone";
         type empty;
       }
       leaf config-partition {
         description "Write snapshot of config partition alone";
         type empty;
       }
     }
     output {
       choice output_c {
         case output-tag {
           leaf output {
             type string;
           }
         }
         case actual-tag {
           anyxml snapshot-information;
         }
         case multichassis-tag {
           anyxml multi-routing-engine-results;
         }
       }
     }
   }
   rpc request-jfw-cpld-upgrade {
     description "Upgrade CPLD firmware";
     input {
       leaf cpld-type {
         description "CPLD type: RE, MAIN, FAN";
         type string;
       }
     }
     output {
       choice output_c {
         case output-tag {
           leaf output {
             type string;
           }
         }
         case actual-tag {
           anyxml system-jfw-cpld-upgrade-information;
         }
         case multichassis-tag {
           anyxml multi-routing-engine-results;
         }
       }
     }
   }
   rpc request-jfw-cpld-mainboard-upgrade {
     description "Upgrade mainboard CPLD firmware";
     output {
       choice output_c {
         case output-tag {
           leaf output {
             type string;
           }
         }
         case actual-tag {
           anyxml system-jfw-cpld-mainboard-upgrade-information;
         }
         case multichassis-tag {
           anyxml multi-routing-engine-results;
         }
       }
     }
   }
   rpc request-jfw-cpld-fanboard-upgrade {
     description "Upgrade fanboard CPLD firmware";
     output {
       choice output_c {
         case output-tag {
           leaf output {
             type string;
           }
         }
         case actual-tag {
           anyxml system-jfw-cpld-fanboard-upgrade-information;
         }
         case multichassis-tag {
           anyxml multi-routing-engine-results;
         }
       }
     }
   }
   rpc request-jfw-cpld-fanboard-upgrade-status {
     description "Show fanboard CPLD upgrade status";
     output {
       choice output_c {
         case output-tag {
           leaf output {
             type string;
           }
         }
         case actual-tag {
           anyxml system-jfw-cpld-fanboard-upgrade-information-status;
         }
         case multichassis-tag {
           anyxml multi-routing-engine-results;
         }
       }
     }
   }
   rpc request-jfw-cpld-cpuboard-upgrade {
     description "Upgrade CPU board CPLD firmware";
     output {
       choice output_c {
         case output-tag {
           leaf output {
             type string;
           }
         }
         case actual-tag {
           anyxml system-jfw-cpld-cpuboard-upgrade-information;
         }
         case multichassis-tag {
           anyxml multi-routing-engine-results;
         }
       }
     }
   }
   rpc request-jfw-nic-i350-upgrade {
     description "Upgrade Builtin i350 NIC firmware";
     output {
       choice output_c {
         case output-tag {
           leaf output {
             type string;
           }
         }
         case actual-tag {
           anyxml system-jfw-nic-i350-upgrade-information;
         }
         case multichassis-tag {
           anyxml multi-routing-engine-results;
         }
       }
     }
   }
   rpc request-jfw-nic-x552-upgrade {
     description "Upgrade Builtin x552 NIC firmware";
     output {
       choice output_c {
         case output-tag {
           leaf output {
             type string;
           }
         }
         case actual-tag {
           anyxml system-jfw-nic-x552-upgrade-information;
         }
         case multichassis-tag {
           anyxml multi-routing-engine-results;
         }
       }
     }
   }
   rpc request-jfw-nic-x553-upgrade {
     description "Upgrade Builtin x553 NIC firmware";
     output {
       choice output_c {
         case output-tag {
           leaf output {
             type string;
           }
         }
         case actual-tag {
           anyxml system-jfw-nic-x553-upgrade-information;
         }
         case multichassis-tag {
           anyxml multi-routing-engine-results;
         }
       }
     }
   }
   rpc request-jfw-nic-i82599-1-upgrade {
     description "Upgrade Builtin i82599_1 NIC firmware";
     output {
       choice output_c {
         case output-tag {
           leaf output {
             type string;
           }
         }
         case actual-tag {
           anyxml system-jfw-nic-i82599-1-upgrade-information;
         }
         case multichassis-tag {
           anyxml multi-routing-engine-results;
         }
       }
     }
   }
   rpc request-jfw-nic-i82599-2-upgrade {
     description "Upgrade Builtin i82599_2 NIC firmware";
     output {
       choice output_c {
         case output-tag {
           leaf output {
             type string;
           }
         }
         case actual-tag {
           anyxml system-jfw-nic-i82599-2-upgrade-information;
         }
         case multichassis-tag {
           anyxml multi-routing-engine-results;
         }
       }
     }
   }
   rpc request-jfw-em-i350-copper-upgrade {
     description "Upgrade Expansion Module i350 NIC Copper firmware";
     output {
       choice output_c {
         case output-tag {
           leaf output {
             type string;
           }
         }
         case actual-tag {
           anyxml system-jfw-em-i350-copper-upgrade-information;
         }
         case multichassis-tag {
           anyxml multi-routing-engine-results;
         }
       }
     }
   }
   rpc request-jfw-em-i350-sfp-upgrade {
     description "Upgrade Expansion Module i350 NIC SFP firmware";
     output {
       choice output_c {
         case output-tag {
           leaf output {
             type string;
           }
         }
         case actual-tag {
           anyxml system-jfw-em-i350-sfp-upgrade-information;
         }
         case multichassis-tag {
           anyxml multi-routing-engine-results;
         }
       }
     }
   }
   rpc request-jfw-bios-upgrade {
     description "Upgrade BIOS firmware";
     input {
       leaf disk {
         description "1, 2";
         type string;
       }
     }
     output {
       choice output_c {
         case output-tag {
           leaf output {
             type string;
           }
         }
         case actual-tag {
           anyxml system-jfw-bios-upgrade-information;
         }
         case multichassis-tag {
           anyxml multi-routing-engine-results;
         }
       }
     }
   }
   rpc request-jfw-bios-upgrade-status {
     description "Show BIOS upgrade status";
     output {
       choice output_c {
         case output-tag {
           leaf output {
             type string;
           }
         }
         case actual-tag {
           anyxml system-jfw-bios-upgrade-information-status;
         }
         case multichassis-tag {
           anyxml multi-routing-engine-results;
         }
       }
     }
   }
   rpc request-jfw-ssd-upgrade {
     description "Upgrade SSD firmware";
     input {
       leaf disk {
         description "1, 2";
         type string;
       }
     }
     output {
       choice output_c {
         case output-tag {
           leaf output {
             type string;
           }
         }
         case actual-tag {
           anyxml system-jfw-ssd-upgrade-information;
         }
         case multichassis-tag {
           anyxml multi-routing-engine-results;
         }
       }
     }
   }
   rpc request-jfw-bcm-pcie-upgrade {
     description "Upgrade BCM PCIe firmware";
     output {
       choice output_c {
         case output-tag {
           leaf output {
             type string;
           }
         }
         case actual-tag {
           anyxml system-jfw-bcm-pcie-upgrade-information;
         }
         case multichassis-tag {
           anyxml multi-routing-engine-results;
         }
       }
     }
   }
   rpc request-jfw-re-fpga-upgrade {
     description "Upgrade RE FPGA";
     input {
       leaf file {
         description "Jfirmware package file";
         type string;
       }
     }
     output {
       choice output_c {
         case output-tag {
           leaf output {
             type string;
           }
         }
         case actual-tag {
           anyxml system-jfw-re-fpga-upgrade-information;
         }
         case multichassis-tag {
           anyxml multi-routing-engine-results;
         }
       }
     }
   }
   rpc request-jfw-re-fpga-upgrade-status {
     description "Show RE FPGA Upgrade status";
     output {
       choice output_c {
         case output-tag {
           leaf output {
             type string;
           }
         }
         case actual-tag {
           anyxml system-jfw-re-fpga-upgrade-information-status;
         }
         case multichassis-tag {
           anyxml multi-routing-engine-results;
         }
       }
     }
   }
   rpc request-jfw-tmc-fpga-upgrade {
     description "Upgrade Mainboard TMC FPGA";
     output {
       choice output_c {
         case output-tag {
           leaf output {
             type string;
           }
         }
         case actual-tag {
           anyxml system-jfw-tmc-fpga-upgrade-information;
         }
         case multichassis-tag {
           anyxml multi-routing-engine-results;
         }
       }
     }
   }
   rpc request-jfw-tmc-fpga-upgrade-status {
     description "Show TMC Upgrade status";
     output {
       choice output_c {
         case output-tag {
           leaf output {
             type string;
           }
         }
         case actual-tag {
           anyxml system-jfw-tmc-fpga-upgrade-information-status;
         }
         case multichassis-tag {
           anyxml multi-routing-engine-results;
         }
       }
     }
   }
   rpc request-jfw-power-cpld-upgrade {
     description "Upgrade Power CPLD";
     output {
       choice output_c {
         case output-tag {
           leaf output {
             type string;
           }
         }
         case actual-tag {
           anyxml system-jfw-power-cpld-upgrade-information;
         }
         case multichassis-tag {
           anyxml multi-routing-engine-results;
         }
       }
     }
   }
   rpc request-jfw-powercpld-upgrade-status {
     description "Show Powercpld Upgrade status";
     output {
       choice output_c {
         case output-tag {
           leaf output {
             type string;
           }
         }
         case actual-tag {
           anyxml system-jfw-powercpld-upgrade-information-status;
         }
         case multichassis-tag {
           anyxml multi-routing-engine-results;
         }
       }
     }
   }
   rpc request-jfw-optics-sfp-upgrade {
     description "Upgrade Optics FPGA";
     output {
       choice output_c {
         case output-tag {
           leaf output {
             type string;
           }
         }
         case actual-tag {
           anyxml system-jfw-optics-sfp-upgrade-information;
         }
         case multichassis-tag {
           anyxml multi-routing-engine-results;
         }
       }
     }
   }
   rpc request-jfw-optics-sfp-upgrade-status {
     description "Show SFP Upgrade status";
     output {
       choice output_c {
         case output-tag {
           leaf output {
             type string;
           }
         }
         case actual-tag {
           anyxml system-jfw-optics-sfp-upgrade-information-status;
         }
         case multichassis-tag {
           anyxml multi-routing-engine-results;
         }
       }
     }
   }
   rpc request-jfw-optics-qsfp-upgrade {
     description "Upgrade Optics FPGA";
     output {
       choice output_c {
         case output-tag {
           leaf output {
             type string;
           }
         }
         case actual-tag {
           anyxml system-jfw-optics-qsfp-upgrade-information;
         }
         case multichassis-tag {
           anyxml multi-routing-engine-results;
         }
       }
     }
   }
   rpc request-jfw-optics-qsfp-upgrade-status {
     description "Show QSFP Upgrade status";
     output {
       choice output_c {
         case output-tag {
           leaf output {
             type string;
           }
         }
         case actual-tag {
           anyxml system-jfw-optics-qsfp-upgrade-information-status;
         }
         case multichassis-tag {
           anyxml multi-routing-engine-results;
         }
       }
     }
   }
   rpc request-jfw-allfw-upgrade {
     description "Upgrade all firmwares applicable in Jfirmware package";
     output {
       choice output_c {
         case output-tag {
           leaf output {
             type string;
           }
         }
         case actual-tag {
           anyxml system-jfw-allfw-upgrade-information;
         }
         case multichassis-tag {
           anyxml multi-routing-engine-results;
         }
       }
     }
   }
   rpc request-fpc-fpga-upgrade {
     description "Upgrade Line Card FPGAs";
     input {
       uses command-forwarding;
       leaf slot {
         description "FPC slot number";
         type union {
           type string {
             pattern "<.*>|$.*";
           }
           type uint32;
         }
       }
     }
     output {
       choice output_c {
         case output-tag {
           leaf output {
             type string;
           }
         }
         case actual-tag {
           anyxml system-fpga-upgrade-information;
         }
         case multichassis-tag {
           anyxml multi-routing-engine-results;
         }
       }
     }
   }
   rpc request-pem-firmware-upgrade {
     description "Upgrade CHASSIS PEM FW";
     input {
       leaf slot {
         description "PEM slot number";
         type union {
           type string {
             pattern "<.*>|$.*";
           }
           type uint32;
         }
       }
     }
     output {
       choice output_c {
         case output-tag {
           leaf output {
             type string;
           }
         }
         case actual-tag {
           anyxml system-firmware-information;
         }
         case multichassis-tag {
           anyxml multi-routing-engine-results;
         }
       }
     }
   }
   rpc request-bitscpld-firmware-upgrade {
     description "Upgrade BITSCPLD programmable on SPMC Mezz board";
     output {
       choice output_c {
         case output-tag {
           leaf output {
             type string;
           }
         }
         case actual-tag {
           anyxml system-firmware-information;
         }
         case multichassis-tag {
           anyxml multi-routing-engine-results;
         }
       }
     }
   }
   rpc request-cb-fpga-upgrade {
     description "Upgrade baseboard FPGA";
     input {
       choice which-arg {
         case fpga {
           leaf fpga {
             description "Upgrade baseboard FPGA";
             type empty;
           }
         }
         case port {
           leaf port {
             description "Upgrade baseboard port";
             type empty;
           }
         }
         case tic-fpga {
           leaf tic-fpga {
             description "Upgrade TIC FPGA";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       choice output_c {
         case output-tag {
           leaf output {
             type string;
           }
         }
         case actual-tag {
           anyxml system-firmware-information;
         }
         case multichassis-tag {
           anyxml multi-routing-engine-results;
         }
       }
     }
   }
   rpc request-i2c-fpga-upgrade {
     description "I2C FPGA Upgrade";
     output {
       choice output_c {
         case output-tag {
           leaf output {
             type string;
           }
         }
         case actual-tag {
           anyxml system-firmware-i2c-information;
         }
         case multichassis-tag {
           anyxml multi-routing-engine-results;
         }
       }
     }
   }
   rpc request-pem-firmware-downgrade {
     description "Upgrade CHASSIS PEM FW";
     input {
       leaf slot {
         description "PEM slot number";
         type union {
           type string {
             pattern "<.*>|$.*";
           }
           type uint32;
         }
       }
     }
     output {
       choice output_c {
         case output-tag {
           leaf output {
             type string;
           }
         }
         case actual-tag {
           anyxml system-firmware-information;
         }
         case multichassis-tag {
           anyxml multi-routing-engine-results;
         }
       }
     }
   }
   rpc request-bitscpld-firmware-downgrade {
     description "Upgrade BITSCPLD programmable on SPMC Mezz board";
     output {
       choice output_c {
         case output-tag {
           leaf output {
             type string;
           }
         }
         case actual-tag {
           anyxml system-firmware-information;
         }
         case multichassis-tag {
           anyxml multi-routing-engine-results;
         }
       }
     }
   }
   rpc request-cb-fpga-downgrade {
     description "Upgrade baseboard FPGA";
     input {
       choice which-arg {
         case fpga {
           leaf fpga {
             description "Upgrade baseboard FPGA";
             type empty;
           }
         }
         case port {
           leaf port {
             description "Upgrade baseboard port";
             type empty;
           }
         }
         case tic-fpga {
           leaf tic-fpga {
             description "Upgrade TIC FPGA";
             type empty;
           }
         }
       }
       leaf slot {
         description "CB slot number";
         type union {
           type string {
             pattern "<.*>|$.*";
           }
           type uint32;
         }
         mandatory true;
       }
       leaf tag {
         description "Firmware tag";
         type union {
           type string {
             pattern "<.*>|$.*";
           }
           type uint32 {
             range "0 .. 2";
           }
         }
         mandatory true;
       }
     }
     output {
       choice output_c {
         case output-tag {
           leaf output {
             type string;
           }
         }
         case actual-tag {
           anyxml system-firmware-information;
         }
         case multichassis-tag {
           anyxml multi-routing-engine-results;
         }
       }
     }
   }
   rpc request-i2c-fpga-downgrade {
     description "I2C FPGA Upgrade";
     output {
       choice output_c {
         case output-tag {
           leaf output {
             type string;
           }
         }
         case actual-tag {
           anyxml system-firmware-i2c-information;
         }
         case multichassis-tag {
           anyxml multi-routing-engine-results;
         }
       }
     }
   }
   rpc request-power-on-other-re {
     description "Power on the system";
     input {
       uses command-forwarding;
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc security-decrypt-password {
     description "Decrypt a $8$ or $9$-encrypted password";
     input {
       leaf password {
         description "A $8$ or $9$-encrypted password";
         type string;
         mandatory true;
       }
     }
     output {
       choice output_c {
         case output-tag {
           leaf output {
             type string;
           }
         }
         case actual-tag {
           anyxml decrypt-password-results;
         }
         case multichassis-tag {
           anyxml multi-routing-engine-results;
         }
       }
     }
   }
   rpc request-security-uefi-revoke {
     description "Revoke platform UEFI keys";
     input {
       leaf cmd {
         type string;
         mandatory true;
       }
     }
     output {
       choice output_c {
         case output-tag {
           leaf output {
             type string;
           }
         }
         case multichassis-tag {
           anyxml multi-routing-engine-results;
         }
       }
     }
   }
   rpc request-security-bios-upgrade {
     description "Upgrade BIOS from the location";
     input {
       leaf package-name {
         description "URL or path name of package";
         type jt:filename;
       }
       leaf re-slot {
         description "RE slot number";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc generate-pki-key-pair {
     description "Generate RSA, DSA or ECDSA private and public key pair";
     input {
       uses command-forwarding;
       choice daemon-select {
         case logical-system {
         }
       }
       leaf certificate-id {
         description "Certificate identifier";
         type string {
           length "1 .. 32";
           junos:posix-pattern "![/ %.]";
           junos:pattern-message "Must not contain '/', %, '.' or a space";
         }
         mandatory true;
       }
       leaf size {
         description "Size of key";
         default "2048";
         units "bits";
         type enumeration {
           enum "256" {
             description "256 bits (ECDSA only)";
           }
           enum "384" {
             description "384 bits (ECDSA only)";
           }
           enum "521" {
             description "521 bits (ECDSA only)";
           }
           enum "512" {
             description "512 bits (RSA only)";
           }
           enum "1024" {
             description "1024 bits (RSA/DSA only)";
           }
           enum "2048" {
             description "2048 bits (RSA/DSA only)";
           }
           enum "4096" {
             description "4096 bits (RSA/DSA only)";
           }
         }
       }
       leaf type {
         description "Algorithm for encrypting public private keys";
         default "rsa";
         type enumeration {
           enum "rsa" {
             description "RSA encryption";
           }
           enum "dsa" {
             description "DSA encryption";
           }
           enum "ecdsa" {
             description "ECDSA encryption";
           }
         }
       }
     }
     output {
       choice output_c {
         case output-tag {
           leaf output {
             type string;
           }
         }
         case actual-tag {
           anyxml cert-key-pair;
         }
         case multichassis-tag {
           anyxml multi-routing-engine-results;
         }
       }
     }
   }
   rpc generate-pki-certificate-request {
     description "Generate the certificate request in PKCS-10 format";
     input {
       uses command-forwarding;
       leaf ip-address {
         description "Static IP address of the device";
         type jt:ipaddr;
       }
       leaf ipv6-address {
         description "Static IPv6 address of the device for subject-alt-name";
         type jt:ipv6addr;
       }
       choice daemon-select {
         case logical-system {
         }
       }
       leaf filename {
         description "Local location for copy of certificate request";
         type string;
       }
       leaf subject {
         description "DC=<Domain component>,CN=<Common-Name>,OU=<Organizational-Unit-name>,O=<Organization-name>,SN=<Serial-Number>,L=<Locality>,ST=<state>,C=<Country>";
         type string;
         mandatory true;
       }
       leaf digest {
         description "Hash algorithm for signing RSA certificates";
         type enumeration {
           enum "sha-1" {
             description "SHA-1 digests (RSA/DSA only, default value for RSA/DSA)";
           }
           enum "sha-256" {
             description "SHA-256 digests (RSA/ECDSA only, default value for ECDSA)";
           }
           enum "sha-384" {
             description "SHA-384 digests (ECDSA only)";
           }
         }
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf certificate-id {
         description "Certificate identifier";
         type string {
           length "1 .. 32";
           junos:posix-pattern "![/%. ]";
           junos:pattern-message "Must not contain '/', %, '.' or a space";
         }
         mandatory true;
       }
       leaf domain-name {
         description "Fully qualified domain name";
         type string;
       }
       leaf email {
         description "Email address";
         type string;
       }
     }
     output {
       choice output_c {
         case output-tag {
           leaf output {
             type string;
           }
         }
         case multichassis-tag {
           anyxml multi-routing-engine-results;
         }
       }
     }
   }
   rpc load-pki-ca-certificate {
     description "Load the certificate onto the routing platform";
     input {
       uses command-forwarding;
       leaf ca-profile {
         description "Certificate authority profile";
         type string {
           length "1 .. 32";
           junos:posix-pattern "![/%. ]";
           junos:pattern-message "Must not contain '/', %, '.' or a space";
         }
         mandatory true;
       }
       choice daemon-select {
         case logical-system {
         }
       }
       leaf filename {
         description "File pathname containing certificate to load";
         type string;
         mandatory true;
       }
     }
     output {
       choice output_c {
         case output-tag {
           leaf output {
             type string;
           }
         }
         case actual-tag {
           anyxml cert-ca-load-status;
         }
         case multichassis-tag {
           anyxml multi-routing-engine-results;
         }
       }
     }
   }
   rpc request-security-pki-ca-profile-group {
     description "Perform operations on group of Certificate-authority(CA) certificates";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case actual-tag {
           anyxml ca-profile-group;
         }
         case multichassis-tag {
           anyxml multi-routing-engine-results;
         }
       }
     }
   }
   rpc request-security-pki-ca-profile-group-load {
     description "Load the certificate group onto the routing platform";
     input {
       uses command-forwarding;
       choice daemon-select {
         case logical-system {
         }
       }
       leaf ca-group-name {
         description "CA group identifier";
         type string {
           length "1 .. 24";
           junos:posix-pattern "![/ %]";
           junos:pattern-message "Must not contain '/', % or a space";
         }
         mandatory true;
       }
       leaf filename {
         description "File pathname containing certificate to load";
         type string;
         mandatory true;
       }
     }
     output {
       choice output_c {
         case output-tag {
           leaf output {
             type string;
           }
         }
         case actual-tag {
           anyxml ca-profile-group-load;
         }
         case multichassis-tag {
           anyxml multi-routing-engine-results;
         }
       }
     }
   }
   rpc verify-pki-ca-certificate {
     description "Verify the certificate";
     input {
       uses command-forwarding;
       choice daemon-select {
         case logical-system {
         }
       }
       leaf ca-profile {
         description "Certificate authority profile";
         type string {
           length "1 .. 32";
           junos:posix-pattern "![/%. ]";
           junos:pattern-message "Must not contain '/', %, '.' or a space";
         }
         mandatory true;
       }
     }
     output {
       choice output_c {
         case output-tag {
           leaf output {
             type string;
           }
         }
         case multichassis-tag {
           anyxml multi-routing-engine-results;
         }
       }
     }
   }
   rpc request-security-local-certificate-enroll {
     description "Enroll router certificate with CA online";
     input {
       uses command-forwarding;
       leaf certificate-id {
         description "Certificate identifier";
         type string {
           length "1 .. 32";
           junos:posix-pattern "![/%. ]";
           junos:pattern-message "Must not contain '/', %, '.' or a space";
         }
         mandatory true;
       }
       leaf ca-profile {
         description "Certificate authority profile";
         type string {
           length "1 .. 32";
           junos:posix-pattern "![/%. ]";
           junos:pattern-message "Must not contain '/', %, '.' or a space";
         }
         mandatory true;
       }
       leaf challenge-password {
         description "Password used by CA for enrollment and revocation";
         type string;
         mandatory true;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
       choice daemon-select {
         case logical-system {
         }
       }
       leaf domain-name {
         description "Fully qualified domain name";
         type string;
       }
       leaf email {
         description "Email address";
         type string;
       }
     }
     output {
       choice output_c {
         case output-tag {
           leaf output {
             type string;
           }
         }
         case actual-tag {
           anyxml local-certificate-enroll;
         }
         case multichassis-tag {
           anyxml multi-routing-engine-results;
         }
       }
     }
   }
   rpc request-security-local-certificate-enroll-cmpv2 {
     description "Enroll certificate using CMPv2 protocol";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf ca-profile {
         description "Certificate authority profile";
         type string {
           length "1 .. 32";
           junos:posix-pattern "![/%. ]";
           junos:pattern-message "Must not contain '/', %, '.' or a space";
         }
         mandatory true;
       }
       leaf ca-dn {
         description "Subject DN for CMPv2 server, if CA certificate is not enrolled";
         type string;
       }
       leaf ca-secret {
         description "Initial Authentication Key, received from CMPv2 server";
         type string;
         mandatory true;
       }
       leaf ca-reference {
         description "Reference value associated with secret, received from CMPv2 server";
         type string;
         mandatory true;
       }
     }
     output {
       choice output_c {
         case output-tag {
           leaf output {
             type string;
           }
         }
         case actual-tag {
           anyxml local-certificate-enroll-cmpv2;
         }
         case multichassis-tag {
           anyxml multi-routing-engine-results;
         }
       }
     }
   }
   rpc request-security-local-certificate-enroll-scep {
     description "Enroll end-entity certificate using SCEP protocol";
     input {
       uses command-forwarding;
       leaf certificate-id {
         description "Certificate identifier";
         type string {
           length "1 .. 32";
           junos:posix-pattern "![/%. ]";
           junos:pattern-message "Must not contain '/', %, '.' or a space";
         }
         mandatory true;
       }
       leaf ca-profile {
         description "Certificate authority profile";
         type string {
           length "1 .. 32";
           junos:posix-pattern "![/%. ]";
           junos:pattern-message "Must not contain '/', %, '.' or a space";
         }
         mandatory true;
       }
       leaf challenge-password {
         description "Password used by CA for enrollment and revocation";
         type string;
         mandatory true;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
       leaf ip-address {
         description "Static IP address of the device";
         type jt:ipaddr;
       }
       leaf ipv6-address {
         description "Static IPv6 address of the device for subject-alt-name";
         type jt:ipv6addr;
       }
       leaf domain-name {
         description "Fully qualified domain name for subject-alt-name";
         type string;
       }
       leaf email {
         description "Email address";
         type string;
       }
       leaf subject {
         description "DC=<Domain component>,CN=<Common-Name>,OU=<Organizational-Unit-name>,O=<Organization-name>,SN=<Serial-Number>,L=<Locality>,ST=<state>,C=<Country>";
         type string;
         mandatory true;
       }
       leaf validity-start-time {
         description "Certificate validity start time (YYYY-MM-DD.HH:MM:SS)";
         status deprecated;
         type jt:time;
       }
       leaf validity-end-time {
         description "Certificate validity end time (YYYY-MM-DD.HH:MM:SS)";
         status deprecated;
         type jt:time;
       }
       leaf digest {
         description "Hash algorithm for signing RSA certificates";
         type enumeration {
           enum "sha-1" {
             description "SHA-1 digests (default value)";
           }
           enum "sha-256" {
             description "SHA-256 digests";
           }
         }
       }
     }
     output {
       choice output_c {
         case output-tag {
           leaf output {
             type string;
           }
         }
         case actual-tag {
           anyxml local-certificate-enroll-scep;
         }
         case multichassis-tag {
           anyxml multi-routing-engine-results;
         }
       }
     }
   }
   rpc request-security-local-certificate-re-enroll {
     description "Re-enroll router certificate with CA online";
     output {
       choice output_c {
         case output-tag {
           leaf output {
             type string;
           }
         }
         case actual-tag {
           anyxml local-certificate-re-enroll;
         }
         case multichassis-tag {
           anyxml multi-routing-engine-results;
         }
       }
     }
   }
   rpc request-security-local-cert-re-enroll-cmpv2 {
     description "Enroll certificate using CMPv2 protocol";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
       leaf ca-profile {
         description "Certificate authority profile";
         type string {
           length "1 .. 32";
           junos:posix-pattern "![/%. ]";
           junos:pattern-message "Must not contain '/', %, '.' or a space";
         }
       }
       leaf re-generate-keypair {
         description "Generate new keypair for re-enrollment";
         type empty;
       }
     }
     output {
       choice output_c {
         case output-tag {
           leaf output {
             type string;
           }
         }
         case actual-tag {
           anyxml local-cert-re-enroll-cmpv2;
         }
         case multichassis-tag {
           anyxml multi-routing-engine-results;
         }
       }
     }
   }
   rpc request-security-local-cert-re-enroll-scep {
     description "Enroll end-entity certificate using SCEP protocol";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
       leaf ca-profile {
         description "Certificate authority profile";
         type string {
           length "1 .. 32";
           junos:posix-pattern "![/%. ]";
           junos:pattern-message "Must not contain '/', %, '.' or a space";
         }
       }
       leaf challenge-password {
         description "Password used by CA for enrollment and revocation";
         type string;
         mandatory true;
       }
       leaf re-generate-keypair {
         description "Generate new keypair for re-enrollment";
         type empty;
       }
       leaf scep-encryption-algorithm {
         description "Encrypion algorithm used for SCEP-PKCS7";
         type enumeration {
           enum "des" {
             description "DES Encryption";
           }
           enum "des3" {
             description "DES-3 Encryption (default)";
           }
         }
       }
       leaf scep-digest-algorithm {
         description "Hash algorithm used for SCEP-PKCS7";
         type enumeration {
           enum "md5" {
             description "MD-5 digest";
           }
           enum "sha1" {
             description "SHA-1 digest (default)";
           }
         }
       }
     }
     output {
       choice output_c {
         case output-tag {
           leaf output {
             type string;
           }
         }
         case actual-tag {
           anyxml local-cert-re-enroll-scep;
         }
         case multichassis-tag {
           anyxml multi-routing-engine-results;
         }
       }
     }
   }
   rpc request-security-local-certificate-export {
     description "Export Certificate";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier";
         type string {
           length "1 .. 32";
           junos:posix-pattern "![/%. ]";
           junos:pattern-message "Must not contain '/', %, '.' or a space";
         }
         mandatory true;
       }
       leaf filename {
         description "Local location for copy of certificate.";
         type string;
         mandatory true;
       }
       leaf type {
         description "Type of certificate.";
         default "pem";
         type enumeration {
           enum "pem" {
             description "PEM format";
           }
           enum "der" {
             description "DER format";
           }
         }
       }
     }
     output {
       choice output_c {
         case output-tag {
           leaf output {
             type string;
           }
         }
         case actual-tag {
           anyxml local-certificate-export;
         }
         case multichassis-tag {
           anyxml multi-routing-engine-results;
         }
       }
     }
   }
   rpc load-pki-local-certificate {
     description "Load the certificate onto the routing platform";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
       leaf filename {
         description "File pathname containing certificate to load";
         type string;
         mandatory true;
       }
       leaf key {
         description "File pathname containing the private key/key-pair to load";
         type string;
       }
       leaf passphrase {
         description "Passphrase of the private key/key-pair (PEM) file";
         type string;
       }
     }
     output {
       choice output_c {
         case output-tag {
           leaf output {
             type string;
           }
         }
         case actual-tag {
           anyxml cert-load-status;
         }
         case multichassis-tag {
           anyxml multi-routing-engine-results;
         }
       }
     }
   }
   rpc verify-pki-local-certificate {
     description "Verify the certificate";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
     }
     output {
       choice output_c {
         case output-tag {
           leaf output {
             type string;
           }
         }
         case multichassis-tag {
           anyxml multi-routing-engine-results;
         }
       }
     }
   }
   rpc generate-pki-self-signed-local-certificate {
     description "Generate a self-signed certificate";
     input {
       uses command-forwarding;
       choice daemon-select {
         case logical-system {
         }
       }
       leaf certificate-id {
         description "Certificate identifier";
         type string {
           length "1 .. 32";
           junos:posix-pattern "![/%. ]";
           junos:pattern-message "Must not contain '/', %, '.' or a space";
         }
         mandatory true;
       }
       leaf domain-name {
         description "Fully qualified domain name";
         type string;
         mandatory true;
       }
       leaf ip-address {
         description "Static IP address of the device";
         type jt:ipaddr;
       }
       leaf email {
         description "Email address of the entity owning the certificate";
         type string;
       }
       leaf subject {
         description "DC=<Domain component>,CN=<Common-Name>,OU=<Organizational-Unit-name>,O=<Organization-name>,SN=<Serial-Number>,L=<Locality>,ST=<state>,C=<Country>";
         type string;
         mandatory true;
       }
       leaf add-ca-constraint {
         description "Certificate can be used for signing other certificates.";
         type empty;
       }
       leaf digest {
         description "Hash algorithm for signing RSA certificates";
         type enumeration {
           enum "sha-1" {
             description "SHA-1 digests";
           }
           enum "sha-256" {
             description "SHA-256 digests (default value)";
           }
         }
       }
     }
     output {
       choice output_c {
         case output-tag {
           leaf output {
             type string;
           }
         }
         case multichassis-tag {
           anyxml multi-routing-engine-results;
         }
       }
     }
   }
   rpc request-security-key-pair-export {
     description "Export Keypair in PEM format";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf certificate-id {
         description "Certificate identifier for keypair";
         type string {
           length "1 .. 32";
           junos:posix-pattern "![/%. ]";
           junos:pattern-message "Must not contain '/', %, '.' or a space";
         }
         mandatory true;
       }
       leaf filename {
         description "Local location for copy of keypair.";
         type string;
         mandatory true;
       }
       leaf type {
         description "Type of key-pair.";
         default "pem";
         type enumeration {
           enum "pem" {
             description "PEM format";
           }
           enum "der" {
             description "DER format";
           }
         }
       }
       leaf passphrase {
         description "Passphrase of the private key/key-pair (PEM) file";
         type string;
         mandatory true;
       }
     }
     output {
       choice output_c {
         case output-tag {
           leaf output {
             type string;
           }
         }
         case actual-tag {
           anyxml key-pair-export;
         }
         case multichassis-tag {
           anyxml multi-routing-engine-results;
         }
       }
     }
   }
   rpc load-pki-crl {
     description "Load the CRL onto the routing platform";
     input {
       uses command-forwarding;
       choice daemon-select {
         case logical-system {
         }
       }
       leaf ca-profile {
         description "Certificate authority profile";
         type string {
           length "1 .. 32";
           junos:posix-pattern "![/%. ]";
           junos:pattern-message "Must not contain '/', %, '.' or a space";
         }
         mandatory true;
       }
       leaf filename {
         description "Pathname of file containing CRL to load";
         type string;
         mandatory true;
       }
     }
     output {
       choice output_c {
         case output-tag {
           leaf output {
             type string;
           }
         }
         case multichassis-tag {
           anyxml multi-routing-engine-results;
         }
       }
     }
   }
   rpc verify-integrity-status {
     description "Check the integrity of PKI files (in CC mode)";
     input {
       uses command-forwarding;
       choice daemon-select {
         case logical-system {
         }
       }
     }
     output {
       choice output_c {
         case output-tag {
           leaf output {
             type string;
           }
         }
         case actual-tag {
           anyxml verify-integrity-status;
         }
         case multichassis-tag {
           anyxml multi-routing-engine-results;
         }
       }
     }
   }
   rpc request-idp-policy-load {
     description "Load a compiled policy";
     input {
       uses command-forwarding;
       leaf policy {
         description "Compiled policy file name";
         type string;
       }
       leaf no-ai {
         description "Application identification flag";
         type empty;
       }
       leaf detector {
         description "Detector file name";
         type string;
       }
     }
     output {
       choice output_c {
         case output-tag {
           leaf output {
             type string;
           }
         }
         case actual-tag {
           anyxml request-idp-policy-load;
         }
         case multichassis-tag {
           anyxml multi-routing-engine-results;
         }
       }
     }
   }
   rpc request-idp-storage-cleanup {
     description "Delete non-essential idp files for freeing up disk space";
     input {
       uses command-forwarding;
       choice cleanup-choice {
         case cache-files {
           leaf cache-files {
             description "Deletes DFA cache files used for optimizing idp policy compilation";
             type empty;
           }
         }
         case downloaded-files {
           leaf downloaded-files {
             description "Deletes downloaded security-package files (doesn't affect installed database)";
             type empty;
           }
         }
       }
     }
     output {
       choice output_c {
         case output-tag {
           leaf output {
             type string;
           }
         }
         case actual-tag {
           anyxml request-idp-storage-cleanup;
         }
         case multichassis-tag {
           anyxml multi-routing-engine-results;
         }
       }
     }
   }
   rpc request-idp-security-package-install {
     description "Update attack database, active policy, detector with new package";
     input {
       uses command-forwarding;
       choice re-selector-idpd {
         case re0 {
         }
         case re1 {
         }
       }
       choice install-choice {
         case update-attack-database-only {
           leaf update-attack-database-only {
             description "Don't update/push active policy or detector to data plane";
             type empty;
           }
         }
         case policy-templates {
           leaf policy-templates {
             description "Update previously installed policy-templates with newly downloaded ones";
             type empty;
           }
         }
         case precompiled-policy {
           leaf precompiled-policy {
             description "Update dataplane 'Recommended' policy and detector for it with newly downloaded ones";
             type empty;
           }
         }
         case older-detector {
           leaf older-detector {
             description "Update dataplane with older detector";
             type empty;
           }
         }
         case status {
           leaf status {
             description "Retrieve the status of security package load operation";
             type empty;
           }
         }
         case policy-template-result {
           leaf policy-template-result {
             description "Status of policy templates operation";
             type empty;
           }
         }
       }
     }
     output {
       choice output_c {
         case output-tag {
           leaf output {
             type string;
           }
         }
         case actual-tag {
           anyxml secpack-update-status;
         }
         case multichassis-tag {
           anyxml multi-routing-engine-results;
         }
       }
     }
   }
   rpc request-idp-security-package-download {
     description "Download security package (Package includes detector and deltas for attack table)";
     input {
       uses command-forwarding;
       choice re-selector-idpd {
         case re0 {
         }
         case re1 {
         }
       }
       choice download-choice {
         case full-update {
           leaf full-update {
             description "Download package with complete attack table";
             type empty;
           }
         }
         case package-option {
           leaf package-option {
             type enumeration {
               enum "check-server" {
                 description "Retrieve version information for latest package on server";
               }
               enum "policy-templates" {
                 description "Download policy templates";
               }
               enum "precompiled-policy" {
                 description "Download pre-compiled 'Recommended' policy and detector for it";
               }
             }
           }
         }
         case status {
           leaf status {
             description "Retrieve the status of security package download operation";
             type empty;
           }
         }
         case policy-template-file {
           leaf policy-template-file {
             description "Current status of policy template file";
             type empty;
           }
         }
         case policy-template-result {
           leaf policy-template-result {
             description "Status of policy templates operation";
             type empty;
           }
         }
       }
     }
     output {
       choice output_c {
         case output-tag {
           leaf output {
             type string;
           }
         }
         case actual-tag {
           anyxml secpack-download-status;
         }
         case multichassis-tag {
           anyxml multi-routing-engine-results;
         }
       }
     }
   }
   rpc request-idp-security-package-download-version {
     description "Version of package to download";
     input {
       uses command-forwarding;
       choice re-selector-idpd {
         case re0 {
         }
         case re1 {
         }
       }
       leaf version-value {
         description "Version number";
         type union {
           type uint32;
           type string {
             pattern "<.*>|$.*";
           }
         }
         mandatory true;
       }
       leaf full-update {
         description "Download package with complete attack table";
         type empty;
       }
     }
     output {
       choice output_c {
         case output-tag {
           leaf output {
             type string;
           }
         }
         case actual-tag {
           anyxml secpack-download-status;
         }
         case multichassis-tag {
           anyxml multi-routing-engine-results;
         }
       }
     }
   }
   rpc request-idp-security-package-offline-download {
     description "Unzip the security package and copy the xml files";
     input {
       uses command-forwarding;
       choice re-selector-idpd {
         case re0 {
         }
         case re1 {
         }
       }
       choice offline-download-choice {
         case package-path {
           leaf package-path {
             description "Package path of the zipped security package ";
             type string;
           }
         }
         case status {
           leaf status {
             description "Retrieve the status of offline package download operation";
             type empty;
           }
         }
       }
     }
     output {
       choice output_c {
         case output-tag {
           leaf output {
             type string;
           }
         }
         case actual-tag {
           anyxml offline-download-status;
         }
         case multichassis-tag {
           anyxml multi-routing-engine-results;
         }
       }
     }
   }
   rpc request-interface-operation {
     description "Perform interface operations";
     output {
       choice output_c {
         case output-tag {
           leaf output {
             type string;
           }
         }
         case multichassis-tag {
           anyxml multi-routing-engine-results;
         }
       }
     }
   }
   rpc revert-redundancy-interface-to-primary {
     description "Revert redundancy interface to its primary";
     input {
       leaf interface-name {
         description "Name of interface";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc switch-redundancy-interface-to-secondary {
     description "Switch redundancy interface over to its secondary";
     input {
       leaf interface-name {
         description "Name of interface";
         type union {
           type jt:interface-wildcard;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-switch-anchor {
     description "Manually switch the anchoring device.";
     input {
       leaf anchoring-device-name {
         description "Anchoring PFE or FPC name.";
         type string {
           junos:posix-pattern "^((pfe-)|(fpc-))";
           junos:pattern-message "Invalid anchoring interface or FPC name.";
         }
       }
     }
     output {
       choice output_c {
         case output-tag {
           leaf output {
             type string;
           }
         }
         case multichassis-tag {
           anyxml multi-routing-engine-results;
         }
       }
     }
   }
   rpc request-intf-modem-reset {
     description "Reset the modem device";
     input {
       leaf interface-name {
         description "Name of physical interface";
         type string;
         mandatory true;
       }
     }
     output {
       choice output_c {
         case output-tag {
           leaf output {
             type string;
           }
         }
         case multichassis-tag {
           anyxml multi-routing-engine-results;
         }
       }
     }
   }
   rpc request-load-balancing-revert {
     description "Revert load-balancing member interface";
     input {
       leaf interface-name {
         description "Name of member-interface";
         type union {
           type jt:interface-wildcard;
           type string {
             pattern "<.*>|$.*";
           }
         }
         mandatory true;
       }
     }
     output {
       choice output_c {
         case output-tag {
           leaf output {
             type string;
           }
         }
         case actual-tag {
           anyxml load-balancing-revert;
         }
         case multichassis-tag {
           anyxml multi-routing-engine-results;
         }
       }
     }
   }
   rpc request-load-balancing-switchover {
     description "Switch load-balancing member interface to backup";
     input {
       leaf interface-name {
         description "Name of member interface";
         type union {
           type jt:interface-wildcard;
           type string {
             pattern "<.*>|$.*";
           }
         }
         mandatory true;
       }
       leaf force {
         description "Force a active member switchover";
         type empty;
       }
     }
     output {
       choice output_c {
         case output-tag {
           leaf output {
             type string;
           }
         }
         case actual-tag {
           anyxml rdd-action-result;
         }
         case multichassis-tag {
           anyxml multi-routing-engine-results;
         }
       }
     }
   }
   rpc request-interface-mcae-switchover {
     description "Request MC-AE mastership switchover";
     input {
       leaf mcae-id {
         description "MC-AE id";
         type union {
           type uint16;
           type string {
             pattern "<.*>|$.*";
           }
         }
         mandatory true;
       }
     }
     output {
       choice output_c {
         case output-tag {
           leaf output {
             type string;
           }
         }
         case actual-tag {
           anyxml interface-mcae-switchover;
         }
         case multichassis-tag {
           anyxml multi-routing-engine-results;
         }
       }
     }
   }
   rpc request-interface-mcae-switchover-immediate {
     description "Request MC-AE mastership switchover immediate";
     input {
       leaf mcae-id {
         description "MC-AE id";
         type union {
           type uint16;
           type string {
             pattern "<.*>|$.*";
           }
         }
         mandatory true;
       }
     }
     output {
       choice output_c {
         case output-tag {
           leaf output {
             type string;
           }
         }
         case actual-tag {
           anyxml interface-mcae-switchover-immediate;
         }
         case multichassis-tag {
           anyxml multi-routing-engine-results;
         }
       }
     }
   }
   rpc request-interface-link-degade-recover {
     description "Perfom manual link recovery";
     input {
       leaf interface-name {
         description "Name of interface";
         type union {
           type jt:interface-device;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-rebalance-interface {
     description "Request rebalance of interfaces on the interface";
     input {
       leaf interface-name {
         description "Name of the interface";
         type string;
         mandatory true;
       }
     }
     output {
       choice output_c {
         case output-tag {
           leaf output {
             type string;
           }
         }
         case actual-tag {
           anyxml rebalance-interface;
         }
         case multichassis-tag {
           anyxml multi-routing-engine-results;
         }
       }
     }
   }
   rpc extension-service-start {
     description "Start JET application";
     input {
       leaf invoke-debugger {
         description "Invoke extension-service in debugger mode";
         type enumeration {
           enum "cli" {
             description "Invoke debugger in cli";
           }
         }
       }
       leaf application-name {
         description "Application name";
         type jt:filename;
         mandatory true;
       }
     }
     output {
       choice output_c {
         case output-tag {
           leaf output {
             type string;
           }
         }
         case multichassis-tag {
           anyxml multi-routing-engine-results;
         }
       }
     }
   }
   rpc extension-service-stop {
     description "Stop JET application";
     input {
       leaf application-name {
         description "Application name";
         type jt:filename;
         mandatory true;
       }
     }
     output {
       choice output_c {
         case output-tag {
           leaf output {
             type string;
           }
         }
         case multichassis-tag {
           anyxml multi-routing-engine-results;
         }
       }
     }
   }
   rpc clear-jdaf-command-client-stats {
     description "Clear JDAF client side statistics";
     output {
       choice output_c {
         case output-tag {
           leaf output {
             type string;
           }
         }
         case actual-tag {
           anyxml jdaf-request-no-response;
         }
         case multichassis-tag {
           anyxml multi-routing-engine-results;
         }
       }
     }
   }
   rpc clear-jdaf-command-server-stats {
     description "Clear JDAF server statistics";
     output {
       choice output_c {
         case output-tag {
           leaf output {
             type string;
           }
         }
         case multichassis-tag {
           anyxml multi-routing-engine-results;
         }
       }
     }
   }
   rpc clear-jdaf-config-client-stats {
     description "Clear JDAF client side statistics";
     output {
       choice output_c {
         case output-tag {
           leaf output {
             type string;
           }
         }
         case actual-tag {
           anyxml jdaf-request-no-response;
         }
         case multichassis-tag {
           anyxml multi-routing-engine-results;
         }
       }
     }
   }
   rpc clear-jdaf-config-server-stats {
     description "Clear JDAF server statistics";
     output {
       choice output_c {
         case output-tag {
           leaf output {
             type string;
           }
         }
         case multichassis-tag {
           anyxml multi-routing-engine-results;
         }
       }
     }
   }
   rpc clear-jdaf-firewall-client-stats {
     description "Clear JDAF client side statistics";
     input {
       leaf client-id {
         description "Client id";
         default "0";
         type union {
           type uint32;
           type string {
             pattern "<.*>|$.*";
           }
         }
       }
     }
     output {
       choice output_c {
         case output-tag {
           leaf output {
             type string;
           }
         }
         case actual-tag {
           anyxml jdaf-request-no-response;
         }
         case multichassis-tag {
           anyxml multi-routing-engine-results;
         }
       }
     }
   }
   rpc clear-jdaf-firewall-server-stats {
     description "Clear JDAF server statistics";
     output {
       choice output_c {
         case output-tag {
           leaf output {
             type string;
           }
         }
         case multichassis-tag {
           anyxml multi-routing-engine-results;
         }
       }
     }
   }
   rpc clear-jdaf-interface-client-stats {
     description "Clear JDAF client side statistics";
     input {
       leaf client-id {
         description "Client id";
         default "0";
         type union {
           type uint32;
           type string {
             pattern "<.*>|$.*";
           }
         }
       }
     }
     output {
       choice output_c {
         case output-tag {
           leaf output {
             type string;
           }
         }
         case actual-tag {
           anyxml jdaf-request-no-response;
         }
         case multichassis-tag {
           anyxml multi-routing-engine-results;
         }
       }
     }
   }
   rpc clear-jdaf-interface-server-stats {
     description "Clear JDAF server statistics";
     output {
       choice output_c {
         case output-tag {
           leaf output {
             type string;
           }
         }
         case multichassis-tag {
           anyxml multi-routing-engine-results;
         }
       }
     }
   }
   rpc clear-jdaf-route-client-stats {
     description "Clear JDAF client side statistics";
     input {
       leaf client-id {
         description "Client id";
         default "0";
         type union {
           type uint32;
           type string {
             pattern "<.*>|$.*";
           }
         }
       }
     }
     output {
       choice output_c {
         case output-tag {
           leaf output {
             type string;
           }
         }
         case actual-tag {
           anyxml jdaf-request-no-response;
         }
         case multichassis-tag {
           anyxml multi-routing-engine-results;
         }
       }
     }
   }
   rpc clear-jdaf-route-server-stats {
     description "Clear JDAF server statistics";
     output {
       choice output_c {
         case output-tag {
           leaf output {
             type string;
           }
         }
         case multichassis-tag {
           anyxml multi-routing-engine-results;
         }
       }
     }
   }
   rpc request-dhcp-server-reconfigure-information {
     description "Perform DHCP server reconfigure operation";
     input {
       choice reconfigure-choice {
         case address {
           leaf address {
             description "IP address or MAC address or Session Id of DHCP client binding";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-server-reconfigure-interface {
     description "Name of interface";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc request-dhcp-server-regenerate-persistent-file {
     description "Triggers the flat file backup operation";
     output {
       choice output_c {
         case output-tag {
           leaf output {
             type string;
           }
         }
         case multichassis-tag {
           anyxml multi-routing-engine-results;
         }
       }
     }
   }
   rpc request-dhcp-server-restore-client-from-file {
     description "Triggers the flat file restore operation";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-client-renew-information {
     description "Request DHCP client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-leasequery {
     description "Perform DHCP relay leasequery operation";
     input {
       leaf address {
         description "Query by IPv4 address or mac-address or Client-ID";
         type string;
         mandatory true;
       }
       leaf gateway-address {
         description "Giaddr of leasequery packet";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery {
     description "Perform DHCP relay bulk leasequery operation";
     input {
       leaf address {
         description "Query by IPv4 address or mac-address or Client-ID";
         type string;
       }
       choice query-server {
         case server-address {
           leaf server-address {
             description "Send leasequery to server address";
             type string;
           }
         }
         case server-group {
           leaf server-group {
             description "Send leasequery to servers in server-group";
             type string;
           }
         }
       }
       leaf all-configured-ip {
         description "Query by all-configure-ip-addresss";
         type empty;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery-relay-id {
     description "Query by relay-id";
     input {
       leaf relay-id {
         description "Query by relay-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-bulk-leasequery-remote-id {
     description "Query by remote-id";
     input {
       leaf remote-id {
         description "Query by remote-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-active-leasequery {
     description "Request DHCP active-leasequery operations";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-alq-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-relay-alq-interface {
     description "Active-leasequery interface";
     input {
       leaf interface-name {
         description "Active-leasequery interface name";
         type string;
         mandatory true;
       }
     }
     output {
       choice output_c {
         case output-tag {
           leaf output {
             type string;
           }
         }
         case multichassis-tag {
           anyxml multi-routing-engine-results;
         }
       }
     }
   }
   rpc request-dhcp-relay-regenerate-persistent-file {
     description "Triggers the flat file backup operation";
     output {
       choice output_c {
         case output-tag {
           leaf output {
             type string;
           }
         }
         case multichassis-tag {
           anyxml multi-routing-engine-results;
         }
       }
     }
   }
   rpc request-dhcp-relay-restore-client-from-file {
     description "Triggers the flat file restore operation";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcp-regenerate-persistent-file {
     description "Triggers the flat file backup operation";
     output {
       choice output_c {
         case output-tag {
           leaf output {
             type string;
           }
         }
         case multichassis-tag {
           anyxml multi-routing-engine-results;
         }
       }
     }
   }
   rpc request-dhcp-restore-client-from-file {
     description "Triggers the flat file restore operation";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-client-renew-information {
     description "Request DHCP client renew";
     input {
       choice renew-choice {
         case interface {
           leaf interface {
             description "Interface name of DHCP client";
             type string;
           }
         }
         case all {
           leaf all {
             description "Renew all clients";
             type empty;
           }
         }
       }
       leaf routing-instance {
         description "Name of routing instance";
         type string;
       }
       choice lsys-tenant {
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-server-reconfigure-information {
     description "Perform DHCPv6 server reconfigure operation";
     input {
       choice reconfigure-choice {
         case address {
           leaf address {
             description "IPv6 Prefix, session-id or CID of DHCPv6 client binding";
             type string;
           }
         }
         case all {
           leaf all {
             description "Reconfigure all clients";
             type empty;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-server-reconfigure-interface {
     description "Name of interface";
     input {
       leaf interface-name {
         description "Name of interface";
         type string;
         mandatory true;
       }
     }
     output {
       choice output_c {
         case output-tag {
           leaf output {
             type string;
           }
         }
         case multichassis-tag {
           anyxml multi-routing-engine-results;
         }
       }
     }
   }
   rpc request-dhcpv6-server-regenerate-persistent-file {
     description "Triggers the flat file backup operation";
     output {
       choice output_c {
         case output-tag {
           leaf output {
             type string;
           }
         }
         case multichassis-tag {
           anyxml multi-routing-engine-results;
         }
       }
     }
   }
   rpc request-dhcpv6-server-restore-client-from-file {
     description "Triggers the flat file restore operation";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-leasequery {
     description "Perform DHCPv6 relay leasequery operation";
     input {
       leaf address {
         description "Query by IPv6 Prefix or CID of DHCPv6 client binding";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery {
     description "Perform DHCPv6 relay bulk leasequery operation";
     input {
       leaf address {
         description "Query by IPv6 Prefix or CID of DHCPv6 client binding";
         type string;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-relay-id {
     description "Query by relay-id";
     input {
       leaf relay-id {
         description "Query by relay-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-link-addr {
     description "Query by link-address";
     input {
       leaf link-addr {
         description "Query by link-address";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-bulk-leasequery-remote-id {
     description "Query by remote-id";
     input {
       leaf remote-id {
         description "Query by remote-id";
         type string;
         mandatory true;
       }
       choice query-server {
         case server-address {
           leaf server-address {
             description "Send leasequery to server address";
             type string;
           }
         }
         case server-group {
           leaf server-group {
             description "Send leasequery to servers in server-group";
             type string;
           }
         }
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-regenerate-persistent-file {
     description "Triggers the flat file backup operation";
     output {
       choice output_c {
         case output-tag {
           leaf output {
             type string;
           }
         }
         case multichassis-tag {
           anyxml multi-routing-engine-results;
         }
       }
     }
   }
   rpc request-dhcpv6-relay-restore-client-from-file {
     description "Triggers the flat file restore operation";
     input {
       leaf from-file {
         description "Restore subscribers from file";
         type empty;
         mandatory true;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-active-leasequery {
     description "Request DHCP active-leasequery operations";
     input {
       leaf discover-neighbor {
         description "Discover neighbors capable of hosting subscribers";
         type empty;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-alq-peer {
     description "Active-leasequery peer";
     input {
       leaf peer-address {
         description "Active-leasequery peer address";
         type jt:ipaddr;
         mandatory true;
       }
       leaf routing-instance {
         description "Name of routing instance";
         type string;
       }
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-dhcpv6-relay-alq-interface {
     description "Active-leasequery interface";
     input {
       leaf interface-name {
         description "Active-leasequery interface name";
         type string;
         mandatory true;
       }
     }
     output {
       choice output_c {
         case output-tag {
           leaf output {
             type string;
           }
         }
         case multichassis-tag {
           anyxml multi-routing-engine-results;
         }
       }
     }
   }
   rpc request-as-ra-guard-forward-interface {
     description "Name of interface";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-block-interface {
     description "Name of interface";
     input {
       leaf interface-name {
         description "Name of interface";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-as-ra-guard-learn-interface {
     description "RA Guard Learn on an Interface";
     input {
       leaf interface {
         description "RA Guard Learn on an interface";
         type union {
           type jt:interface-name;
           type string {
             pattern "<.*>|$.*";
           }
         }
         mandatory true;
       }
       leaf duration {
         description "Time window for RA Guard learn";
         units "seconds";
         type union {
           type string {
             pattern "<.*>|$.*";
           }
           type uint32 {
             range "1 .. 3600";
           }
         }
         mandatory true;
       }
     }
     output {
       choice output_c {
         case output-tag {
           leaf output {
             type string;
           }
         }
         case multichassis-tag {
           anyxml multi-routing-engine-results;
         }
       }
     }
   }
   rpc request-slaac-unblock-all {
     description "Unblock all interfaces";
     output {
       choice output_c {
         case output-tag {
           leaf output {
             type string;
           }
         }
         case multichassis-tag {
           anyxml multi-routing-engine-results;
         }
       }
     }
   }
   rpc request-slaac-unblock-interface {
     description "Name of interface to unblock";
     input {
       leaf interface-name {
         description "Interface-name";
         type union {
           type jt:interface-name;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-static-subscribers-login {
     description "Login static subscribers";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
     output {
       choice output_c {
         case output-tag {
           leaf output {
             type string;
           }
         }
         case actual-tag {
           anyxml static-subscribers-information;
         }
         case multichassis-tag {
           anyxml multi-routing-engine-results;
         }
       }
     }
   }
   rpc request-static-subscribers-logout {
     description "Logout static subscribers";
     input {
       choice filter {
         case interface {
           leaf interface {
             description "Interface name";
             type union {
               type jt:interface-name;
               type string {
                 pattern "<.*>|$.*";
               }
             }
           }
         }
         case group {
           leaf group {
             description "Group name";
             type string {
               length "1 .. 64";
             }
           }
         }
       }
     }
     output {
       choice output_c {
         case output-tag {
           leaf output {
             type string;
           }
         }
         case actual-tag {
           anyxml static-subscribers-information;
         }
         case multichassis-tag {
           anyxml multi-routing-engine-results;
         }
       }
     }
   }
   rpc twamp-test-start {
     description "Start TWAMP test sessions";
     input {
       leaf control-connection {
         description "Name of the control connection";
         default "all";
         type string;
       }
     }
     output {
       choice output_c {
         case output-tag {
           leaf output {
             type string;
           }
         }
         case multichassis-tag {
           anyxml multi-routing-engine-results;
         }
       }
     }
   }
   rpc twamp-test-stop {
     description "Stop TWAMP test sessions";
     input {
       leaf control-connection {
         description "Name of the control connection";
         default "all";
         type string;
       }
     }
     output {
       choice output_c {
         case output-tag {
           leaf output {
             type string;
           }
         }
         case multichassis-tag {
           anyxml multi-routing-engine-results;
         }
       }
     }
   }
   rpc request-services-flow-collector-test-file-transfer {
     description "Transfer a test file to the current primary server";
     input {
       leaf filename {
         description "Specify the filename to use";
         type string;
         mandatory true;
       }
       leaf channel {
         description "File transfer channel to use";
         type enumeration {
           enum "channel-zero" {
             description "Channel 0";
           }
           enum "channel-one" {
             description "Channel 1";
           }
         }
       }
       leaf destination-type {
         type enumeration {
           enum "primary" {
             description "Primary server";
           }
           enum "secondary" {
             description "Secondary server";
           }
         }
       }
       leaf interface {
         description "Interface name";
         type string;
         mandatory true;
       }
     }
     output {
       choice output_c {
         case output-tag {
           leaf output {
             type string;
           }
         }
         case actual-tag {
           anyxml flow-collector-test-file-transfer-response;
         }
         case multichassis-tag {
           anyxml multi-routing-engine-results;
         }
       }
     }
   }
   rpc request-services-flow-collector-destination {
     description "Change to Destination server";
     input {
       leaf destination-type {
         description "Destination server";
         type enumeration {
           enum "primary" {
             description "Primary server";
           }
           enum "secondary" {
             description "Secondary server";
           }
         }
         mandatory true;
       }
       leaf interface {
         description "Physical interface";
         type union {
           type jt:interface-device;
           type string {
             pattern "<.*>|$.*";
           }
         }
         mandatory true;
       }
       leaf clear-files {
         description "Remove existing files";
         type empty;
       }
       leaf clear-logs {
         description "Remove existing logs";
         type empty;
       }
       leaf how-to-switch {
         description "Options when switching destination";
         default "gracefully";
         type enumeration {
           enum "gracefully" {
             description "Retain existing FTP connections";
           }
           enum "immediately" {
             description "Terminate existing FTP connections";
           }
         }
       }
     }
     output {
       choice output_c {
         case output-tag {
           leaf output {
             type string;
           }
         }
         case actual-tag {
           anyxml flow-collector-destination-response;
         }
         case multichassis-tag {
           anyxml multi-routing-engine-results;
         }
       }
     }
   }
   rpc request-extensible-subscriber-services-reload-dictionary {
     description "Reload dictionary";
     output {
       choice output_c {
         case output-tag {
           leaf output {
             type string;
           }
         }
         case actual-tag {
           anyxml extensible-subscriber-services-information;
         }
         case multichassis-tag {
           anyxml multi-routing-engine-results;
         }
       }
     }
   }
   rpc request-appid-protocol-bundle-load {
     description "Load a QM protocols bundle dynamically";
     input {
       uses command-forwarding;
       leaf proto_bundle {
         description "Protocol Bundle file name";
         type string;
       }
     }
     output {
       choice output_c {
         case output-tag {
           leaf output {
             type string;
           }
         }
         case actual-tag {
           anyxml request-appid-protocol-bundle-load;
         }
         case multichassis-tag {
           anyxml multi-routing-engine-results;
         }
       }
     }
   }
   rpc request-appid-protocol-bundle-unload {
     description "UnLoad a QM protocols bundle dynamically";
     input {
       uses command-forwarding;
       leaf proto_bundle {
         description "Protocol Bundle file name";
         type string;
       }
     }
     output {
       choice output_c {
         case output-tag {
           leaf output {
             type string;
           }
         }
         case actual-tag {
           anyxml request-appid-protocol-bundle-unload;
         }
         case multichassis-tag {
           anyxml multi-routing-engine-results;
         }
       }
     }
   }
   rpc request-appid-application-package-download {
     description "Download application package";
     output {
       choice output_c {
         case output-tag {
           leaf output {
             type string;
           }
         }
         case actual-tag {
           anyxml appid-download-status;
         }
         case multichassis-tag {
           anyxml multi-routing-engine-results;
         }
       }
     }
   }
   rpc request-appid-application-package-download-version {
     description "Version of application package to download";
     input {
       leaf version-value {
         description "Version number (1 - 65535)";
         type union {
           type string {
             pattern "<.*>|$.*";
           }
           type uint16 {
             range "1 .. 65535";
           }
         }
         mandatory true;
       }
     }
     output {
       choice output_c {
         case output-tag {
           leaf output {
             type string;
           }
         }
         case actual-tag {
           anyxml appid-download-status;
         }
         case multichassis-tag {
           anyxml multi-routing-engine-results;
         }
       }
     }
   }
   rpc request-appid-application-package-download-status {
     description "Display download status";
     output {
       choice output_c {
         case output-tag {
           leaf output {
             type string;
           }
         }
         case actual-tag {
           anyxml appid-download-status;
         }
         case multichassis-tag {
           anyxml multi-routing-engine-results;
         }
       }
     }
   }
   rpc request-appid-application-package-download-check-server {
     description "Retrieve version information for latest package on server";
     output {
       choice output_c {
         case output-tag {
           leaf output {
             type string;
           }
         }
         case actual-tag {
           anyxml appid-check-server;
         }
         case multichassis-tag {
           anyxml multi-routing-engine-results;
         }
       }
     }
   }
   rpc request-appid-application-package-install {
     description "Install application package";
     output {
       choice output_c {
         case output-tag {
           leaf output {
             type string;
           }
         }
         case actual-tag {
           anyxml appid-install-status;
         }
         case multichassis-tag {
           anyxml multi-routing-engine-results;
         }
       }
     }
   }
   rpc request-appid-application-package-install-status {
     description "Display install status";
     output {
       choice output_c {
         case output-tag {
           leaf output {
             type string;
           }
         }
         case actual-tag {
           anyxml appid-install-status;
         }
         case multichassis-tag {
           anyxml multi-routing-engine-results;
         }
       }
     }
   }
   rpc request-appid-application-package-uninstall {
     description "Uninstall predefined application package";
     output {
       choice output_c {
         case output-tag {
           leaf output {
             type string;
           }
         }
         case actual-tag {
           anyxml appid-apppack-uinstall;
         }
         case multichassis-tag {
           anyxml multi-routing-engine-results;
         }
       }
     }
   }
   rpc request-appid-application-package-uninstall-status {
     description "Display uninstall status";
     output {
       choice output_c {
         case output-tag {
           leaf output {
             type string;
           }
         }
         case actual-tag {
           anyxml appid-uninstall-status;
         }
         case multichassis-tag {
           anyxml multi-routing-engine-results;
         }
       }
     }
   }
   rpc request-appid-application-predefined-disable {
     description "Disable a predefined application";
     input {
       uses command-forwarding;
       leaf application-name {
         description "Predefined application name";
         type string;
         mandatory true;
       }
       leaf no-commit {
         description "Do not re-compile signatures";
         status deprecated;
         type empty;
       }
     }
     output {
       choice output_c {
         case output-tag {
           leaf output {
             type string;
           }
         }
         case actual-tag {
           anyxml appid-application-predefined-disable;
         }
         case multichassis-tag {
           anyxml multi-routing-engine-results;
         }
       }
     }
   }
   rpc request-appid-application-predefined-enable {
     description "Enable a predefined application";
     input {
       uses command-forwarding;
       leaf application-name {
         description "Predefined application name";
         type string;
         mandatory true;
       }
       leaf no-commit {
         description "Do not re-compile signatures";
         status deprecated;
         type empty;
       }
     }
     output {
       choice output_c {
         case output-tag {
           leaf output {
             type string;
           }
         }
         case actual-tag {
           anyxml appid-application-predefined-enable;
         }
         case multichassis-tag {
           anyxml multi-routing-engine-results;
         }
       }
     }
   }
   rpc request-appid-application-predefined-group-copy {
     description "Copy a predefined application group into junos configuration";
     input {
       uses command-forwarding;
       leaf group-name {
         description "Predefined application group name";
         type string;
         mandatory true;
       }
     }
     output {
       choice output_c {
         case output-tag {
           leaf output {
             type string;
           }
         }
         case actual-tag {
           anyxml appid-application-predefined-group-copy;
         }
         case multichassis-tag {
           anyxml multi-routing-engine-results;
         }
       }
     }
   }
   rpc request-appid-application-predefined-group-disable {
     description "Disable a predefined application group";
     input {
       uses command-forwarding;
       leaf group-name {
         description "Predefined application group name";
         type string;
         mandatory true;
       }
     }
     output {
       choice output_c {
         case output-tag {
           leaf output {
             type string;
           }
         }
         case actual-tag {
           anyxml appid-application-predefined-group-disable;
         }
         case multichassis-tag {
           anyxml multi-routing-engine-results;
         }
       }
     }
   }
   rpc request-appid-application-predefined-group-enable {
     description "Enable a predefined application group";
     input {
       uses command-forwarding;
       leaf group-name {
         description "Predefined application group name";
         type string;
         mandatory true;
       }
     }
     output {
       choice output_c {
         case output-tag {
           leaf output {
             type string;
           }
         }
         case actual-tag {
           anyxml appid-application-predefined-group-enable;
         }
         case multichassis-tag {
           anyxml multi-routing-engine-results;
         }
       }
     }
   }
   rpc rdm-reload-dictionary {
     description "Reload dictionary";
     input {
       leaf dictionary-path {
         description "Complete path with dictionary name";
         type jt:filename;
         mandatory true;
       }
     }
     output {
       choice output_c {
         case output-tag {
           leaf output {
             type string;
           }
         }
         case actual-tag {
           anyxml rdm-information;
         }
         case multichassis-tag {
           anyxml multi-routing-engine-results;
         }
       }
     }
   }
   rpc rdm-sd-reconfigure {
     description "Reconfigure service device";
     input {
       leaf service-device-name {
         description "Service device name";
         type string;
         mandatory true;
       }
     }
     output {
       choice output_c {
         case output-tag {
           leaf output {
             type string;
           }
         }
         case actual-tag {
           anyxml rdm-information;
         }
         case multichassis-tag {
           anyxml multi-routing-engine-results;
         }
       }
     }
   }
   rpc request-netconf-trace {
     description "NETCONF tracing";
     input {
       leaf on-demand {
         description "Control on-demand tracing";
         type enumeration {
           enum "start" {
             description "Start NETCONF tracing";
           }
           enum "stop" {
             description "Stop NETCONF tracing";
           }
         }
         mandatory true;
       }
     }
     output {
       choice output_c {
         case output-tag {
           leaf output {
             type string;
           }
         }
         case multichassis-tag {
           anyxml multi-routing-engine-results;
         }
       }
     }
   }
   rpc request-service-capture-snapshot {
     description "Request a snapshot of the current packet capture";
     input {
       leaf interface {
         description "Name of adaptive services interface";
         type string;
         mandatory true;
       }
       leaf file {
         type string;
         mandatory true;
       }
     }
     output {
       choice output_c {
         case output-tag {
           leaf output {
             type string;
           }
         }
         case actual-tag {
           anyxml service-service-capture-snapshot;
         }
         case multichassis-tag {
           anyxml multi-routing-engine-results;
         }
       }
     }
   }
   rpc request-service-capture-clear {
     description "Clear the current packet capture";
     input {
       leaf interface {
         description "Name of adaptive services interface";
         type string;
         mandatory true;
       }
     }
     output {
       choice output_c {
         case output-tag {
           leaf output {
             type string;
           }
         }
         case actual-tag {
           anyxml service-service-capture-clear;
         }
         case multichassis-tag {
           anyxml multi-routing-engine-results;
         }
       }
     }
   }
   rpc request-services-redundancy-set {
     description "Request services redundancy-set";
     input {
       leaf id {
         description "Set id";
         type union {
           type uint32;
           type string {
             pattern "<.*>|$.*";
           }
         }
         mandatory true;
       }
       leaf trigger {
         description "Trigger a redundancy-event";
         type empty;
         mandatory true;
       }
       leaf redundancy-event {
         description "Redundancy event which needs to be triggered";
         type string;
         mandatory true;
       }
       leaf force {
         description "Trigger event forcefully overriding warnings";
         type empty;
       }
     }
     output {
       choice output_c {
         case output-tag {
           leaf output {
             type string;
           }
         }
         case actual-tag {
           anyxml services-redundancy-set-request;
         }
         case multichassis-tag {
           anyxml multi-routing-engine-results;
         }
       }
     }
   }
   rpc request-traffic-loadbalance-real-service-rejoin {
     description "Rejoin for load-balance request";
     input {
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
     }
     output {
       choice output_c {
         case output-tag {
           leaf output {
             type string;
           }
         }
         case multichassis-tag {
           anyxml multi-routing-engine-results;
         }
       }
     }
   }
   rpc request-url-filter-force-dns-resolution-all {
     description "All profiles";
     output {
       choice output_c {
         case output-tag {
           leaf output {
             type string;
           }
         }
         case actual-tag {
           anyxml force-dns-options;
         }
         case multichassis-tag {
           anyxml multi-routing-engine-results;
         }
       }
     }
   }
   rpc request-url-filter-force-dns-resolution-profile {
     description "Profile name";
     input {
       leaf profile-name {
         description "Profile name";
         type string;
         mandatory true;
       }
       leaf url-filter-template {
         description "Template name";
         type string;
       }
     }
     output {
       choice output_c {
         case output-tag {
           leaf output {
             type string;
           }
         }
         case actual-tag {
           anyxml force-dns-options;
         }
         case multichassis-tag {
           anyxml multi-routing-engine-results;
         }
       }
     }
   }
   rpc request-url-filter-database-update {
     description "Update the specific url-filter-database";
     input {
       leaf file {
         description "URL filter database file";
         type string;
         mandatory true;
       }
     }
     output {
       choice output_c {
         case output-tag {
           leaf output {
             type string;
           }
         }
         case actual-tag {
           anyxml update-db-filepath;
         }
         case multichassis-tag {
           anyxml multi-routing-engine-results;
         }
       }
     }
   }
   rpc request-dns-filter-database-update {
     description "Update the specific dns-filter-database";
     input {
       leaf file {
         description "DNS filter database file";
         type string;
         mandatory true;
       }
     }
     output {
       choice output_c {
         case output-tag {
           leaf output {
             type string;
           }
         }
         case actual-tag {
           anyxml update-db-filepath;
         }
         case multichassis-tag {
           anyxml multi-routing-engine-results;
         }
       }
     }
   }
   rpc request-url-filter-validate {
     description "Validate the web-filter database";
     input {
       choice file {
         case all {
           leaf all {
             description "Validate the url-filter database for all profiles";
             type empty;
           }
         }
         case url-filter-file-name {
           leaf url-filter-file-name {
             description "URL filter database file";
             type string;
           }
         }
         case dns-filter-file-name {
           leaf dns-filter-file-name {
             description "DNS filter database file";
             type string;
           }
         }
       }
       leaf hash-method {
         description "Hash method";
         type enumeration {
           enum "hmac-md5-96" {
             description "HMAC-MD5-96 algorithm";
           }
           enum "hmac-sha1-96" {
             description "HMAC-SHA1-96 algorithm";
           }
           enum "hmac-sha2-256" {
             description "HMAC-SHA2-256 algorithm";
           }
           enum "hmac-sha-256-128" {
             description "HMAC-SHA-256-128 algorithm";
           }
         }
       }
       leaf hash-key {
         description "Hash key";
         type string;
       }
     }
     output {
       choice output_c {
         case output-tag {
           leaf output {
             type string;
           }
         }
         case actual-tag {
           anyxml validate-db-options;
         }
         case multichassis-tag {
           anyxml multi-routing-engine-results;
         }
       }
     }
   }
   rpc request-services-url-filter-delete-gencfg-data {
     description "Gencfg data";
     output {
       choice output_c {
         case output-tag {
           leaf output {
             type string;
           }
         }
         case actual-tag {
           anyxml request-delete-gencfg;
         }
         case multichassis-tag {
           anyxml multi-routing-engine-results;
         }
       }
     }
   }
   rpc request-lacp-link-protection-switchover {
     description "Request LACP link protection switchover";
     input {
       leaf interface-name {
         description "Name of AE interface";
         type union {
           type jt:interface-wildcard;
           type string {
             pattern "<.*>|$.*";
           }
         }
         mandatory true;
       }
     }
     output {
       choice output_c {
         case output-tag {
           leaf output {
             type string;
           }
         }
         case actual-tag {
           anyxml lacp-link-switchover;
         }
         case multichassis-tag {
           anyxml multi-routing-engine-results;
         }
       }
     }
   }
   rpc request-message {
     description "Send text message to other users";
     input {
       leaf user {
         description "Name of user (account@terminal) to receive message";
         type string;
         mandatory true;
       }
       leaf terminal {
         description "Device name of target terminal (/dev/ttyXX)";
         type string;
       }
       leaf message {
         description "Text of message";
         type string;
       }
     }
     output {
       choice output_c {
         case output-tag {
           leaf output {
             type string;
           }
         }
         case multichassis-tag {
           anyxml multi-routing-engine-results;
         }
       }
     }
   }
   rpc request-message-all {
     description "Send message to all logged-in users";
     input {
       leaf message {
         description "Text of message";
         type string;
       }
     }
     output {
       choice output_c {
         case output-tag {
           leaf output {
             type string;
           }
         }
         case multichassis-tag {
           anyxml multi-routing-engine-results;
         }
       }
     }
   }
   rpc request-compute-node-cleanup-log {
     description "Compute node cleanup /var/tmp and /var/log";
     input {
       uses command-forwarding;
       leaf compute-cluster {
         description "Compute cluster name";
         type string {
           length "1 .. 15";
         }
       }
       leaf compute-node {
         description "Compute node name";
         type string {
           length "1 .. 15";
         }
       }
     }
     output {
       choice output_c {
         case output-tag {
           leaf output {
             type string;
           }
         }
         case multichassis-tag {
           anyxml multi-routing-engine-results;
         }
       }
     }
   }
   rpc request-compute-node-file-copy {
     description "Copy file from host to vjunos";
     input {
       leaf host-path {
         description "Copy files related to";
         type enumeration {
           enum "crash" {
             description "Files in /var/crash";
           }
           enum "log" {
             description "Files in /var/log";
           }
         }
         mandatory true;
       }
       leaf from-jhost {
         description "Host file name";
         type string {
           junos:posix-pattern "!(^/|\\.\\./)";
           junos:pattern-message "Must not be absolute path or contain relative components";
         }
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-vmhost-poweroff {
     description "Power off the software on RE";
     input {
       leaf other-routing-engine {
         description "Power off other Routing Engine";
         type empty;
       }
     }
     output {
       choice output_c {
         case output-tag {
           leaf output {
             type string;
           }
         }
         case multichassis-tag {
           anyxml multi-routing-engine-results;
         }
       }
     }
   }
   rpc request-vmhost-halt {
     description "Halt the software on RE";
     output {
       choice output_c {
         case output-tag {
           leaf output {
             type string;
           }
         }
         case multichassis-tag {
           anyxml multi-routing-engine-results;
         }
       }
     }
   }
   rpc request-vmhost-power-on-other-re {
     description "Power on the system";
     input {
       leaf other-routing-engine {
         description "Power on other Routing Engine";
         type empty;
         mandatory true;
       }
     }
     output {
       choice output_c {
         case output-tag {
           leaf output {
             type string;
           }
         }
         case multichassis-tag {
           anyxml multi-routing-engine-results;
         }
       }
     }
   }
   rpc request-vmhost-reboot {
     description "Reboot RE vmhost";
     input {
       uses command-forwarding;
       leaf media {
         type enumeration {
           enum "disk1" {
             description "Boot off disk1(primary) device";
           }
           enum "disk2" {
             description "Boot off disk2(backup) device";
           }
           enum "network" {
             description "Network boot via PXE";
           }
           enum "usb" {
             description "Boot off USB device";
           }
         }
       }
       leaf in {
         description "Number of minutes to delay before reboot operation";
         type union {
           type string {
             pattern "<.*>|$.*";
           }
           type uint32 {
             range "0 .. 100";
           }
         }
       }
     }
     output {
       choice output_c {
         case output-tag {
           leaf output {
             type string;
           }
         }
         case multichassis-tag {
           anyxml multi-routing-engine-results;
         }
       }
     }
   }
   rpc request-vmhost-file-cleanup {
     description "RE vmhost cleanup /var/tmp, /var/crash and /var/log";
     output {
       choice output_c {
         case output-tag {
           leaf output {
             type string;
           }
         }
         case multichassis-tag {
           anyxml multi-routing-engine-results;
         }
       }
     }
   }
   rpc request-vmhost-file-copy {
     description "Copy file from vmhost to vjunos";
     input {
       leaf node-path {
         description "Copy files related to";
         type enumeration {
           enum "crash" {
             description "Files in /var/crash";
           }
           enum "log" {
             description "Files in /var/log";
           }
         }
         mandatory true;
       }
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-copy-vjunos-to-jnode {
     description "Copy file from vjunos to vmhost";
     input {
       leaf from-vjunos {
         description "Junos file name";
         type string;
         mandatory true;
       }
       leaf to-jnode {
         description "Host file name";
         type string;
         mandatory true;
       }
     }
     output {
       choice output_c {
         case output-tag {
           leaf output {
             type string;
           }
         }
         case multichassis-tag {
           anyxml multi-routing-engine-results;
         }
       }
     }
   }
   rpc request-copy-jnode-to-vjunos {
     description "Copy file from vmhost to vjunos";
     input {
       leaf from-jnode {
         description "Host file name";
         type string;
         mandatory true;
       }
       leaf to-vjunos {
         description "Junos file name";
         type string;
         mandatory true;
       }
     }
     output {
       choice output_c {
         case output-tag {
           leaf output {
             type string;
           }
         }
         case multichassis-tag {
           anyxml multi-routing-engine-results;
         }
       }
     }
   }
   rpc request-vmhost-package-add {
     description "Add extension or upgrade package";
     input {
       choice package-options {
         case set {
           leaf-list set {
             ordered-by user;
             description "List of URLs or pathnames corresponding to packages";
             type jt:filename;
           }
         }
         case package-name {
           leaf package-name {
             description "URL or pathname of package";
             type jt:filename;
           }
         }
       }
       leaf reboot {
         description "Reboot RE vmhost after adding package";
         type empty;
       }
       leaf in {
         description "Number of minutes to delay before reboot operation";
         type union {
           type string {
             pattern "<.*>|$.*";
           }
           type uint32 {
             range "0 .. 100";
           }
         }
       }
       choice re-choice {
         case re0 {
           leaf re0 {
             description "Install package on RE0";
             type empty;
           }
         }
         case re1 {
           leaf re1 {
             description "Install package on RE1";
             type empty;
           }
         }
       }
       choice validate_choice {
         case no-validate {
           leaf no-validate {
             description "Don't check compatibility with current configuration";
             type empty;
           }
         }
       }
       choice chassis {
         case dont-forward {
           leaf dont-forward {
             type empty;
           }
         }
       }
       leaf issu-internal {
         description "Internally executed by mgd, to allow software adds during issu";
         type empty;
       }
       leaf upgrade-to-model {
         description "Name of the model to upgrade to";
         type string;
       }
       leaf unlink {
         description "Remove the package after successful installation";
         type empty;
       }
     }
     output {
       choice output_c {
         case output-tag {
           leaf output {
             type string;
           }
         }
         case multichassis-tag {
           anyxml multi-routing-engine-results;
         }
       }
     }
   }
   rpc request-vmhost-package-delete {
     description "Remove extension or upgrade package";
     input {
       leaf force {
         description "Force removal of package (ignore warnings)";
         type empty;
       }
       choice package-options {
         case set {
           leaf-list set {
             ordered-by user;
             description "List of package name";
             type string;
           }
         }
         case package-name {
           leaf package-name {
             description "Name of package";
             type string;
           }
         }
         case upgrade-group {
           leaf upgrade-group {
             description "Satellite upgrade group name";
             type string;
           }
         }
         case version {
           leaf version {
             description "Version of satellite package";
             type string;
           }
         }
       }
       leaf reboot {
         description "Reboot system after package delete";
         type empty;
       }
     }
     output {
       choice output_c {
         case output-tag {
           leaf output {
             type string;
           }
         }
         case multichassis-tag {
           anyxml multi-routing-engine-results;
         }
       }
     }
   }
   rpc abort-vmhost-in-service-upgrade {
     description "Abort in-service software upgrade";
     output {
       choice output_c {
         case output-tag {
           leaf output {
             type string;
           }
         }
         case multichassis-tag {
           anyxml multi-routing-engine-results;
         }
       }
     }
   }
   rpc request-vmhost-package-in-service-upgrade {
     description "In-service software upgrade";
     input {
       leaf package-name {
         description "URL or pathname of package";
         type jt:filename;
         mandatory true;
       }
       leaf no-old-master-upgrade {
         description "Don't upgrade the old master after switchover";
         type empty;
       }
       leaf verbose {
         description "Enable detailed output";
         type empty;
       }
       leaf reboot {
         description "Reboot RE vmhost after adding package";
         type empty;
       }
     }
     output {
       choice output_c {
         case output-tag {
           leaf output {
             type string;
           }
         }
         case multichassis-tag {
           anyxml multi-routing-engine-results;
         }
       }
     }
   }
   rpc request-vmhost-package-validate {
     description "Verify package compatibility with current configuration";
     input {
       choice package-options {
         case package-name {
           leaf package-name {
             description "URL or pathname of package";
             type jt:filename;
           }
         }
       }
       choice chassis {
         case member {
           leaf member {
             description "Validate package on member";
             type union {
               type string {
                 pattern "<.*>|$.*";
               }
               type uint32;
             }
           }
         }
         case dont-forward {
           leaf dont-forward {
             type empty;
           }
         }
       }
     }
     output {
       choice output_c {
         case output-tag {
           leaf output {
             type string;
           }
         }
         case multichassis-tag {
           anyxml multi-routing-engine-results;
         }
       }
     }
   }
   rpc request-vmhost-package-rollback {
     description "Attempt to roll back to previous set of packages";
     input {
       uses command-forwarding;
       leaf reboot {
         description "Reboot system after rollback";
         type empty;
       }
     }
     output {
       choice output_c {
         case output-tag {
           leaf output {
             type string;
           }
         }
         case actual-tag {
           anyxml rollback-information;
         }
         case multichassis-tag {
           anyxml multi-routing-engine-results;
         }
       }
     }
   }
   rpc request-vmhost-jdm-package-add {
     description "Install fresh JDM package or upgrade package";
     input {
       leaf package-name {
         description "JDM package name";
         type jt:filename;
         mandatory true;
       }
       leaf force {
         description "Force package add";
         type empty;
       }
     }
     output {
       choice output_c {
         case output-tag {
           leaf output {
             type string;
           }
         }
         case multichassis-tag {
           anyxml multi-routing-engine-results;
         }
       }
     }
   }
   rpc request-vmhost-jdm-package-delete {
     description "Remove currently installed JDM package";
     output {
       choice output_c {
         case output-tag {
           leaf output {
             type string;
           }
         }
         case multichassis-tag {
           anyxml multi-routing-engine-results;
         }
       }
     }
   }
   rpc request-package-vmhost-jdm-start {
     description "Start the JDM";
     output {
       choice output_c {
         case output-tag {
           leaf output {
             type string;
           }
         }
         case multichassis-tag {
           anyxml multi-routing-engine-results;
         }
       }
     }
   }
   rpc request-package-vmhost-jdm-stop {
     description "Stop the JDM";
     output {
       choice output_c {
         case output-tag {
           leaf output {
             type string;
           }
         }
         case multichassis-tag {
           anyxml multi-routing-engine-results;
         }
       }
     }
   }
   rpc request-vmhost-jdm-login {
     description "Login to JDM";
     output {
       choice output_c {
         case output-tag {
           leaf output {
             type string;
           }
         }
         case multichassis-tag {
           anyxml multi-routing-engine-results;
         }
       }
     }
   }
   rpc request-vmhost-snapshot {
     description "Create a vmhost recovery snapshot";
     output {
       choice output_c {
         case output-tag {
           leaf output {
             type string;
           }
         }
         case actual-tag {
           anyxml vmhost-snapshot-information;
         }
         case multichassis-tag {
           anyxml multi-routing-engine-results;
         }
       }
     }
   }
   rpc request-vmhost-snapshot-partition {
     description "Partition the target media";
     output {
       choice output_c {
         case output-tag {
           leaf output {
             type string;
           }
         }
         case actual-tag {
           anyxml vmhost-snapshot-partition-information;
         }
         case multichassis-tag {
           anyxml multi-routing-engine-results;
         }
       }
     }
   }
   rpc request-vmhost-snapshot-recovery {
     description "Recover the primary media from snapshot";
     output {
       choice output_c {
         case output-tag {
           leaf output {
             type string;
           }
         }
         case actual-tag {
           anyxml vmhost-snapshot-recovery-information;
         }
         case multichassis-tag {
           anyxml multi-routing-engine-results;
         }
       }
     }
   }
   rpc request-vmhost-snapshot-recovery-partition {
     description "Partition the media before snapshot";
     output {
       choice output_c {
         case output-tag {
           leaf output {
             type string;
           }
         }
         case actual-tag {
           anyxml vmhost-snapshot-recovery-partition-information;
         }
         case multichassis-tag {
           anyxml multi-routing-engine-results;
         }
       }
     }
   }
   rpc request-vmhost-zeroize {
     description "Erase all data, including configuration and log files";
     output {
       choice output_c {
         case output-tag {
           leaf output {
             type string;
           }
         }
         case actual-tag {
           anyxml vmhost-zeroize-information;
         }
         case multichassis-tag {
           anyxml multi-routing-engine-results;
         }
       }
     }
   }
   rpc request-vmhost-hard-disk-test {
     description "Run smartd self tests on hard disks";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       choice output_c {
         case output-tag {
           leaf output {
             type string;
           }
         }
         case actual-tag {
           anyxml raid-information;
         }
         case multichassis-tag {
           anyxml multi-routing-engine-results;
         }
       }
     }
   }
   rpc request-snmp-spoof-trap {
     description "Generate artificial SNMP notification";
     input {
       leaf trap {
         description "The name of the trap to spoof";
         type string;
         mandatory true;
       }
       leaf variable-bindings {
         description "The list of variables & values to include in the trap";
         type string;
       }
     }
     output {
       choice output_c {
         case output-tag {
           leaf output {
             type string;
           }
         }
         case actual-tag {
           anyxml snmp-spoof-trap-results;
         }
         case multichassis-tag {
           anyxml multi-routing-engine-results;
         }
       }
     }
   }
   rpc request-snmp-utility-mib-set {
     description "Set values in utility mib objects";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
       leaf object-value {
         type string;
         mandatory true;
       }
     }
     output {
       choice output_c {
         case output-tag {
           leaf output {
             type string;
           }
         }
         case actual-tag {
           anyxml snmp-utility-mib-results;
         }
         case multichassis-tag {
           anyxml multi-routing-engine-results;
         }
       }
     }
   }
   rpc request-snmp-utility-mib-clear {
     description "Clear values in utility mib objects";
     input {
       leaf object-type {
         type enumeration {
           enum "counter" {
             description "Set counter value";
           }
           enum "counter64" {
             description "Set 64 bit counter value";
           }
           enum "integer" {
             description "Set signed integer value";
           }
           enum "unsigned-integer" {
             description "Set unsigned integer value";
           }
           enum "string" {
             description "Set string value";
           }
         }
         mandatory true;
       }
       leaf instance {
         type string {
           length "1 .. 80";
         }
         mandatory true;
       }
     }
     output {
       choice output_c {
         case output-tag {
           leaf output {
             type string;
           }
         }
         case actual-tag {
           anyxml snmp-utility-mib-results;
         }
         case multichassis-tag {
           anyxml multi-routing-engine-results;
         }
       }
     }
   }
   rpc request-ancp-oam-information {
     description "Request ANCP operation, administration, and management";
     output {
       choice output_c {
         case output-tag {
           leaf output {
             type string;
           }
         }
         case actual-tag {
           anyxml ancp-oam-information;
         }
         case multichassis-tag {
           anyxml multi-routing-engine-results;
         }
       }
     }
   }
   rpc request-ancp-oam-neighbor-information {
     description "Neighbor identifier";
     input {
       choice neighbor-opts {
         case system-name {
           leaf system-name {
             description "MAC address of the neighbor";
             type string;
           }
         }
         case ip-address {
           leaf ip-address {
             description "IP address of the neighbor";
             type jt:ipaddr;
           }
         }
       }
       leaf subscriber {
         description "Subscriber identifier";
         type string;
         mandatory true;
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
     output {
       choice output_c {
         case output-tag {
           leaf output {
             type string;
           }
         }
         case actual-tag {
           anyxml ancp-oam-information;
         }
         case multichassis-tag {
           anyxml multi-routing-engine-results;
         }
       }
     }
   }
   rpc request-ancp-oam-interface-information {
     description "ANCP interface specific options";
     input {
       choice interface-opts {
         case interface-name {
           leaf interface-name {
             description "Name of ANCP interface";
             type string;
           }
         }
         case interface-set {
           leaf interface-set {
             description "Name of ANCP interface set";
             type string {
               junos:posix-pattern "^.{1,64}$";
               junos:pattern-message "Must be string of 64 characters or less";
             }
           }
         }
       }
       leaf count {
         description "Number of local loopback messages";
         default "1";
         type union {
           type string {
             pattern "<.*>|$.*";
           }
           type uint16 {
             range "1 .. 32";
           }
         }
       }
       leaf timeout {
         description "Timeout for loopback response from the neighbor";
         default "30";
         units "seconds";
         type union {
           type string {
             pattern "<.*>|$.*";
           }
           type uint32 {
             range "1 .. 255";
           }
         }
       }
     }
     output {
       choice output_c {
         case output-tag {
           leaf output {
             type string;
           }
         }
         case actual-tag {
           anyxml ancp-oam-information;
         }
         case multichassis-tag {
           anyxml multi-routing-engine-results;
         }
       }
     }
   }
   rpc request-ancp-oam-port-up {
     description "ANCP port-up processing";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
         mandatory true;
       }
       leaf remote-id {
         description "Access loop remote id";
         type string {
           junos:posix-pattern "^.{1,63}$";
           junos:pattern-message "Must be a string of 63 characters or less";
         }
         mandatory true;
       }
       leaf outer-vlan-id {
         description "Access aggregation circuit id binary";
         type union {
           type string {
             pattern "<.*>|$.*";
           }
           type uint16 {
             range "1 .. 4094";
           }
         }
         mandatory true;
       }
     }
     output {
       choice output_c {
         case output-tag {
           leaf output {
             type string;
           }
         }
         case actual-tag {
           anyxml ancp-oam-port-up;
         }
         case multichassis-tag {
           anyxml multi-routing-engine-results;
         }
       }
     }
   }
   rpc request-ancp-oam-port-down {
     description "ANCP port-down processing";
     input {
       choice interface-opts {
         case neighbor {
           leaf neighbor {
             description "IP address of the neighbor";
             type jt:ipaddr;
           }
         }
         case subscriber-interface {
           leaf subscriber-interface {
             description "Subscriber-facing interface";
             type string;
           }
         }
       }
       leaf circuit-id {
         description "Access loop circuit id";
         type string {
           junos:posix-pattern "^.{1,63}$";
           junos:pattern-message "Must be a string of 63 characters or less";
         }
       }
       leaf remote-id {
         description "Access loop remote id";
         type string {
           junos:posix-pattern "^.{1,63}$";
           junos:pattern-message "Must be a string of 63 characters or less";
         }
       }
       leaf outer-vlan-id {
         description "Access aggregation circuit id binary";
         type union {
           type string {
             pattern "<.*>|$.*";
           }
           type uint16 {
             range "1 .. 4094";
           }
         }
       }
     }
     output {
       choice output_c {
         case output-tag {
           leaf output {
             type string;
           }
         }
         case actual-tag {
           anyxml ancp-oam-port-down;
         }
         case multichassis-tag {
           anyxml multi-routing-engine-results;
         }
       }
     }
   }
   rpc aaa-subscriber-add-service {
     description "Service activation";
     input {
       leaf session-id {
         description "Session id";
         type union {
           type string {
             pattern "<.*>|$.*";
           }
           type uint64 {
             range "1 .. 18446744073709551615";
           }
         }
         mandatory true;
       }
       leaf service-profile {
         description "Name of service-profile";
         type string;
         mandatory true;
       }
     }
     output {
       choice output_c {
         case output-tag {
           leaf output {
             type string;
           }
         }
         case actual-tag {
           anyxml aaa-subscriber-add-service-results;
         }
         case multichassis-tag {
           anyxml multi-routing-engine-results;
         }
       }
     }
   }
   rpc aaa-subscriber-delete-service {
     description "Service deactivation";
     input {
       leaf session-id {
         description "Session id";
         type union {
           type string {
             pattern "<.*>|$.*";
           }
           type uint64 {
             range "1 .. 18446744073709551615";
           }
         }
         mandatory true;
       }
       leaf service-profile {
         description "Name of dynamic-profile";
         type string;
         mandatory true;
       }
     }
     output {
       choice output_c {
         case output-tag {
           leaf output {
             type string;
           }
         }
         case actual-tag {
           anyxml aaa-subscriber-delete-service-results;
         }
         case multichassis-tag {
           anyxml multi-routing-engine-results;
         }
       }
     }
   }
   rpc aaa-subscriber-modify-variable {
     description "Modify dynamic variable";
     input {
       leaf session-id {
         description "Session id";
         type union {
           type string {
             pattern "<.*>|$.*";
           }
           type uint64 {
             range "1 .. 18446744073709551615";
           }
         }
         mandatory true;
       }
       leaf junos-cos-traffic-control-profile {
         description "Modify $junos-cos-traffic-control-profile variable";
         type string;
       }
     }
     output {
       choice output_c {
         case output-tag {
           leaf output {
             type string;
           }
         }
         case actual-tag {
           anyxml aaa-subscriber-modify-variable-results;
         }
         case multichassis-tag {
           anyxml multi-routing-engine-results;
         }
       }
     }
   }
   rpc aaa-subscriber-set-parameters {
     description "Set AAA subscriber parameters";
     input {
       leaf session-id {
         description "Session id";
         type union {
           type string {
             pattern "<.*>|$.*";
           }
           type uint64 {
             range "1 .. 18446744073709551615";
           }
         }
         mandatory true;
       }
       leaf provisioning-state {
         description "Provisioning state";
         type enumeration {
           enum "none" {
             description "Set provisioning to none";
           }
         }
         mandatory true;
       }
     }
     output {
       choice output_c {
         case output-tag {
           leaf output {
             type string;
           }
         }
         case actual-tag {
           anyxml aaa-subscriber-set-parameters-results;
         }
         case multichassis-tag {
           anyxml multi-routing-engine-results;
         }
       }
     }
   }
   rpc replay-pending-accounting-stops {
     description "Replay pending acct stops to radius";
     output {
       choice output_c {
         case output-tag {
           leaf output {
             type string;
           }
         }
         case actual-tag {
           anyxml replay-pending-accounting-results;
         }
         case multichassis-tag {
           anyxml multi-routing-engine-results;
         }
       }
     }
   }
   rpc request-accounting-action {
     description "Accounting suspend or baseline";
     input {
       choice accounting_action {
         case suspend {
           leaf suspend {
             description "Suspend accounting";
             type empty;
           }
         }
         case baseline {
           leaf baseline {
             description "Baseline statistics";
             type empty;
           }
         }
         case resume {
           leaf resume {
             description "Resume accounting";
             type empty;
           }
         }
       }
     }
     output {
       choice output_c {
         case output-tag {
           leaf output {
             type string;
           }
         }
         case multichassis-tag {
           anyxml multi-routing-engine-results;
         }
       }
     }
   }
   rpc request-auto-configuration-reconnect-pending {
     description "Request reconnect of pending out-of-band sessions";
     output {
       choice output_c {
         case output-tag {
           leaf output {
             type string;
           }
         }
         case multichassis-tag {
           anyxml multi-routing-engine-results;
         }
       }
     }
   }
   rpc request-system-mode-change {
     description "Change member's current system-mode configuration";
     input {
       uses command-forwarding;
       leaf mode {
         type enumeration {
           enum "mode-104port" {
             description "104port-mode. This will restart PFE";
           }
           enum "non-oversubscribed-mode" {
             description "Non-oversubscribed-mode. This will restart PFE";
           }
           enum "flexi-pic-mode" {
             description "Flexi-pic-mode. This will restart PFE";
           }
           enum "default-mode" {
             description "Default-mode is oversubscribed mode. This will restart PFE";
           }
         }
         mandatory true;
       }
     }
     output {
       choice output_c {
         case output-tag {
           leaf output {
             type string;
           }
         }
         case multichassis-tag {
           anyxml multi-routing-engine-results;
         }
       }
     }
   }
   rpc request-chassis-mic {
     description "Change Media Interface Card status";
     input {
       uses command-forwarding;
       leaf fpc-slot {
         description "Slot number of FPC that houses MIC";
         type union {
           type string {
             pattern "<.*>|$.*";
           }
           type uint32;
         }
         mandatory true;
       }
       leaf mic-slot {
         description "MIC slot number";
         type union {
           type string {
             pattern "<.*>|$.*";
           }
           type uint32 {
             range "0 .. 1";
           }
         }
         mandatory true;
       }
       leaf cmd {
         type enumeration {
           enum "offline" {
             description "Take MIC offline";
           }
           enum "online" {
             description "Bring MIC online";
           }
         }
         mandatory true;
       }
     }
     output {
       choice output_c {
         case output-tag {
           leaf output {
             type string;
           }
         }
         case actual-tag {
           anyxml chassis-mic-state;
         }
         case multichassis-tag {
           anyxml multi-routing-engine-results;
         }
       }
     }
   }
   rpc request-chassis-optics {
     description "Change linecard optics status";
     input {
       uses command-forwarding;
       leaf fpc-slot {
         description "Slot number of FPC that houses optics";
         type union {
           type string {
             pattern "<.*>|$.*";
           }
           type uint32;
         }
         mandatory true;
       }
       leaf reactivate {
         description "Reactivate linecard optics";
         type empty;
         mandatory true;
       }
     }
     output {
       choice output_c {
         case output-tag {
           leaf output {
             type string;
           }
         }
         case actual-tag {
           anyxml chassis-optics-state;
         }
         case multichassis-tag {
           anyxml multi-routing-engine-results;
         }
       }
     }
   }
   rpc request-chassis-pic {
     description "Change Physical Interface Card status";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf cmd {
         type enumeration {
           enum "offline" {
             description "Take PIC offline";
           }
           enum "online" {
             description "Bring PIC online";
           }
         }
         mandatory true;
       }
     }
     output {
       choice output_c {
         case output-tag {
           leaf output {
             type string;
           }
         }
         case multichassis-tag {
           anyxml multi-routing-engine-results;
         }
       }
     }
   }
   rpc request-chassis-port-led-switch-on {
     description "Switch on LED";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-10g {
           description "All 10Gig ports";
           type empty;
         }
         leaf all-40g {
           description "All 40Gig ports";
           type empty;
         }
         leaf all-100g {
           description "All 100Gig ports";
           type empty;
         }
         leaf all-ports {
           description "All PIC ports";
           type empty;
         }
         leaf pic-port {
           description "PIC port number";
           type union {
             type string {
               pattern "<.*>|$.*";
             }
             type uint32 {
               range "0 .. 127";
             }
           }
         }
       }
       leaf duration {
         description "Duration (in seconds) to perform LED blinking";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc request-chassis-port-led-switch-off {
     description "Switch off LED";
     input {
       uses command-forwarding;
       leaf fpc-slot {
         description "Slot number of FPC that houses PIC";
         type union {
           type string {
             pattern "<.*>|$.*";
           }
           type uint32;
         }
         mandatory true;
       }
       leaf pic-slot {
         description "PIC slot number";
         type union {
           type string {
             pattern "<.*>|$.*";
           }
           type uint32;
         }
         mandatory true;
       }
       container port {
         leaf all-10g {
           description "All 10Gig ports";
           type empty;
         }
         leaf all-40g {
           description "All 40Gig ports";
           type empty;
         }
         leaf all-100g {
           description "All 100Gig ports";
           type empty;
         }
         leaf all-ports {
           description "All PIC ports";
           type empty;
         }
         leaf pic-port {
           description "PIC port number";
           type union {
             type string {
               pattern "<.*>|$.*";
             }
             type uint32 {
               range "0 .. 127";
             }
           }
         }
       }
     }
     output {
       choice output_c {
         case output-tag {
           leaf output {
             type string;
           }
         }
         case multichassis-tag {
           anyxml multi-routing-engine-results;
         }
       }
     }
   }
   rpc request-redundancy-feb {
     description "Change Forwarding Engine Board redundancy status";
     input {
       leaf slot {
         description "FEB slot number";
         type union {
           type string {
             pattern "<.*>|$.*";
           }
           type uint32;
         }
         mandatory true;
       }
       leaf cmd {
         type enumeration {
           enum "switch-to-backup" {
             description "Switch mastership to other FEB";
           }
           enum "revert-from-backup" {
             description "Revert mastership back to configured default";
           }
         }
         mandatory true;
       }
     }
     output {
       choice output_c {
         case output-tag {
           leaf output {
             type string;
           }
         }
         case multichassis-tag {
           anyxml multi-routing-engine-results;
         }
       }
     }
   }
   rpc request-chassis-fpc {
     description "Change Flexible PIC Concentrator status";
     input {
       uses command-forwarding;
       leaf slot {
         description "FPC slot number";
         type union {
           type string {
             pattern "<.*>|$.*";
           }
           type uint32;
         }
         mandatory true;
       }
       leaf cmd {
         type enumeration {
           enum "offline" {
             description "Take FPC offline";
           }
           enum "online" {
             description "Bring FPC online";
           }
           enum "restart" {
             description "Restart FPC";
           }
         }
         mandatory true;
       }
     }
     output {
       choice output_c {
         case output-tag {
           leaf output {
             type string;
           }
         }
         case actual-tag {
           anyxml chassis-fpc-state;
         }
         case multichassis-tag {
           anyxml multi-routing-engine-results;
         }
       }
     }
   }
   rpc request-fpc-optical-module {
     description "Change optical module status";
     output {
       choice output_c {
         case output-tag {
           leaf output {
             type string;
           }
         }
         case multichassis-tag {
           anyxml multi-routing-engine-results;
         }
       }
     }
   }
   rpc request-fpc-optical-module-amplifier-chain {
     description "Change amplifier-chain status";
     output {
       choice output_c {
         case output-tag {
           leaf output {
             type string;
           }
         }
         case multichassis-tag {
           anyxml multi-routing-engine-results;
         }
       }
     }
   }
   rpc request-fpc-optical-module-ila {
     description "Change inline-amplifier status";
     output {
       choice output_c {
         case output-tag {
           leaf output {
             type string;
           }
         }
         case multichassis-tag {
           anyxml multi-routing-engine-results;
         }
       }
     }
   }
   rpc request-fpc-optical-module-ila-firmware-upgrade {
     description "Change firmware bundle of inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-soft-reset {
     description "Perform soft-reset on inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-ila-hard-reset {
     description "Perform hard-reset on inline-amplifier";
     input {
       leaf fpc-slot {
         description "FPC slot number";
         type union {
           type string {
             pattern "<.*>|$.*";
           }
           type uint32;
         }
         mandatory true;
       }
       leaf ila-number {
         description "In-line amplifier number";
         type union {
           type uint32;
           type string {
             pattern "<.*>|$.*";
           }
         }
         mandatory true;
       }
     }
     output {
       choice output_c {
         case output-tag {
           leaf output {
             type string;
           }
         }
         case multichassis-tag {
           anyxml multi-routing-engine-results;
         }
       }
     }
   }
   rpc request-fpc-optical-module-firmware-upgrade {
     description "Change firmware bundle of optical module";
     input {
       leaf fpc-slot {
         description "FPC slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-chassis-fabric-plane-sfb {
     description "Change Switch Fabric Card status";
     input {
       uses command-forwarding;
       leaf slot {
         description "SFB slot number";
         type union {
           type string {
             pattern "<.*>|$.*";
           }
           type uint32 {
             range "0 .. 7";
           }
         }
         mandatory true;
       }
       leaf cmd {
         type enumeration {
           enum "offline" {
             description "Take SFB offline";
           }
           enum "online" {
             description "Bring SFB online";
           }
         }
         mandatory true;
       }
     }
     output {
       choice output_c {
         case output-tag {
           leaf output {
             type string;
           }
         }
         case actual-tag {
           anyxml chassis-fabric-plane-state;
         }
         case multichassis-tag {
           anyxml multi-routing-engine-results;
         }
       }
     }
   }
   rpc request-chassis-afeb {
     description "Change Forwarding Engine Board status";
     input {
       leaf cmd {
         type enumeration {
           enum "offline" {
             description "Take AFEB offline";
           }
           enum "online" {
             description "Bring AFEB online";
           }
           enum "restart" {
             description "Restart AFEB";
           }
         }
         mandatory true;
       }
     }
     output {
       choice output_c {
         case output-tag {
           leaf output {
             type string;
           }
         }
         case actual-tag {
           anyxml chassis-afeb-state;
         }
         case multichassis-tag {
           anyxml multi-routing-engine-results;
         }
       }
     }
   }
   rpc request-chassis-tfeb {
     description "Change Taz Forwarding Engine Board status";
     input {
       leaf cmd {
         type enumeration {
           enum "offline" {
             description "Take TFEB offline";
           }
           enum "online" {
             description "Bring TFEB online";
           }
           enum "restart" {
             description "Restart TFEB";
           }
         }
         mandatory true;
       }
     }
     output {
       choice output_c {
         case output-tag {
           leaf output {
             type string;
           }
         }
         case actual-tag {
           anyxml chassis-tfeb-state;
         }
         case multichassis-tag {
           anyxml multi-routing-engine-results;
         }
       }
     }
   }
   rpc request-chassis-fabric-plane {
     description "Change fabric plane status";
     input {
       uses command-forwarding;
       leaf plane {
         description "Fabric plane number";
         type union {
           type string {
             pattern "<.*>|$.*";
           }
           type uint32;
         }
         mandatory true;
       }
       leaf which-command {
         type enumeration {
           enum "offline" {
             description "Take fabric plane offline";
           }
           enum "online" {
             description "Bring fabric plane online";
           }
         }
         mandatory true;
       }
     }
     output {
       choice output_c {
         case output-tag {
           leaf output {
             type string;
           }
         }
         case actual-tag {
           anyxml chassis-fabric-plane-state;
         }
         case multichassis-tag {
           anyxml multi-routing-engine-results;
         }
       }
     }
   }
   rpc request-chassis-fabric-pfe {
     description "Change PFE's fabric status";
     input {
       leaf pfe {
         description "PFE number";
         type union {
           type string {
             pattern "<.*>|$.*";
           }
           type uint32;
         }
         mandatory true;
       }
       leaf fpc {
         description "FPC slot number";
         type union {
           type string {
             pattern "<.*>|$.*";
           }
           type uint32;
         }
         mandatory true;
       }
       leaf which-command {
         type enumeration {
           enum "offline" {
             description "Offline FPC,PFE's fabric";
           }
         }
         mandatory true;
       }
     }
     output {
       choice output_c {
         case output-tag {
           leaf output {
             type string;
           }
         }
         case multichassis-tag {
           anyxml multi-routing-engine-results;
         }
       }
     }
   }
   rpc request-chassis-fabric-upgrade-bandwidth-fpc {
     description "Flexible PIC Concentrator";
     input {
       choice slot_type {
         case slot {
           leaf slot {
             description "FPC slot number for upgrade";
             type union {
               type string {
                 pattern "<.*>|$.*";
               }
               type uint32;
             }
           }
         }
         case all {
           leaf all {
             description "Upgrade all available/possible FPCs";
             type empty;
           }
         }
       }
     }
     output {
       choice output_c {
         case output-tag {
           leaf output {
             type string;
           }
         }
         case multichassis-tag {
           anyxml multi-routing-engine-results;
         }
       }
     }
   }
   rpc request-chassis-fabric-upgrade-bandwidth-info {
     description "Status of FPC to fabric connections";
     output {
       choice output_c {
         case output-tag {
           leaf output {
             type string;
           }
         }
         case multichassis-tag {
           anyxml multi-routing-engine-results;
         }
       }
     }
   }
   rpc request-chassis-spmb {
     description "Change Switch Processor Mezzanine Board status";
     input {
       uses command-forwarding;
       leaf slot {
         description "SPMB slot number";
         type union {
           type string {
             pattern "<.*>|$.*";
           }
           type uint32;
         }
         mandatory true;
       }
       leaf cmd {
         type enumeration {
           enum "restart" {
             description "Restart SPMB";
           }
         }
         mandatory true;
       }
     }
     output {
       choice output_c {
         case output-tag {
           leaf output {
             type string;
           }
         }
         case multichassis-tag {
           anyxml multi-routing-engine-results;
         }
       }
     }
   }
   rpc request-chassis-sib {
     description "Change Switch Interface Board status";
     input {
       uses command-forwarding;
       leaf slot {
         description "SIB slot number";
         type union {
           type string {
             pattern "<.*>|$.*";
           }
           type uint32;
         }
         mandatory true;
       }
       choice cmd {
         case online-offline {
           leaf online-offline {
             type enumeration {
               enum "offline" {
                 description "Take SIB offline";
               }
               enum "online" {
                 description "Bring SIB online";
               }
             }
           }
         }
         case start-receiver {
           leaf start-receiver {
             description "Start SIB optical receiver";
             type union {
               type string {
                 pattern "<.*>|$.*";
               }
               type uint32;
             }
           }
         }
         case stop-receiver {
           leaf stop-receiver {
             description "Stop SIB optical receiver";
             type union {
               type string {
                 pattern "<.*>|$.*";
               }
               type uint32;
             }
           }
         }
         case train-rx-tx {
           leaf train-rx-tx {
             type enumeration {
               enum "train-link-receive" {
                 description "Train link receiver";
               }
               enum "train-link-transmit" {
                 description "Train link transmitter";
               }
             }
           }
         }
       }
     }
     output {
       choice output_c {
         case output-tag {
           leaf output {
             type string;
           }
         }
         case multichassis-tag {
           anyxml multi-routing-engine-results;
         }
       }
     }
   }
   rpc request-chassis-ccg {
     description "Change clock generator status";
     input {
       leaf slot {
         description "CCG slot number";
         type union {
           type string {
             pattern "<.*>|$.*";
           }
           type uint32 {
             range "0 .. 1";
           }
         }
         mandatory true;
       }
       leaf cmd {
         type enumeration {
           enum "offline" {
             description "Take CCG offline";
           }
           enum "online" {
             description "Bring CCG online";
           }
         }
         mandatory true;
       }
     }
     output {
       choice output_c {
         case output-tag {
           leaf output {
             type string;
           }
         }
         case multichassis-tag {
           anyxml multi-routing-engine-results;
         }
       }
     }
   }
   rpc request-chassis-routing-engine {
     description "Change Routing Engine status";
     output {
       choice output_c {
         case output-tag {
           leaf output {
             type string;
           }
         }
         case actual-tag {
           anyxml chassis-routing-engine-state;
         }
         case multichassis-tag {
           anyxml multi-routing-engine-results;
         }
       }
     }
   }
   rpc request-chassis-routing-engine-hard-disk-test {
     description "Run smartd self tests on hard disks";
     input {
       choice test-type {
         case short {
           leaf short {
             description "Run short test";
             type empty;
           }
         }
         case long {
           leaf long {
             description "Run SMART extended self test";
             type empty;
           }
         }
         case show-status {
           leaf show-status {
             description "Display status of test";
             type empty;
           }
         }
       }
       leaf disk {
         description "Name of hard disk";
         type string;
       }
     }
     output {
       choice output_c {
         case output-tag {
           leaf output {
             type string;
           }
         }
         case actual-tag {
           anyxml raid-information;
         }
         case multichassis-tag {
           anyxml multi-routing-engine-results;
         }
       }
     }
   }
   rpc request-chassis-routing-engine-acquire {
     description "Attempt to become master Routing Engine";
     input {
       uses command-forwarding;
       leaf no-confirm {
         description "Do not ask for confirmation";
         type empty;
       }
       leaf check {
         description "Check status of graceful switchover";
         type empty;
       }
     }
     output {
       choice output_c {
         case output-tag {
           leaf output {
             type string;
           }
         }
         case actual-tag {
           anyxml chassis-routing-engine-state;
         }
         case multichassis-tag {
           anyxml multi-routing-engine-results;
         }
       }
     }
   }
   rpc request-chassis-routing-engine-release {
     description "Request that other Routing Engine become master";
     input {
       uses command-forwarding;
       leaf no-confirm {
         description "Do not ask for confirmation";
         type empty;
       }
       leaf check {
         description "Check status of graceful switchover";
         type empty;
       }
     }
     output {
       choice output_c {
         case output-tag {
           leaf output {
             type string;
           }
         }
         case actual-tag {
           anyxml chassis-routing-engine-state;
         }
         case multichassis-tag {
           anyxml multi-routing-engine-results;
         }
       }
     }
   }
   rpc request-chassis-routing-engine-switch {
     description "Toggle mastership between Routing Engines";
     input {
       uses command-forwarding;
       leaf no-confirm {
         description "Do not ask for confirmation";
         type empty;
       }
       leaf check {
         description "Check status of graceful switchover";
         type empty;
       }
     }
     output {
       choice output_c {
         case output-tag {
           leaf output {
             type string;
           }
         }
         case actual-tag {
           anyxml chassis-routing-engine-state;
         }
         case multichassis-tag {
           anyxml multi-routing-engine-results;
         }
       }
     }
   }
   rpc request-feb {
     description "Change Forwarding Engine Board status";
     input {
       leaf slot {
         description "FEB slot number";
         type union {
           type string {
             pattern "<.*>|$.*";
           }
           type uint32;
         }
         mandatory true;
       }
       leaf cmd {
         type enumeration {
           enum "offline" {
             description "Take FEB offline";
           }
           enum "online" {
             description "Bring FEB online";
           }
           enum "restart" {
             description "Restart FEB";
           }
         }
         mandatory true;
       }
     }
     output {
       choice output_c {
         case output-tag {
           leaf output {
             type string;
           }
         }
         case multichassis-tag {
           anyxml multi-routing-engine-results;
         }
       }
     }
   }
   rpc request-chassis-cb {
     description "Change Control Board status";
     input {
       uses command-forwarding;
       leaf slot {
         description "CB slot number";
         type union {
           type string {
             pattern "<.*>|$.*";
           }
           type uint32;
         }
         mandatory true;
       }
       leaf cmd {
         type enumeration {
           enum "offline" {
             description "Take CB offline";
           }
           enum "online" {
             description "Bring CB online";
           }
         }
         mandatory true;
       }
     }
     output {
       choice output_c {
         case output-tag {
           leaf output {
             type string;
           }
         }
         case multichassis-tag {
           anyxml multi-routing-engine-results;
         }
       }
     }
   }
   rpc request-chassis-fpm {
     description "Change craft interface status";
     input {
       uses command-forwarding;
       leaf cmd {
         type enumeration {
           enum "resync" {
             description "Resynchronize craft interface";
           }
         }
         mandatory true;
       }
     }
     output {
       choice output_c {
         case output-tag {
           leaf output {
             type string;
           }
         }
         case actual-tag {
           anyxml chassis-fpm;
         }
         case multichassis-tag {
           anyxml multi-routing-engine-results;
         }
       }
     }
   }
   rpc request-chassis-beacon {
     description "Change beacon status";
     input {
       leaf cmd {
         type enumeration {
           enum "off" {
             description "Turn beacon off";
           }
           enum "on" {
             description "Turn beacon on";
           }
         }
         mandatory true;
       }
       choice which-arg {
         case all {
           leaf all {
             description "All beacons";
             type empty;
           }
         }
         case fpc {
           leaf fpc {
             description "Flexible PIC Controller slot number";
             type union {
               type string {
                 pattern "<.*>|$.*";
               }
               type uint32;
             }
           }
         }
         case cb {
           leaf cb {
             description "Control Board slot number";
             type union {
               type string {
                 pattern "<.*>|$.*";
               }
               type uint32;
             }
           }
         }
         case service-node {
           leaf service-node {
             description "Service node slot number";
             type union {
               type string {
                 pattern "<.*>|$.*";
               }
               type uint32 {
                 range "0 .. 1";
               }
             }
           }
         }
       }
       leaf pic-slot {
         description "PIC slot number";
         type union {
           type string {
             pattern "<.*>|$.*";
           }
           type uint32;
         }
       }
       choice port-num {
         case port {
           leaf port {
             description "Port number";
             type union {
               type string {
                 pattern "<.*>|$.*";
               }
               type uint32;
             }
           }
         }
         case port-range {
           leaf port-range {
             description "Port range";
             type empty;
           }
         }
       }
       leaf lower-limit {
         description "Port range lower limit";
         type union {
           type string {
             pattern "<.*>|$.*";
           }
           type uint32;
         }
       }
       leaf upper-limit {
         description "Port range upper limit";
         type union {
           type string {
             pattern "<.*>|$.*";
           }
           type uint32;
         }
       }
     }
     output {
       choice output_c {
         case output-tag {
           leaf output {
             type string;
           }
         }
         case actual-tag {
           anyxml chassis-beacon-information;
         }
         case multichassis-tag {
           anyxml multi-routing-engine-results;
         }
       }
     }
   }
   rpc request-chassis-satellite-device-mode {
     description "Satellite device specific commands";
     input {
       leaf interface {
         description "Interface name";
         type string;
         mandatory true;
       }
       leaf device-mode {
         description "Device Mode";
         type enumeration {
           enum "satellite" {
             description "Satellite Mode";
           }
         }
         mandatory true;
       }
     }
     output {
       choice output_c {
         case output-tag {
           leaf output {
             type string;
           }
         }
         case multichassis-tag {
           anyxml multi-routing-engine-results;
         }
       }
     }
   }
   rpc request-chassis-satellite-reboot {
     description "Reboot one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
     }
     output {
       choice output_c {
         case output-tag {
           leaf output {
             type string;
           }
         }
         case multichassis-tag {
           anyxml multi-routing-engine-results;
         }
       }
     }
   }
   rpc request-chassis-satellite-restart {
     description "Restart a process on one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf process {
         description "Remote fpc shell command";
         type enumeration {
           enum "packet-forwarding-engine" {
             description "SPFE process";
           }
           enum "discovery-and-provisioning-daemon" {
             description "DPD process";
           }
           enum "chassis-management-daemon" {
             description "LCMD process";
           }
           enum "api-management-daemon" {
             description "AMD process";
           }
           enum "ppman" {
             description "PPMAN process";
           }
           enum "ppman-lite" {
             description "PPMAN-lite process";
           }
         }
         mandatory true;
       }
     }
     output {
       choice output_c {
         case output-tag {
           leaf output {
             type string;
           }
         }
         case multichassis-tag {
           anyxml multi-routing-engine-results;
         }
       }
     }
   }
   rpc request-chassis-satellite-shell-command {
     description "Execute shell command on one or more satellite";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf remote-command {
         description "Remote fpc shell command";
         type string;
         mandatory true;
       }
     }
     output {
       choice output_c {
         case output-tag {
           leaf output {
             type string;
           }
         }
         case multichassis-tag {
           anyxml multi-routing-engine-results;
         }
       }
     }
   }
   rpc request-chassis-satellite-file-copy {
     description "File copy";
     input {
       leaf cmd {
         type enumeration {
           enum "local" {
             description "Local user";
           }
           enum "remote" {
             description "Remote user";
           }
         }
       }
       leaf source {
         description "URL of source file e.g. For SD, use sd100:/..";
         type string;
       }
       leaf destination {
         description "URL of destination file e.g. For SD, use sd100:/..";
         type string;
       }
     }
     output {
       choice output_c {
         case output-tag {
           leaf output {
             type string;
           }
         }
         case multichassis-tag {
           anyxml multi-routing-engine-results;
         }
       }
     }
   }
   rpc request-chassis-satellite-login {
     description "Connect to satellite device";
     input {
       leaf fpc-slot {
         description "Satellite slot number";
         type union {
           type string {
             pattern "<.*>|$.*";
           }
           type uint32 {
             range "65 .. 254";
           }
         }
       }
       leaf interface-name {
         description "Name of the interface";
         type string;
       }
     }
     output {
       choice output_c {
         case output-tag {
           leaf output {
             type string;
           }
         }
         case multichassis-tag {
           anyxml multi-routing-engine-results;
         }
       }
     }
   }
   rpc request-chassis-satellite-beacon {
     description "Change beacon status";
     input {
       choice arg {
         case fpc-slot {
           leaf fpc-slot {
             description "Satellite slot number";
             type union {
               type string {
                 pattern "<.*>|$.*";
               }
               type uint32 {
                 range "65 .. 254";
               }
             }
           }
         }
         case range {
           leaf range {
             description "Slot range as <start-end> slot number (e.g. 100-110)";
             type string;
           }
         }
       }
       leaf cmd {
         type enumeration {
           enum "off" {
             description "Beacon(s) in OFF state";
           }
           enum "on" {
             description "Beacon(s) in ON state";
           }
         }
         mandatory true;
       }
     }
     output {
       choice output_c {
         case output-tag {
           leaf output {
             type string;
           }
         }
         case multichassis-tag {
           anyxml multi-routing-engine-results;
         }
       }
     }
   }
   rpc request-chassis-satellite-disable {
     description "Disable satellite";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-enable {
     description "Enable satellite";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
     }
     output {
       choice output_c {
         case output-tag {
           leaf output {
             type string;
           }
         }
         case multichassis-tag {
           anyxml multi-routing-engine-results;
         }
       }
     }
   }
   rpc request-chassis-satellite-install {
     description "Convert satellite device to standalone Junos device";
     input {
       choice arg {
         case fpc-slot {
           leaf fpc-slot {
             description "Satellite slot number";
             type union {
               type string {
                 pattern "<.*>|$.*";
               }
               type uint32 {
                 range "65 .. 254";
               }
             }
           }
         }
         case device-alias {
           leaf device-alias {
             description "Device alias";
             type string;
           }
         }
       }
       leaf package-name {
         description "URL or pathname of package";
         type jt:filename;
       }
       leaf no-confirm {
         description "Do not ask for confirmation";
         type empty;
       }
     }
     output {
       choice output_c {
         case output-tag {
           leaf output {
             type string;
           }
         }
         case multichassis-tag {
           anyxml multi-routing-engine-results;
         }
       }
     }
   }
   rpc request-mpls-lable-range-reserve {
     description "Request label space repartition now";
     output {
       choice output_c {
         case output-tag {
           leaf output {
             type string;
           }
         }
         case multichassis-tag {
           anyxml multi-routing-engine-results;
         }
       }
     }
   }
   rpc request-mpls-lsp-autobandwidth-adjust {
     description "Request LSP autobandwidth adjustment now";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-autobandwidth-adjust {
     description "Request LSP autobandwidth adjustment now";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
     }
     output {
       choice output_c {
         case output-tag {
           leaf output {
             type string;
           }
         }
         case multichassis-tag {
           anyxml multi-routing-engine-results;
         }
       }
     }
   }
   rpc request-mpls-container-lsp-normalization {
     description "Request container LSP normalization now";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf regex {
         description "Regular expression for LSP names to match";
         type string;
       }
       leaf instance {
         description "Name of routing instance";
         type string;
       }
       leaf bandwidth {
         description "Use the bandwidth for manual normalization";
         type union {
           type uint64;
           type string {
             pattern "<.*>|$.*";
           }
         }
       }
     }
     output {
       choice output_c {
         case output-tag {
           leaf output {
             type string;
           }
         }
         case multichassis-tag {
           anyxml multi-routing-engine-results;
         }
       }
     }
   }
   rpc request-validation-policy {
     description "Request policy reevaluation";
     input {
       choice daemon-select {
         case logical-system {
           leaf logical-system {
             description "Name of logical system";
             type string {
               junos:posix-pattern "^[a-zA-Z0-9_-]{1,63}$";
               junos:pattern-message "Logical-system name is a string consisting of up to 63 letters, numbers, dashes and underscores";
             }
           }
         }
         case rib-sharding {
           leaf rib-sharding {
             description "Name of rib shard";
             type string {
               junos:posix-pattern "^[a-zA-Z0-9_-]{1,63}$";
               junos:pattern-message "Shard name is a string consisting of up to 63 letters, numbers, dashes and underscores";
             }
           }
         }
       }
       leaf record {
         description "Filter by record";
         type jt:ipprefix;
       }
       leaf instance {
         description "Name of route validation instance";
         type string;
       }
     }
     output {
       choice output_c {
         case output-tag {
           leaf output {
             type string;
           }
         }
         case actual-tag {
           anyxml rv-request-policy-information;
         }
         case multichassis-tag {
           anyxml multi-routing-engine-results;
         }
       }
     }
   }
   rpc request-l2ckt-switchover {
     description "Perform l2circuit switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf neighbor {
         description "IP address of neighbor";
         type jt:ipv4addr;
         mandatory true;
       }
       leaf virtual-circuit-id {
         description "Layer 2 circuit ID";
         default "all";
         type string;
       }
     }
     output {
       choice output_c {
         case output-tag {
           leaf output {
             type string;
           }
         }
         case multichassis-tag {
           anyxml multi-routing-engine-results;
         }
       }
     }
   }
   rpc request-vpls-switchover {
     description "Perform LDP VPLS pseudowire switchover";
     input {
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
       leaf instance {
         description "Name of VPLS instance";
         type string;
         mandatory true;
       }
       leaf neighbor {
         description "IP address of neighbor";
         type jt:ipv4addr;
         mandatory true;
       }
       leaf vpls-id {
         description "Layer 2 circuit ID";
         default "all";
         type string;
       }
     }
     output {
       choice output_c {
         case output-tag {
           leaf output {
             type string;
           }
         }
         case multichassis-tag {
           anyxml multi-routing-engine-results;
         }
       }
     }
   }
   rpc request-protection-group-ethernet-aps {
     description "Ethernet APS related operations";
     input {
       leaf maintenance-domain {
         description "Name of maintenance domain";
         type string {
           length "1 .. 45";
         }
         mandatory true;
       }
       leaf maintenance-association {
         description "Name of maintenance association";
         type string {
           length "1 .. 45";
         }
         mandatory true;
       }
       leaf eaps-action {
         type enumeration {
           enum "switch-to-working" {
             description "Switch data path to use working path";
           }
           enum "switch-to-protect" {
             description "Switch data path to use protection path";
           }
           enum "lockout" {
             description "Lockout protection";
           }
           enum "force-switch" {
             description "Force switch data path to use protection path";
           }
           enum "manual-switch" {
             description "Manual switch data path to use protection path";
           }
           enum "exercise" {
             description "Excercise APS protocol";
           }
           enum "clear" {
             description "Clears active local command";
           }
         }
         mandatory true;
       }
       choice daemon-select {
         case logical-system {
           leaf logical-system {
             description "Name of logical system, or 'all'";
             type string {
               junos:posix-pattern "^[a-zA-Z0-9_-]{1,63}$";
               junos:pattern-message "Logical-system name is a string consisting of up to 63 letters, numbers, dashes and underscores";
             }
           }
         }
       }
     }
     output {
       choice output_c {
         case output-tag {
           leaf output {
             type string;
           }
         }
         case multichassis-tag {
           anyxml multi-routing-engine-results;
         }
       }
     }
   }
   rpc request-protection-group-erps-clear {
     description "Clears active local commands";
     input {
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-manual-switch {
     description "Manual switch data path to use protection path";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc request-protection-group-erps-force-switch {
     description "Force switch data path to use protection path";
     input {
       leaf interface-name {
         description "Name of interface";
         type union {
           type jt:interface-wildcard;
           type string {
             pattern "<.*>|$.*";
           }
         }
         mandatory true;
       }
       leaf group-name {
         description "Name of protection group";
         type string {
           length "1 .. 32";
         }
       }
     }
     output {
       choice output_c {
         case output-tag {
           leaf output {
             type string;
           }
         }
         case multichassis-tag {
           anyxml multi-routing-engine-results;
         }
       }
     }
   }
   rpc get-flight-recorder-information {
     description "Debug high cpu issues and scheduler slips";
     input {
       leaf disable {
         description "Disable the flight recorder";
         type empty;
       }
       leaf logical-system {
         description "Enable logical systems";
         type empty;
       }
       leaf cpu-threshold {
         description "Threshold over which the collection is triggered";
         type union {
           type string {
             pattern "<.*>|$.*";
           }
           type uint32 {
             range "1 .. 400";
           }
         }
       }
       leaf polling-frequency {
         description "Frequency of polling for high cpu";
         type union {
           type string {
             pattern "<.*>|$.*";
           }
           type uint32 {
             range "5 .. 100";
           }
         }
       }
       leaf backoff-duration {
         description "Time to wait between two snapshots";
         type union {
           type string {
             pattern "<.*>|$.*";
           }
           type uint32 {
             range "10 .. 1000";
           }
         }
       }
       leaf collect-core {
         description "Whether to take a running core with every snapshot";
         type empty;
       }
       leaf num-snapshots {
         description "How many snapshots to collect before quitting";
         type union {
           type string {
             pattern "<.*>|$.*";
           }
           type uint32 {
             range "1 .. 20";
           }
         }
       }
     }
     output {
       choice output_c {
         case output-tag {
           leaf output {
             type string;
           }
         }
         case actual-tag {
           anyxml flight-recorder-information;
         }
         case multichassis-tag {
           anyxml multi-routing-engine-results;
         }
       }
     }
   }
   rpc monitor-mobile-gateways-call-trace-start {
     description "Trace subscriber events";
     output {
       choice output_c {
         case output-tag {
           leaf output {
             type string;
           }
         }
         case actual-tag {
           anyxml mobile-gateway-sm-af-call-trace-start;
         }
         case multichassis-tag {
           anyxml multi-routing-engine-results;
         }
       }
     }
   }
   rpc get-mobile-gateways-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf apn-name {
         description "Name of APN";
         type string {
           length "1 .. 100";
         }
       }
       leaf file-name-prefix {
         description "Name of file prefix";
         type string {
           length "4 .. 24";
         }
       }
       leaf comment {
         description "Comment to be added in the file";
         type string {
           length "4 .. 100";
         }
       }
     }
     output {
       choice output_c {
         case output-tag {
           leaf output {
             type string;
           }
         }
         case actual-tag {
           anyxml mobile-gateways-call-trace-start-information;
         }
         case multichassis-tag {
           anyxml multi-routing-engine-results;
         }
       }
     }
   }
   rpc get-mobile-gateways-call-trace-stop-information {
     description "Stop subscriber events trace";
     input {
       leaf identifier {
         description "Name of identifier";
         type string {
           length "1 .. 100";
         }
       }
       leaf all {
         description "All call traces";
         type empty;
       }
     }
     output {
       choice output_c {
         case output-tag {
           leaf output {
             type string;
           }
         }
         case actual-tag {
           anyxml mobile-gateways-call-trace-stop-information;
         }
         case multichassis-tag {
           anyxml multi-routing-engine-results;
         }
       }
     }
   }
   rpc get-mobile-gateways-call-trace-clear {
     description "Clear subscriber events trace";
     output {
       choice output_c {
         case output-tag {
           leaf output {
             type string;
           }
         }
         case multichassis-tag {
           anyxml multi-routing-engine-results;
         }
       }
     }
   }
   rpc get-mobile-gateways-call-trace-information {
     description "Show subscriber events trace";
     input {
       leaf selector {
         default "all";
         type enumeration {
           enum "current" {
             description "Display information about current traces";
           }
           enum "completed" {
             description "Display information about completed traces";
           }
           enum "all" {
             description "Display information about all trace";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-call-trace-information;
         }
         case multichassis-tag {
           anyxml multi-routing-engine-results;
         }
       }
     }
   }
   rpc get-mobile-gateways-sgw-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events";
         default "1";
         type union {
           type string {
             pattern "<.*>|$.*";
           }
           type uint32 {
             range "1 .. 50";
           }
         }
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       choice output_c {
         case output-tag {
           leaf output {
             type string;
           }
         }
         case actual-tag {
           anyxml mobile-gateways-call-trace-start-information;
         }
         case multichassis-tag {
           anyxml multi-routing-engine-results;
         }
       }
     }
   }
   rpc get-mobile-gateways-sgw-call-trace-stop-information {
     description "Stop subscriber events trace";
     input {
       leaf identifier {
         description "Name of identifier";
         type string {
           length "1 .. 100";
         }
       }
       leaf all {
         description "All call traces";
         type empty;
       }
     }
     output {
       choice output_c {
         case output-tag {
           leaf output {
             type string;
           }
         }
         case actual-tag {
           anyxml mobile-gateways-call-trace-stop-information;
         }
         case multichassis-tag {
           anyxml multi-routing-engine-results;
         }
       }
     }
   }
   rpc get-mobile-gateways-sgw-call-trace-clear {
     description "Clear subscriber events trace";
     output {
       choice output_c {
         case output-tag {
           leaf output {
             type string;
           }
         }
         case multichassis-tag {
           anyxml multi-routing-engine-results;
         }
       }
     }
   }
   rpc get-mobile-gateways-sgw-call-trace-information {
     description "Show subscriber events trace";
     input {
       leaf selector {
         default "all";
         type enumeration {
           enum "current" {
             description "Display information about current traces";
           }
           enum "completed" {
             description "Display information about completed traces";
           }
           enum "all" {
             description "Display information about all trace";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-call-trace-information;
         }
         case multichassis-tag {
           anyxml multi-routing-engine-results;
         }
       }
     }
   }
   rpc get-mobile-gateways-tdf-call-trace-start-information {
     description "Start subscriber events trace";
     input {
       leaf msisdn {
         description "Trace events for a specific msisdn";
         type string {
           length "3 .. 15";
         }
       }
       leaf imsi {
         description "Trace events for a specific imsi";
         type string {
           length "5 .. 15";
         }
       }
       leaf next-call {
         description "Trace the next call events on each session PIC";
         type empty;
       }
       leaf v4-addr {
         description "Trace events for a specific IPV4 subscriber";
         type jt:ipaddr;
       }
       leaf v6-addr {
         description "Trace events for a specific IPV6 subscriber";
         type jt:ipv6addr;
       }
       leaf routing-instance {
         description "Routing Instance which the subscriber belong to";
         type string;
       }
       leaf user-name {
         description "Subscriber User Name";
         type string;
       }
       leaf subscriber-name {
         description "Non-IP Subscriber Name";
         type string;
       }
     }
     output {
       choice output_c {
         case output-tag {
           leaf output {
             type string;
           }
         }
         case actual-tag {
           anyxml mobile-gateways-call-trace-start-information;
         }
         case multichassis-tag {
           anyxml multi-routing-engine-results;
         }
       }
     }
   }
   rpc get-mobile-gateways-tdf-call-trace-stop-information {
     description "Stop subscriber events trace";
     input {
       leaf identifier {
         description "Name of identifier";
         type string {
           length "1 .. 100";
         }
       }
       leaf all {
         description "All call traces";
         type empty;
       }
     }
     output {
       choice output_c {
         case output-tag {
           leaf output {
             type string;
           }
         }
         case actual-tag {
           anyxml mobile-gateways-call-trace-stop-information;
         }
         case multichassis-tag {
           anyxml multi-routing-engine-results;
         }
       }
     }
   }
   rpc get-mobile-gateways-tdf-call-trace-clear {
     description "Clear subscriber events trace";
     output {
       choice output_c {
         case output-tag {
           leaf output {
             type string;
           }
         }
         case multichassis-tag {
           anyxml multi-routing-engine-results;
         }
       }
     }
   }
   rpc get-mobile-gateways-tdf-call-trace-information {
     description "Show subscriber events trace";
     input {
       leaf selector {
         default "all";
         type enumeration {
           enum "current" {
             description "Display information about current traces";
           }
           enum "completed" {
             description "Display information about completed traces";
           }
           enum "all" {
             description "Display information about all traces";
           }
         }
       }
       leaf verbosity-level {
         description "Select the verbosity level";
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml mobile-gateways-call-trace-information;
         }
         case multichassis-tag {
           anyxml multi-routing-engine-results;
         }
       }
     }
   }
   rpc request-path-computation-client-main-pce {
     description "Request new active PCE";
     input {
       leaf pce-id {
         description "PCE ID from configuration";
         type string;
         mandatory true;
       }
     }
     output {
       choice output_c {
         case output-tag {
           leaf output {
             type string;
           }
         }
         case multichassis-tag {
           anyxml multi-routing-engine-results;
         }
       }
     }
   }
   rpc request-path-computation-retry-delegation {
     description "Request new active PCE";
     input {
       leaf lsp-name {
         description "Name of static label-switched-path";
         type string;
         mandatory true;
       }
     }
     output {
       choice output_c {
         case output-tag {
           leaf output {
             type string;
           }
         }
         case multichassis-tag {
           anyxml multi-routing-engine-results;
         }
       }
     }
   }
   rpc request-line-card-login {
     description "Connect to line card";
     input {
       leaf member {
         description "Member ID";
         type union {
           type string {
             pattern "<.*>|$.*";
           }
           type int32;
         }
         mandatory true;
       }
     }
     output {
       choice output_c {
         case output-tag {
           leaf output {
             type string;
           }
         }
         case actual-tag {
           anyxml run-command;
         }
         case multichassis-tag {
           anyxml multi-routing-engine-results;
         }
       }
     }
   }
   rpc request-virtual-chassis-reactivate {
     description "Make active from inactive-split mode";
     output {
       choice output_c {
         case output-tag {
           leaf output {
             type string;
           }
         }
         case multichassis-tag {
           anyxml multi-routing-engine-results;
         }
       }
     }
   }
   rpc request-virtual-chassis-renumber {
     description "Change member ID";
     input {
       leaf member-id {
         description "Current member ID";
         type union {
           type string {
             pattern "<.*>|$.*";
           }
           type int32;
         }
         mandatory true;
       }
       leaf new-member-id {
         description "New member ID";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc request-virtual-chassis-recycle {
     description "Recycle member ID";
     input {
       leaf member-id {
         description "Member ID";
         type union {
           type string {
             pattern "<.*>|$.*";
           }
           type int32;
         }
         mandatory true;
       }
     }
     output {
       choice output_c {
         case output-tag {
           leaf output {
             type string;
           }
         }
         case multichassis-tag {
           anyxml multi-routing-engine-results;
         }
       }
     }
   }
   rpc request-virtual-chassis-vc-port-set-interface {
     description "Member's virtual chassis interface";
     input {
       uses command-forwarding;
       leaf interface-name {
         description "Name of dedicated virtual chassis interface";
         type string;
         mandatory true;
       }
       leaf disable {
         description "Disable virtual chassis interface";
         type empty;
       }
     }
     output {
       choice output_c {
         case output-tag {
           leaf output {
             type string;
           }
         }
         case multichassis-tag {
           anyxml multi-routing-engine-results;
         }
       }
     }
   }
   rpc request-virtual-chassis-vc-port-set-pic-slot {
     description "Member's PIC slot";
     input {
       uses command-forwarding;
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-virtual-chassis-vc-port-set-fpc-slot {
     description "Member's FPC slot";
     input {
       uses command-forwarding;
       leaf fpc-slot {
         description "FPC slot number";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
       leaf channel {
         description "Channel number";
         type union {
           type string {
             pattern "<.*>|$.*";
           }
           type uint32 {
             range "0 .. 3";
           }
         }
       }
     }
     output {
       choice output_c {
         case output-tag {
           leaf output {
             type string;
           }
         }
         case multichassis-tag {
           anyxml multi-routing-engine-results;
         }
       }
     }
   }
   rpc request-virtual-chassis-vc-port-delete-pic-slot {
     description "Member's PIC slot";
     input {
       uses command-forwarding;
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc request-virtual-chassis-vc-port-delete-fpc-slot {
     description "Member's FPC slot";
     input {
       uses command-forwarding;
       leaf fpc-slot {
         description "FPC slot number";
         type union {
           type string {
             pattern "<.*>|$.*";
           }
           type uint32;
         }
         mandatory true;
       }
       leaf pic-slot {
         description "PIC slot number";
         type union {
           type string {
             pattern "<.*>|$.*";
           }
           type uint32;
         }
         mandatory true;
       }
       leaf port {
         description "Port number";
         type union {
           type string {
             pattern "<.*>|$.*";
           }
           type uint32;
         }
         mandatory true;
       }
       leaf channel {
         description "Channel number";
         type union {
           type string {
             pattern "<.*>|$.*";
           }
           type uint32 {
             range "0 .. 3";
           }
         }
       }
     }
     output {
       choice output_c {
         case output-tag {
           leaf output {
             type string;
           }
         }
         case multichassis-tag {
           anyxml multi-routing-engine-results;
         }
       }
     }
   }
   rpc request-virtual-chassis-vc-port-diag-optics {
     description "Virtual chassis port diagnostics optics";
     input {
       uses command-forwarding;
       leaf interface-name {
         description "Name of virtual chassis port";
         type string;
       }
     }
     output {
       choice output_c {
         case output-tag {
           leaf output {
             type string;
           }
         }
         case multichassis-tag {
           anyxml multi-routing-engine-results;
         }
       }
     }
   }
   rpc req-virtual-chassis-mode {
     description "Set a member's mode (Warning: member's mode must be consistent)";
     input {
       uses command-forwarding;
       leaf fabric {
         description "Set to virtual chassis fabric mode";
         type empty;
       }
       leaf mixed {
         description "Allow devices from different product families to become members";
         type empty;
       }
       leaf disable {
         description "Disable specified mode";
         type empty;
       }
       leaf reboot {
         description "Reboot system after changing mode";
         type empty;
       }
       leaf ieee-clause-82 {
         description "Allow devices to operate in ieee-clause-82 PCS encoding";
         type empty;
       }
     }
     output {
       choice output_c {
         case output-tag {
           leaf output {
             type string;
           }
         }
         case multichassis-tag {
           anyxml multi-routing-engine-results;
         }
       }
     }
   }
   rpc set-virtual-chassis-member-id {
     description "Set virtual-chassis information";
     input {
       leaf member {
         description "Virtual-Chassis member number";
         type union {
           type string {
             pattern "<.*>|$.*";
           }
           type int32;
         }
         mandatory true;
       }
       leaf slots-per-chassis {
         description "Virtual-Chassis FPC slots per chassis number";
         type enumeration {
           enum "12" {
             description "12 FPC slots per chassis";
           }
           enum "20" {
             description "20 FPC slots per chassis";
           }
         }
       }
     }
     output {
       choice output_c {
         case output-tag {
           leaf output {
             type string;
           }
         }
         case multichassis-tag {
           anyxml multi-routing-engine-results;
         }
       }
     }
   }
   rpc delete-virtual-chassis-member-id {
     description "Delete virtual-chassis information";
     output {
       choice output_c {
         case output-tag {
           leaf output {
             type string;
           }
         }
         case multichassis-tag {
           anyxml multi-routing-engine-results;
         }
       }
     }
   }
   rpc get-virtual-chassis-diagnostic-information {
     description "Device reachability diagnostics";
     input {
       leaf test-name {
         description "Name of the test";
         type string {
           length "1 .. 20";
         }
         mandatory true;
       }
       leaf destination-device {
         description "Probe destination (global) device ID";
         type union {
           type uint32;
           type string {
             pattern "<.*>|$.*";
           }
         }
       }
       leaf destination-fpc {
         description "Probe destination FPC";
         type union {
           type uint32;
           type string {
             pattern "<.*>|$.*";
           }
         }
       }
       leaf destination-ip-address {
         description "IP address of destination FPC";
         type jt:ipaddr;
       }
       leaf source-fpc {
         description "Probe initiator FPC";
         type union {
           type uint32;
           type string {
             pattern "<.*>|$.*";
           }
         }
       }
       leaf source-ip-address {
         description "IP address of source FPC";
         type jt:ipaddr;
       }
       leaf probe-size {
         description "Size of one probe in bytes";
         default "56";
         type union {
           type string {
             pattern "<.*>|$.*";
           }
           type uint32 {
             range "56 .. 1500";
           }
         }
       }
       leaf probe-count {
         description "Number of probes in a test";
         default "5";
         type union {
           type string {
             pattern "<.*>|$.*";
           }
           type uint32 {
             range "1 .. 10";
           }
         }
       }
       leaf probe-pattern {
         description "Payload pattern byte in the probe (0x00-0xff)";
         default "0x00";
         type string {
           junos:posix-pattern "^0(x|X)([0-9|a-f|A-F])([0-9|a-f|A-F])$";
           junos:pattern-message "Must be hexadecimal bit pattern in (0x00..0xff)";
         }
       }
       leaf probe-interval {
         description "Duration between successive probes";
         default "1";
         units "seconds";
         type union {
           type string {
             pattern "<.*>|$.*";
           }
           type uint32 {
             range "1 .. 3";
           }
         }
       }
       leaf test-interval {
         description "Time interval to perform this test again";
         default "1";
         units "seconds";
         type union {
           type string {
             pattern "<.*>|$.*";
           }
           type uint32 {
             range "1 .. 5";
           }
         }
       }
       leaf test-count {
         description "Number of times this test to be performed";
         default "1";
         type union {
           type string {
             pattern "<.*>|$.*";
           }
           type uint32 {
             range "1 .. 3";
           }
         }
       }
     }
     output {
       choice output_c {
         case output-tag {
           leaf output {
             type string;
           }
         }
         case actual-tag {
           anyxml virtual-chassis-diagnostic-information;
         }
         case multichassis-tag {
           anyxml multi-routing-engine-results;
         }
       }
     }
   }
   rpc switch-vc-routing-engine-protocol-master {
     description "Toggle mastership between VC members";
     input {
       leaf check {
         description "Check status of graceful switchover";
         type empty;
       }
     }
     output {
       choice output_c {
         case output-tag {
           leaf output {
             type string;
           }
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
