/*
 * Copyright (c) 2019 Juniper Networks, Inc.
 * All rights reserved.
 */
 module junos-ex-conf-multicast-snooping-options {
   namespace "http://yang.juniper.net/junos-ex/conf/multicast-snooping-options";

   prefix jc-multicast-snooping-options;

   import junos-common-types {
     prefix jt;
   }

   import junos-ex-conf-root {
     prefix jc;
   }

   organization "Juniper Networks, Inc.";

   contact "yang-support@juniper.net";

   description "Junos multicast-snooping-options configuration module";

   revision 2019-01-01 {
     description "Junos: 19.2R1.8";
   }

   augment /jc:configuration {
     uses multicast-snooping-options-group;
   }
   augment /jc:configuration/jc:groups {
     uses multicast-snooping-options-group;
   }
   grouping multicast-snooping-options-group {
     container multicast-snooping-options {
       description "Multicast snooping option configuration";
       uses juniper-multicast-snooping-options;
     }
   }
   grouping juniper-multicast-snooping-options {
     uses apply-advanced;
     container options {
       description "Miscellaneous options";
       uses apply-advanced;
       container syslog {
         description "Set system logging level";
         uses apply-advanced;
         container level {
           description "Logging level";
           leaf emergency {
             description "Emergency level";
             type empty;
           }
           leaf alert {
             description "Alert level";
             type empty;
           }
           leaf critical {
             description "Critical level";
             type empty;
           }
           leaf error {
             description "Error level";
             type empty;
           }
           leaf warning {
             description "Warning level";
             type empty;
           }
           leaf notice {
             description "Notice level";
             type empty;
           }
           leaf info {
             description "Informational level";
             type empty;
           }
           leaf debug {
             description "Debugging level";
             type empty;
           }
         }
         leaf upto {
           description "Log up to a particular logging level";
           type enumeration {
             enum "emergency" {
               description "Emergency level";
             }
             enum "alert" {
               description "Alert level";
             }
             enum "critical" {
               description "Critical level";
             }
             enum "error" {
               description "Error level";
             }
             enum "warning" {
               description "Warning level";
             }
             enum "notice" {
               description "Notice level";
             }
             enum "info" {
               description "Informational level";
             }
             enum "debug" {
               description "Debugging level";
             }
           }
         }
         leaf mark {
           description "Periodically mark the trace file";
           units "seconds";
           type union {
             type int32;
             type string {
               pattern "<.*>|$.*";
             }
           }
         }
       }
     }
     container traceoptions {
       description "Multicast snooping trace options";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "parse" {
               description "Trace configuration parsing";
             }
             enum "config-internal" {
               description "Trace configuration internals";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf disable {
           description "Disable this trace flag";
           type empty;
         }
       }
     }
     container forwarding-cache {
       description "Multicast forwarding cache";
       uses apply-advanced;
       container threshold {
         description "Threshold";
         uses apply-advanced;
         leaf suppress {
           description "Suppress threshold";
           type union {
             type string {
               pattern "<.*>|$.*";
             }
             type uint32 {
               range "1 .. 200000";
             }
           }
         }
         leaf reuse {
           description "Reuse threshold";
           type union {
             type string {
               pattern "<.*>|$.*";
             }
             type uint32 {
               range "1 .. 200000";
             }
           }
         }
       }
     }
     leaf-list flood-groups {
       ordered-by user;
       description "Groups for which the traffic will be flooded";
       type jt:ipaddr;
     }
     container graceful-restart {
       description "Configure graceful restart attributes";
       uses apply-advanced;
       choice enable-disable {
         case case_1 {
           leaf disable {
             description "Disable graceful restart";
             type empty;
           }
         }
       }
       leaf restart-duration {
         description "Maximum time for graceful restart to finish";
         default "180";
         units "seconds";
         type union {
           type string {
             pattern "<.*>|$.*";
           }
           type uint32 {
             range "0 .. 300";
           }
         }
       }
     }
     container multichassis-lag-replicate-state {
       presence "enable multichassis-lag-replicate-state";
       description "Enable multichassis lag replication";
       uses apply-advanced;
       leaf suppress-report {
         description "Enable mclag report suppression";
         type empty;
       }
     }
     leaf nexthop-hold-time {
       description "Nexthop hold time in milliseconds";
       units "milliseconds";
       type union {
         type string {
           pattern "<.*>|$.*";
         }
         type uint32 {
           range "1 .. 1000";
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping macro-data-type {
     leaf name {
       description "Keyword part of the keyword-value pair";
       type string;
     }
     leaf value {
       description "Value part of the keyword-value pair";
       type string;
     }
   }
 }
