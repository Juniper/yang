/*
 * Copyright (c) 2022 Juniper Networks, Inc.
 * All rights reserved.
 */
 module junos-es-rpc-isis {
   namespace "http://yang.juniper.net/junos-es/rpc/isis";

   prefix isis;

   import junos-common-types {
     prefix jt;
     revision-date 2022-01-01;
   }

   organization "Juniper Networks, Inc.";

   contact "yang-support@juniper.net";

   description "Junos RPC YANG module for isis command(s)";

   revision 2022-01-01 {
     description "Junos: 22.3R1.9";
   }

   rpc get-isis-adjacency-information {
     description "Show IS-IS adjacency database";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf system-id {
         description "System ID of intermediate system";
         type string;
       }
     }
     output {
       choice output_c {
         case output-tag {
           leaf output {
             type string;
           }
         }
         case actual-tag {
           anyxml isis-adjacency-information;
         }
         case multichassis-tag {
           anyxml multi-routing-engine-results;
         }
       }
     }
   }
   rpc get-isis-adjacency-holddown-information {
     description "Show IS-IS adjacency-holddown status";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
     }
     output {
       choice output_c {
         case output-tag {
           leaf output {
             type string;
           }
         }
         case actual-tag {
           anyxml isis-adjacency-holddown-information;
         }
         case multichassis-tag {
           anyxml multi-routing-engine-results;
         }
       }
     }
   }
   rpc get-isis-authentication-information {
     description "Show IS-IS authentication information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output_c {
         case output-tag {
           leaf output {
             type string;
           }
         }
         case actual-tag {
           anyxml isis-authentication-information;
         }
         case multichassis-tag {
           anyxml multi-routing-engine-results;
         }
       }
     }
   }
   rpc get-isis-bgporr-information {
     description "Show BGP optimal route reflection groups";
     input {
       choice daemon-select {
         case logical-system {
           leaf logical-system {
             description "Name of logical system, or 'all'";
             type string {
             }
           }
         }
       }
       leaf igp-instance {
         description "Name of igp-instance";
         type string;
       }
       leaf destination {
         description "IP address and optional prefix length of destination";
         type jt:ipprefix;
       }
       leaf instance {
         description "Name of IS-IS instance";
         type string;
       }
       leaf group {
         description "BGP optimal route-reflection peer group name";
         type string;
       }
     }
     output {
       choice output_c {
         case output-tag {
           leaf output {
             type string;
           }
         }
         case actual-tag {
           anyxml isis-bgporr-information;
         }
         case multichassis-tag {
           anyxml multi-routing-engine-results;
         }
       }
     }
   }
   rpc get-isis-database-information {
     description "Show IS-IS link-state database";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf level {
         description "Number of IS-IS level";
         type union {
           type string {
             pattern "<.*>|$.*";
           }
           type uint32 {
             range "1 .. 2";
           }
         }
       }
       leaf system-id {
         description "System ID of IS";
         type string;
       }
     }
     output {
       choice output_c {
         case output-tag {
           leaf output {
             type string;
           }
         }
         case actual-tag {
           anyxml isis-database-information;
         }
         case multichassis-tag {
           anyxml multi-routing-engine-results;
         }
       }
     }
   }
   rpc get-isis-hostname-information {
     description "Show IS-IS hostname database";
     input {
       choice daemon-select {
         case logical-system {
           leaf logical-system {
             description "Name of logical system, or 'all'";
             type string {
             }
           }
         }
       }
     }
     output {
       choice output_c {
         case output-tag {
           leaf output {
             type string;
           }
         }
         case actual-tag {
           anyxml isis-hostname-information;
         }
         case multichassis-tag {
           anyxml multi-routing-engine-results;
         }
       }
     }
   }
   rpc get-isis-interface-information {
     description "Show IS-IS interface information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
           enum "extensive" {
             description "Display extensive output";
           }
         }
       }
       leaf instance {
         description "Name of IS-IS instance";
         type string;
       }
       leaf interface-name {
         description "Name of interface";
         type string;
       }
     }
     output {
       choice output_c {
         case output-tag {
           leaf output {
             type string;
           }
         }
         case actual-tag {
           anyxml isis-interface-information;
         }
         case multichassis-tag {
           anyxml multi-routing-engine-results;
         }
       }
     }
   }
   rpc get-isis-interface-group-information {
     description "Show IS-IS interface-group information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output_c {
         case output-tag {
           leaf output {
             type string;
           }
         }
         case actual-tag {
           anyxml isis-interface-group-information;
         }
         case multichassis-tag {
           anyxml multi-routing-engine-results;
         }
       }
     }
   }
   rpc get-isis-layer2-map-information {
     description "Show IS-IS ARP/ND mapping information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf destination {
         description "IP address of mapping entry";
         type jt:ipaddr;
       }
     }
     output {
       choice output_c {
         case output-tag {
           leaf output {
             type string;
           }
         }
         case actual-tag {
           anyxml isis-layer2-map-information;
         }
         case multichassis-tag {
           anyxml multi-routing-engine-results;
         }
       }
     }
   }
   rpc get-isis-overview-information {
     description "Show overview of IS-IS information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output_c {
         case output-tag {
           leaf output {
             type string;
           }
         }
         case actual-tag {
           anyxml isis-overview-information;
         }
         case multichassis-tag {
           anyxml multi-routing-engine-results;
         }
       }
     }
   }
   rpc get-isis-route-information {
     description "Show IS-IS routing table";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf instance {
         description "Name of IS-IS instance";
         type string;
       }
       leaf destination {
         description "IP address and optional prefix length of destination";
         type jt:ipprefix;
       }
       leaf floodgroup {
         description "Routes belonging to a specific floodgroup";
         type string {
         }
       }
       leaf nexthop {
         description "Routes reachable through specific nexthop";
         type string;
       }
       leaf download-priority {
         description "Sorted by download priority";
         type empty;
       }
       leaf family {
         type enumeration {
           enum "inet" {
             description "Display IPv4 routes";
           }
           enum "inet6" {
             description "Display IPv6 routes";
           }
           enum "iso" {
             description "Display CLNS routes";
           }
         }
       }
       leaf topology {
         description "Name of topology from which routes were learned";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output_c {
         case output-tag {
           leaf output {
             type string;
           }
         }
         case actual-tag {
           anyxml isis-route-information;
         }
         case multichassis-tag {
           anyxml multi-routing-engine-results;
         }
       }
     }
   }
   rpc get-isis-purge-log-information {
     description "Show log of PURGE runs";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of IS-IS level";
         type union {
           type string {
             pattern "<.*>|$.*";
           }
           type uint32 {
             range "1 .. 2";
           }
         }
       }
     }
     output {
       choice output_c {
         case output-tag {
           leaf output {
             type string;
           }
         }
         case actual-tag {
           anyxml isis-purge-information;
         }
         case multichassis-tag {
           anyxml multi-routing-engine-results;
         }
       }
     }
   }
   rpc get-isis-spf-log-information {
     description "Show log of SPF runs";
     input {
       choice daemon-select {
         case logical-system {
           leaf logical-system {
             description "Name of logical system, or 'all'";
             type string {
             }
           }
         }
       }
       leaf igp-instance {
         description "Name of igp-instance";
         type string;
       }
       leaf flex-algorithm-id {
         description "Flex Algorithm id";
         type union {
           type string {
             pattern "<.*>|$.*";
           }
           type uint32 {
             range "128 .. 255";
           }
         }
       }
       leaf instance {
         description "Name of IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output_c {
         case output-tag {
           leaf output {
             type string;
           }
         }
         case actual-tag {
           anyxml isis-spf-information;
         }
         case multichassis-tag {
           anyxml multi-routing-engine-results;
         }
       }
     }
   }
   rpc get-isis-spf-results-information {
     description "Show results from SPF runs";
     input {
       choice daemon-select {
         case logical-system {
           leaf logical-system {
             description "Name of logical system, or 'all'";
             type string {
             }
           }
         }
       }
       leaf igp-instance {
         description "Name of igp-instance";
         type string;
       }
       leaf instance {
         description "IS-IS instance";
         type string;
       }
       leaf level {
         description "Number of IS-IS level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output_c {
         case output-tag {
           leaf output {
             type string;
           }
         }
         case actual-tag {
           anyxml isis-spf-information;
         }
         case multichassis-tag {
           anyxml multi-routing-engine-results;
         }
       }
     }
   }
   rpc get-isis-spf-results-brief-information {
     description "Show brief summary of SPF results";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf level {
         description "Number of level";
         type union {
           type string {
             pattern "<.*>|$.*";
           }
           type uint32 {
             range "1 .. 2";
           }
         }
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output_c {
         case output-tag {
           leaf output {
             type string;
           }
         }
         case actual-tag {
           anyxml isis-spf-information;
         }
         case multichassis-tag {
           anyxml multi-routing-engine-results;
         }
       }
     }
   }
   rpc get-isis-statistics-information {
     description "Show IS-IS performance statistics";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output_c {
         case output-tag {
           leaf output {
             type string;
           }
         }
         case actual-tag {
           anyxml isis-statistics-information;
         }
         case multichassis-tag {
           anyxml multi-routing-engine-results;
         }
       }
     }
   }
   rpc get-isis-interface-statistics-information {
     description "ISIS interface statistics information";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
       leaf interface-name {
         description "Name of interface";
         type string;
       }
     }
     output {
       choice output_c {
         case output-tag {
           leaf output {
             type string;
           }
         }
         case actual-tag {
           anyxml isis-interface-statistics-information;
         }
         case multichassis-tag {
           anyxml multi-routing-engine-results;
         }
       }
     }
   }
   rpc get-isis-interface-traffic-stats-information {
     description "Show aggregate SPRING traffic";
     input {
       choice daemon-select {
         case logical-system {
           leaf logical-system {
             description "Name of logical system, or 'all'";
             type string {
             }
           }
         }
       }
       leaf igp-instance {
         description "Name of igp-instance";
         type string;
       }
     }
     output {
       choice output_c {
         case output-tag {
           leaf output {
             type string;
           }
         }
         case actual-tag {
           anyxml isis-interface-traffic-statistics-information;
         }
         case multichassis-tag {
           anyxml multi-routing-engine-results;
         }
       }
     }
   }
   rpc get-isis-spring-flex-algorithm-information {
     description "Show SPRING flex-algorithm information";
     input {
       choice daemon-select {
         case logical-system {
           leaf logical-system {
             description "Name of logical system, or 'all'";
             type string {
             }
           }
         }
       }
       leaf flex-algorithm-id {
         description "Flex Algorithm id";
         type union {
           type string {
             pattern "<.*>|$.*";
           }
           type uint32 {
             range "128 .. 255";
           }
         }
       }
       leaf igp-instance {
         description "Name of igp-instance";
         type string;
       }
       leaf level {
         description "Number of IS-IS level";
         type union {
           type string {
             pattern "<.*>|$.*";
           }
           type uint32 {
             range "1 .. 2";
           }
         }
       }
     }
     output {
       choice output_c {
         case output-tag {
           leaf output {
             type string;
           }
         }
         case actual-tag {
           anyxml isis-spring-flex-algorithm-information;
         }
         case multichassis-tag {
           anyxml multi-routing-engine-results;
         }
       }
     }
   }
   rpc get-isis-spring-sensor-information {
     description "Show SPRING sensor info";
     input {
       choice daemon-select {
         case logical-system {
           leaf logical-system {
             description "Name of logical system, or 'all'";
             type string {
             }
           }
         }
       }
       leaf igp-instance {
         description "Name of igp-instance";
         type string;
       }
     }
     output {
       choice output_c {
         case output-tag {
           leaf output {
             type string;
           }
         }
         case actual-tag {
           anyxml isis-spring-sensor-information;
         }
         case multichassis-tag {
           anyxml multi-routing-engine-results;
         }
       }
     }
   }
   rpc get-isis-backup-spf-results-information {
     description "Show results from backup SPF runs";
     input {
       choice daemon-select {
         case logical-system {
           leaf logical-system {
             description "Name of logical system, or 'all'";
             type string {
             }
           }
         }
       }
       leaf igp-instance {
         description "Name of igp-instance";
         type string;
       }
       leaf destination {
         description "Hostname or System-ID of remote destination";
         type string;
       }
       leaf instance {
         description "IS-IS instance";
         type string;
       }
       leaf level {
         description "Number of IS-IS level";
         type union {
           type string {
             pattern "<.*>|$.*";
           }
           type uint32 {
             range "1 .. 2";
           }
         }
       }
       leaf no-coverage {
         description "Destinations with no backup coverage";
         type empty;
       }
       leaf topology {
         description "Name of topology";
         type enumeration {
           enum "unicast" {
             description "Unicast topology";
           }
           enum "ipv4-multicast" {
             description "IPv4 multicast topology";
           }
           enum "ipv6-unicast" {
             description "IPv6 unicast topology";
           }
           enum "ipv6-multicast" {
             description "IPv6 multicast topology";
           }
         }
       }
     }
     output {
       choice output_c {
         case output-tag {
           leaf output {
             type string;
           }
         }
         case actual-tag {
           anyxml isis-spf-information;
         }
         case multichassis-tag {
           anyxml multi-routing-engine-results;
         }
       }
     }
   }
   rpc get-isis-backup-coverage-information {
     description "Show IS-IS backup coverage";
     input {
       choice daemon-select {
         case logical-system {
           leaf logical-system {
             description "Name of logical system, or 'all'";
             type string {
             }
           }
         }
       }
       leaf igp-instance {
         description "Name of igp-instance";
         type string;
       }
       leaf instance {
         description "Name of IS-IS instance";
         type string;
       }
     }
     output {
       choice output_c {
         case output-tag {
           leaf output {
             type string;
           }
         }
         case actual-tag {
           anyxml isis-backup-coverage-information;
         }
         case multichassis-tag {
           anyxml multi-routing-engine-results;
         }
       }
     }
   }
   rpc get-isis-backup-lsp-information {
     description "Show IS-IS MPLS backup LSP information";
     input {
       choice daemon-select {
         case logical-system {
           leaf logical-system {
             description "Name of logical system, or 'all'";
             type string {
             }
           }
         }
       }
       leaf igp-instance {
         description "Name of igp-instance";
         type string;
       }
     }
     output {
       choice output_c {
         case output-tag {
           leaf output {
             type string;
           }
         }
         case actual-tag {
           anyxml isis-backup-mplsp-information;
         }
         case multichassis-tag {
           anyxml multi-routing-engine-results;
         }
       }
     }
   }
   rpc get-isis-context-identifier-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf instance {
         description "Name of IS-IS instance";
         type string;
       }
     }
     output {
       choice output_c {
         case output-tag {
           leaf output {
             type string;
           }
         }
         case actual-tag {
           anyxml isis-context-information;
         }
         case multichassis-tag {
           anyxml multi-routing-engine-results;
         }
       }
     }
   }
   rpc get-isis-context-identifier-origin-information {
     description "Show IS-IS context-identifier information";
     input {
       choice daemon-select {
         case logical-system {
           leaf logical-system {
             description "Name of logical system, or 'all'";
             type string {
             }
           }
         }
       }
       leaf igp-instance {
         description "Name of igp-instance";
         type string;
       }
       leaf verbosity_level {
         default "brief";
         type enumeration {
           enum "brief" {
             description "Display brief output (default)";
           }
           enum "detail" {
             description "Display detailed output";
           }
         }
       }
       leaf id_addr {
         description "Context identifier address of session";
         type jt:ipprefix;
         mandatory true;
       }
       leaf instance {
         description "Name of IS-IS instance";
         type string;
       }
     }
     output {
       choice output_c {
         case output-tag {
           leaf output {
             type string;
           }
         }
         case actual-tag {
           anyxml isis-context-information;
         }
         case multichassis-tag {
           anyxml multi-routing-engine-results;
         }
       }
     }
   }
   grouping command-forwarding {
     leaf no-forwarding {
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
