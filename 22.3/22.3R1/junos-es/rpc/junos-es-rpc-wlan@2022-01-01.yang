/*
 * Copyright (c) 2022 Juniper Networks, Inc.
 * All rights reserved.
 */
 module junos-es-rpc-wlan {
   namespace "http://yang.juniper.net/junos-es/rpc/wlan";

   prefix wlan;

   import junos-common-types {
     prefix jt;
     revision-date 2022-01-01;
   }

   organization "Juniper Networks, Inc.";

   contact "yang-support@juniper.net";

   description "Junos RPC YANG module for wlan command(s)";

   revision 2022-01-01 {
     description "Junos: 22.3R1.9";
   }

   rpc get-wlan-access-points-list {
     description "Show Wireless LAN access points information";
     input {
       leaf wlan-access-point-name {
         description "Name of the access point";
         type string {
         }
       }
       choice filter {
         case options {
           leaf options {
             type enumeration {
               enum "client-associations" {
                 description "Show access point client associations";
               }
               enum "neighbors" {
                 description "Show access point neighbors";
               }
             }
           }
         }
         case virtual-access-points {
           leaf virtual-access-points {
             description "Show virtual access point information";
             type enumeration {
               enum "all" {
                 description "All VAP";
               }
               enum "0" {
                 description "VAP identifier 0";
               }
               enum "1" {
                 description "VAP identifier 1";
               }
               enum "2" {
                 description "VAP identifier 2";
               }
               enum "3" {
                 description "VAP identifier 3";
               }
               enum "4" {
                 description "VAP identifier 4";
               }
               enum "5" {
                 description "VAP identifier 5";
               }
               enum "6" {
                 description "VAP identifier 6";
               }
               enum "7" {
                 description "VAP identifier 7";
               }
             }
           }
         }
       }
       leaf radio {
         description "Show access point radio information";
         type enumeration {
           enum "1" {
             description "Radio index 1";
           }
           enum "2" {
             description "Radio index 2";
           }
         }
       }
       choice display {
         case detail {
           leaf detail {
             description "Show detailed output";
             type empty;
           }
         }
         case summary {
           leaf summary {
             description "Show summary output";
             type empty;
           }
         }
         case ha {
           leaf ha {
             description "Show Wireless LAN ha status";
             type enumeration {
               enum "status" {
                 description "Ha status";
               }
             }
           }
         }
       }
     }
     output {
       choice output_c {
         case output-tag {
           leaf output {
             type string;
           }
         }
         case actual-tag {
           anyxml wlan-access-points-list;
         }
         case multichassis-tag {
           anyxml multi-routing-engine-results;
         }
       }
     }
   }
   grouping command-forwarding {
     leaf no-forwarding {
       type empty;
     }
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
