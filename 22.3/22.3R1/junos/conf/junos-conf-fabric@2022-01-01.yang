/*
 * Copyright (c) 2022 Juniper Networks, Inc.
 * All rights reserved.
 */
 module junos-conf-fabric {
   namespace "http://yang.juniper.net/junos/conf/fabric";

   prefix jc-fabric;

   import junos-common-types {
     prefix jt;
     revision-date 2022-01-01;
   }

   import junos-conf-root {
     prefix jc;
     revision-date 2022-01-01;
   }

   organization "Juniper Networks, Inc.";

   contact "yang-support@juniper.net";

   description "Junos fabric configuration module";

   revision 2022-01-01 {
     description "Junos: 22.3R1.9";
   }

   augment /jc:configuration {
     uses fabric-group;
   }
   augment /jc:configuration/jc:groups {
     uses fabric-group;
   }
   grouping fabric-group {
     container fabric {
       description "Fabric configuration";
       uses apply-advanced;
       container protocols {
         description "Routing protocol configuration";
         status deprecated;
         uses apply-advanced;
         container bgp {
           description "BGP options";
           uses juniper-protocols-bgp;
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping juniper-protocols-bgp {
     uses apply-advanced;
     container path-selection {
       description "Configure path selection strategy";
       uses apply-advanced;
       leaf l2vpn-use-bgp-rules {
         description "Use standard BGP rules during L2VPN path selection";
         type empty;
       }
       leaf cisco-non-deterministic {
         description "Use Cisco IOS nondeterministic path selection algorithm";
         type empty;
       }
       leaf always-compare-med {
         description "Always compare MED values, regardless of neighbor AS";
         type empty;
       }
       container med-plus-igp {
         presence "enable med-plus-igp";
         description "Add IGP cost to next-hop to MED before comparing MED values";
         uses apply-advanced;
         leaf med-multiplier {
           description "Multiplier for MED";
           default "1";
           type union {
             type string {
               pattern "<.*>|$.*";
             }
             type uint16 {
               range "1 .. 1000";
             }
           }
         }
         leaf igp-multiplier {
           description "Multiplier for IGP cost to next-hop";
           default "1";
           type union {
             type string {
               pattern "<.*>|$.*";
             }
             type uint16 {
               range "1 .. 1000";
             }
           }
         }
       }
       leaf external-router-id {
         description "Compare router ID on BGP externals";
         type empty;
       }
       leaf as-path-ignore {
         description "Ignore AS path comparison during path selection";
         type empty;
       }
     }
     container accept-prpd-connection {
       presence "enable accept-prpd-connection";
       description "Enable BGP to accept PRPD connections";
     }
     leaf advertise-from-main-vpn-tables {
       description "Advertise VPN routes from bgp.Xvpn.0 tables in master instance";
       type empty;
     }
     leaf stale-labels-holddown-period {
       description "Duration (sec) MPLS labels allocated by BGP are kept after they go stale";
       type union {
         type string {
           pattern "<.*>|$.*";
         }
         type int32 {
           range "1 .. 600";
         }
       }
     }
     leaf holddown-all-stale-labels {
       description "Hold all BGP stale-labels, facilating make-before-break for new label advertisements";
       type empty;
     }
     container egress-te-backup-paths {
       description "Backup-path for Egress-TE peer interface failure";
       uses apply-advanced;
       list template {
         key name;
         description "Backup-path template";
         leaf name {
           description "Name of Egress-TE backup path";
           type string {
           }
         }
         uses apply-advanced;
         list peer {
           key name;
           ordered-by user;
           description "Egress peer TE backup exit path";
           leaf name {
             description "Address of BGP peer to use as backup next-hop";
             type jt:ipaddr;
           }
           uses apply-advanced;
         }
         container remote-nexthop {
           description "Resolve and use tunnel to this next-hop as backup path";
           uses apply-advanced;
           leaf remote-nh-addr {
             description "Address of remote-nexthop to use as backup path";
             type jt:ipaddr;
           }
         }
         container ip-forward {
           presence "enable ip-forward";
           description "Use IP-forward backup path for Egress TE";
           uses apply-advanced;
           leaf rti-name {
             description "Routing-instance to use as IP forward backup-path";
             type string {
             }
           }
         }
       }
     }
     leaf sr-preference-override {
       description "Replace received segment routing traffic engineering preference value with override value";
       type union {
         type uint32;
         type string {
           pattern "<.*>|$.*";
         }
       }
     }
     leaf vpn-apply-export {
       description "Apply BGP export policy when exporting VPN routes";
       type empty;
     }
     container family {
       description "Protocol family for NLRIs in updates";
       uses apply-advanced;
       container inet {
         description "IPv4 NLRI parameters";
         uses apply-advanced;
         container labeled-unicast {
           description "Include labeled unicast NLRI";
           presence "enable labeled-unicast";
           uses bgp-afi-labeled;
         }
         container segment-routing-te {
           description "Include segment-routing TE policy";
           presence "enable segment-routing-te";
           uses bgp-afi-srte;
         }
         container transport {
           description "Include Classful Transport NLRI";
           presence "enable transport";
           uses bgp-afi-inet-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow-with-redirect-ip-action;
         }
         container any {
           description "Include unicast or multicast NLRI";
           presence "enable any";
           uses bgp-afi-default;
         }
       }
       container inet-vpn {
         description "IPv4 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow-with-redirect-ip-action;
         }
         container any {
           description "Include unicast or multicast NLRI";
           presence "enable any";
           uses bgp-afi-vpn;
         }
       }
       container inet6 {
         description "IPv6 NLRI parameters";
         uses apply-advanced;
         container labeled-unicast {
           description "Include labeled unicast NLRI";
           presence "enable labeled-unicast";
           uses bgp-afi-inet6-labeled;
         }
         container segment-routing-te {
           description "Include segment-routing TE policy";
           presence "enable segment-routing-te";
           uses bgp-afi-srte;
         }
         container transport {
           description "Include Classful Transport NLRI";
           presence "enable transport";
           uses bgp-afi-inet6-transport;
         }
         container unicast {
           description "Include unicast NLRI";
           presence "enable unicast";
           uses bgp-afi-topo;
         }
         container multicast {
           description "Include multicast NLRI";
           presence "enable multicast";
           uses bgp-afi-default;
         }
         container flow {
           description "Include flow NLRI";
           presence "enable flow";
           uses bgp-afi-flow;
         }
         container any {
           description "Include unicast or multicast NLRI";
           presence "enable any";
           uses bgp-afi-default;
         }
       }
       container inet6-vpn {
         description "IPv6 Layer 3 VPN NLRI parameters";
         uses apply-advanced;
         container unicast {
           description "Include unicast NLRI";
           presence "enable unicast";
           uses bgp-afi-l3vpn;
         }
         container multicast {
           description "Include multicast NLRI";
           presence "enable multicast";
           uses bgp-afi-vpn;
         }
         container flow {
           description "Include flow VPN NLRI";
           presence "enable flow";
           uses bgp-afi-flow;
         }
         container any {
           description "Include unicast or multicast NLRI";
           presence "enable any";
           uses bgp-afi-vpn;
         }
       }
       container iso-vpn {
         description "ISO Layer 3 VPN NLRI parameters";
         uses apply-advanced;
         container unicast {
           description "Include unicast NLRI";
           presence "enable unicast";
           uses bgp-afi-vpn-protection;
         }
       }
       container l2vpn {
         description "MPLS-based Layer 2 VPN and VPLS NLRI parameters";
         uses apply-advanced;
         container auto-discovery-only {
           description "Include auto-discovery NLRI for LDP Layer 2 VPN and VPLS";
           presence "enable auto-discovery-only";
           uses bgp-afi-default;
         }
         container auto-discovery-mspw {
           description "Include auto-discovery NLRI for LDP Signalled MultiSegment PW";
           presence "enable auto-discovery-mspw";
           uses bgp-afi-default;
         }
         container signaling {
           description "Include Layer 2 VPN and VPLS signaling NLRI";
           presence "enable signaling";
           uses bgp-afi-l2vpn;
         }
       }
       container evpn {
         description "EVPN NLRI parameters";
         uses apply-advanced;
         container signaling {
           description "Include EVPN signaling NLRI";
           presence "enable signaling";
           uses bgp-afi-default;
         }
       }
       container inet-mvpn {
         description "IPv4 MVPN NLRI parameters";
         uses apply-advanced;
         container signaling {
           description "Include IPv4 multicast VPN signaling NLRI";
           presence "enable signaling";
           uses bgp-afi-default;
         }
       }
       container inet6-mvpn {
         description "IPv6 MVPN NLRI parameters";
         uses apply-advanced;
         container signaling {
           description "Include IPv6 multicast VPN signaling NLRI";
           presence "enable signaling";
           uses bgp-afi-default;
         }
       }
       container inet-mdt {
         description "IPv4 Multicast Distribution Tree (MDT) NLRI parameters";
         uses apply-advanced;
         container signaling {
           description "Include IPv4 multicast VPN auto-discovery NLRI";
           presence "enable signaling";
           uses bgp-afi-default;
         }
       }
       container traffic-engineering {
         description "Traffic Engineering (BGP-TE) NLRI parameters";
         uses apply-advanced;
         container unicast {
           description "Include BGP-TE NLRI";
           presence "enable unicast";
           uses bgp-afi-default;
         }
       }
       container route-target {
         presence "enable route-target";
         description "Route target NLRI used for VPN route filtering";
         uses apply-advanced;
         container prefix-limit {
           description "Limit maximum number of prefixes from a peer";
           uses bgpaf-prefix-limit;
         }
         container accepted-prefix-limit {
           description "Limit maximum number of prefixes accepted from a peer";
           uses bgpaf-accepted-prefix-limit;
         }
         container proxy-generate {
           presence "enable proxy-generate";
           description "Generate route target NLRI for peers that don't support it";
           uses apply-advanced;
           leaf-list route-target-policy {
             ordered-by user;
             description "Limit VPN routes that are used to generate proxy route-target filters";
             type jt:policy-algebra;
           }
         }
         leaf external-paths {
           description "Number of external paths accepted for route filtering";
           type union {
             type string {
               pattern "<.*>|$.*";
             }
             type uint32 {
               range "1 .. 256";
             }
           }
         }
         leaf advertise-default {
           description "Advertise default and suppress more specific routes";
           type empty;
         }
         leaf damping {
           description "Enable route flap damping";
           type empty;
         }
         container graceful-restart {
           description "BGP graceful restart options";
           uses bgp-af-gr;
         }
         leaf local-ipv4-address {
           description "Local IPv4 address";
           type jt:ipv4addr;
         }
         container output-queue-priority {
           description "Default output-queue to assign updates to";
           uses bgp-output-queue-priority-class;
         }
         container route-refresh-priority {
           description "Default output-queue to assign route refreshes to";
           uses bgp-output-queue-priority-class;
         }
         container withdraw-priority {
           description "Default output-queue to assign withdrawn routes to";
           uses bgp-output-queue-priority-class;
         }
       }
       container fabric {
         description "Fabric NLRI parameters";
         status deprecated;
         uses apply-advanced;
         container unicast {
           description "Include unicast NLRI";
           presence "enable unicast";
           uses bgp-afi-default;
         }
       }
       container bridge {
         description "Bridge NLRI parameters";
         status deprecated;
         uses apply-advanced;
         container unicast {
           description "Include unicast NLRI";
           presence "enable unicast";
           uses bgp-afi-default;
         }
       }
       container bridge-vpn {
         description "Bridge VPN NLRI parameters";
         status deprecated;
         uses apply-advanced;
         container unicast {
           description "Include unicast NLRI";
           presence "enable unicast";
           uses bgp-afi-vpn;
         }
       }
       container fabric-vpn {
         description "Fabric VPN NLRI parameters";
         status deprecated;
         uses apply-advanced;
         container unicast {
           description "Include unicast NLRI";
           presence "enable unicast";
           uses bgp-afi-vpn;
         }
       }
       container inet-bgpmcast {
         description "IPv4 BGPMCAST NLRI parameters";
         uses apply-advanced;
         container signaling {
           description "Include IPv4 BGP multicast signaling NLRI";
           presence "enable signaling";
           uses bgp-afi-default;
         }
       }
       container inet6-bgpmcast {
         description "IPv6 BGPMCAST NLRI parameters";
         uses apply-advanced;
         container signaling {
           description "Include IPv6 BGP multicast signaling NLRI";
           presence "enable signaling";
           uses bgp-afi-default;
         }
       }
     }
     container egress-te {
       presence "enable egress-te";
       description "Use Egress Peering traffic engineering";
       uses apply-advanced;
       leaf install-address {
         description "Address to use in egress-te created inet route";
         type jt:ipaddr;
       }
       container rib {
         description "Select primary table for Egress-TE routes";
         uses apply-advanced;
         leaf inet.0 {
           description "Install Egress-TE routes in inet.0";
           type empty;
         }
         leaf inet6.0 {
           description "Install Egress-TE routes in inet6.0";
           type empty;
         }
       }
       leaf no-install {
         description "Avoid installation to FIB or resolving over";
         type empty;
       }
       leaf-list import {
         ordered-by user;
         description "Import policy to set attributes";
         type jt:policy-algebra;
       }
       leaf backup-path {
         description "The 'egress-te-backup-paths template' to use for this peer";
         type string {
         }
       }
     }
     leaf advertise-prefix-sid {
       description "Advertise prefix sid to E-BGP peers";
       type empty;
     }
     leaf accept-prefix-sid {
       description "Accept prefix sid from E-BGP peers";
       type empty;
     }
     leaf advertise-srgb {
       description "Advertise SRGB TLV";
       type empty;
     }
     leaf tcp-connect-port {
       description "TCP port number to connect with peer on";
       type union {
         type string {
           pattern "<.*>|$.*";
         }
         type uint16 {
           range "1 .. 65535";
         }
       }
     }
     leaf egress-te-sid-stats {
       description "Create BGP-Peer-SID sensor";
       type empty;
     }
     list egress-te-set-segment {
       key name;
       ordered-by user;
       description "Configure BGP-Peer-Set segment";
       leaf name {
         description "The BGP-Peer-Set segment name";
         type string {
         }
       }
       uses apply-advanced;
       container label {
         description "BGP-Peer-Set SID label from static label pool";
         uses apply-advanced;
         leaf label-value {
           description "BGP-Peer-Set SID label value from static label pool";
           type union {
             type string {
               pattern "<.*>|$.*";
             }
             type uint32 {
               range "16 .. 1048575";
             }
           }
         }
       }
       container egress-te-backup-segment {
         description "Backup segment for FRR";
         uses apply-advanced;
         container label {
           description "Backup segment label from static label pool";
           uses apply-advanced;
           leaf label-value {
             description "Backup segment label value from static label pool";
             type union {
               type string {
                 pattern "<.*>|$.*";
               }
               type uint32 {
                 range "16 .. 1048575";
               }
             }
           }
         }
       }
       container egress-te-backup-ip-forward {
         presence "enable egress-te-backup-ip-forward";
         description "Use IP-forward backup path for Egress TE";
         uses apply-advanced;
         leaf instance-name {
           description "Routing-instance to use as IP forward backup-path";
           type string {
           }
         }
       }
     }
     list group {
       key name;
       ordered-by user;
       description "Define a peer group";
       leaf name {
         description "Group name";
         type string;
       }
       uses apply-advanced;
       leaf type {
         description "Type of peer group";
         type enumeration {
           enum "internal" {
             description "IBGP group";
           }
           enum "external" {
             description "EBGP group";
           }
         }
       }
       leaf protocol {
         description "IGP to use to resolve the next hop";
         status deprecated;
         type enumeration {
           enum "rip" {
             description "Use RIP to resolve the BGP next hop";
             status deprecated;
           }
           enum "ospf" {
             description "Use OSPF to resolve the BGP next hop";
             status deprecated;
           }
           enum "isis" {
             description "Use IS-IS to resolve the BGP next hop";
             status deprecated;
           }
         }
       }
       container traceoptions {
         description "Trace options for BGP";
         uses apply-advanced;
         container file {
           description "Trace file options";
           leaf filename {
             description "Name of file in which to write trace information";
             type string {
               length "1 .. 1024";
             }
           }
           leaf replace {
             description "Replace trace file rather than appending to it";
             status deprecated;
             type empty;
           }
           leaf size {
             description "Maximum trace file size";
             type string;
           }
           leaf files {
             description "Maximum number of trace files";
             default "10";
             type union {
               type string {
                 pattern "<.*>|$.*";
               }
               type uint32 {
                 range "2 .. 1000";
               }
             }
           }
           leaf no-stamp {
             description "Do not timestamp trace file";
             status deprecated;
             type empty;
           }
           choice world-readable-choice {
             leaf world-readable {
               description "Allow any user to read the log file";
               type empty;
             }
             leaf no-world-readable {
               description "Don't allow any user to read the log file";
               type empty;
             }
           }
         }
         list flag {
           key name;
           ordered-by user;
           description "Tracing parameters";
           leaf name {
             type enumeration {
               enum "damping" {
                 description "Trace BGP damping information";
               }
               enum "packets" {
                 description "Trace all BGP protocol packets";
               }
               enum "open" {
                 description "Trace BGP open packets";
               }
               enum "update" {
                 description "Trace BGP update packets";
               }
               enum "keepalive" {
                 description "Trace BGP keepalive packets";
               }
               enum "refresh" {
                 description "Trace BGP refresh packets";
               }
               enum "nsr-synchronization" {
                 description "Trace NSR synchronization events";
               }
               enum "bfd" {
                 description "Trace BFD events";
               }
               enum "4byte-as" {
                 description "Trace 4 byte AS events";
               }
               enum "add-path" {
                 description "Trace add-path events";
               }
               enum "graceful-restart" {
                 description "Trace Graceful Restart events";
               }
               enum "egress-te" {
                 description "Egress Peering Traffic-Engineering events";
               }
               enum "thread-io" {
                 description "Trace threaded I/O processing";
               }
               enum "sharding" {
                 description "Trace BGP rib sharding";
               }
               enum "thread-update-io" {
                 description "Trace threaded update I/O processing";
               }
               enum "route-validation" {
                 description "Trace route validation";
               }
               enum "ipsec" {
                 description "Trace ipsec";
               }
               enum "route" {
                 description "Trace routing information";
               }
               enum "normal" {
                 description "Trace normal events";
               }
               enum "general" {
                 description "Trace general events";
               }
               enum "state" {
                 description "Trace state transitions";
               }
               enum "policy" {
                 description "Trace policy processing";
               }
               enum "task" {
                 description "Trace routing protocol task processing";
               }
               enum "timer" {
                 description "Trace routing protocol timer processing";
               }
               enum "all" {
                 description "Trace everything";
               }
             }
           }
           leaf send {
             description "Trace transmitted packets";
             type empty;
           }
           leaf receive {
             description "Trace received packets";
             type empty;
           }
           leaf detail {
             description "Trace detailed information";
             type empty;
           }
           leaf disable {
             description "Disable this trace flag";
             type empty;
           }
           container filter {
             description "Filter to apply to this flag";
             presence "enable filter";
             uses bgp_filter_obj;
           }
         }
       }
       leaf description {
         description "Text description";
         type string {
           length "1 .. 255";
         }
       }
       container metric-out {
         description "Route metric sent in MED";
         choice metric_param {
           case case_1 {
             leaf metric-value {
               description "Metric value";
               type union {
                 type string {
                   pattern "<.*>|$.*";
                 }
                 type uint32 {
                   range "0 .. 4294967295";
                 }
               }
             }
           }
           case case_2 {
             container minimum-igp {
               presence "enable minimum-igp";
               description "Track the minimum IGP metric";
               leaf metric-offset {
                 description "Metric offset for MED";
                 type union {
                   type int32;
                   type string {
                     pattern "<.*>|$.*";
                   }
                 }
               }
             }
           }
           case case_3 {
             container igp {
               presence "enable igp";
               description "Track the IGP metric";
               leaf metric-offset {
                 description "Metric offset for MED";
                 type union {
                   type int32;
                   type string {
                     pattern "<.*>|$.*";
                   }
                 }
               }
               leaf delay-med-update {
                 description "Delay updating MED when IGP metric increases";
                 type empty;
               }
             }
           }
           case case_4 {
             container effective-aigp {
               presence "enable effective-aigp";
               description "Track the effective AIGP metric";
               leaf metric-offset {
                 description "Metric offset for MED";
                 type union {
                   type int32;
                   type string {
                     pattern "<.*>|$.*";
                   }
                 }
               }
             }
           }
           case case_5 {
             container minimum-effective-aigp {
               presence "enable minimum-effective-aigp";
               description "Track the minimum effective AIGP metric";
               leaf metric-offset {
                 description "Metric offset for MED";
                 type union {
                   type int32;
                   type string {
                     pattern "<.*>|$.*";
                   }
                 }
               }
             }
           }
         }
       }
       container multihop {
         presence "enable multihop";
         description "Configure an EBGP multihop session";
         uses apply-advanced;
         leaf ttl {
           description "TTL value for the session";
           type union {
             type string {
               pattern "<.*>|$.*";
             }
             type uint8 {
               range "1 .. 255";
             }
           }
         }
         leaf no-nexthop-change {
           description "Do not change next hop to self in advertisements";
           type empty;
         }
       }
       container ebgp-community-cleanup {
         presence "enable ebgp-community-cleanup";
         description "Community specific cleanup for eBGP peers";
         uses apply-advanced;
         leaf origin-validation {
           description "Origin Validation State receive behavior";
           type enumeration {
             enum "accept" {
               description "Accept Origin Validation State Community";
             }
             enum "reject" {
               description "Reject Origin Validation State Community";
             }
           }
         }
       }
       leaf route-server-client {
         description "Enable route server client behavior";
         type empty;
       }
       leaf accept-remote-nexthop {
         description "Allow import policy to specify a non-directly connected next-hop";
         type empty;
       }
       leaf preference {
         description "Preference value";
         type union {
           type uint32;
           type string {
             pattern "<.*>|$.*";
           }
         }
       }
       leaf local-preference {
         description "Value of LOCAL_PREF path attribute";
         type union {
           type uint32;
           type string {
             pattern "<.*>|$.*";
           }
         }
       }
       leaf local-address {
         description "Address of local end of BGP session";
         type jt:ipaddr;
       }
       leaf local-interface {
         description "Local interface for IPv6 link local EBGP peering";
         type union {
           type jt:interface-name;
           type string {
             pattern "<.*>|$.*";
           }
         }
       }
       leaf forwarding-context {
         description "Routing-instance used for data-forwarding and transport-session";
         type string {
         }
       }
       leaf hold-time {
         description "Hold time used when negotiating with a peer";
         type union {
           type string {
             pattern "<.*>|$.*";
           }
           type uint32 {
             range "0 .. 65535";
           }
         }
       }
       leaf minimum-hold-time {
         description "Minimum hold time accepted from the peer";
         type union {
           type string {
             pattern "<.*>|$.*";
           }
           type uint32 {
             range "3 .. 65535";
           }
         }
       }
       leaf passive {
         description "Do not send open messages to a peer";
         type empty;
       }
       leaf advertise-inactive {
         description "Advertise inactive routes";
         type empty;
       }
       choice advertise-peer-as-choice {
         leaf advertise-peer-as {
           description "Advertise routes received from the same autonomous system";
           type empty;
         }
         leaf no-advertise-peer-as {
           description "Don't advertise routes received from the same autonomous system";
           type empty;
         }
       }
       container advertise-external {
         presence "enable advertise-external";
         description "Advertise best external routes";
         leaf conditional {
           description "Route matches active route upto med-comparison rule";
           type empty;
         }
       }
       leaf keep {
         description "How to retain routes in the routing table";
         type enumeration {
           enum "all" {
             description "Retain all routes";
           }
           enum "none" {
             description "Retain no routes";
           }
         }
       }
       leaf rfc6514-compliant-safi129 {
         description "Compliant with RFC6514 SAFI129 format";
         type empty;
       }
       leaf no-aggregator-id {
         description "Set router ID in aggregator path attribute to 0";
         type empty;
       }
       leaf mtu-discovery {
         description "Enable TCP path MTU discovery";
         type empty;
       }
       leaf enforce-first-as {
         description "Enforce first AS in AS-path is the neighbor's AS";
         type empty;
       }
       leaf out-delay {
         description "How long before exporting routes from routing table";
         type union {
           type string {
             pattern "<.*>|$.*";
           }
           type uint32 {
             range "0 .. 65535";
           }
         }
       }
       leaf ttl {
         description "TTL value for the single-hop peer";
         type enumeration {
           enum "1" {
           }
           enum "255" {
           }
         }
       }
       leaf log-updown {
         description "Log a message for peer state transitions";
         type empty;
       }
       leaf damping {
         description "Enable route flap damping";
         type empty;
       }
       leaf-list import {
         ordered-by user;
         description "Import policy";
         type jt:policy-algebra;
       }
       leaf-list nlri {
         ordered-by user;
         description "NLRI type to include in updates";
         status deprecated;
         type enumeration {
           enum "unicast" {
             description "Include unicast NLRI";
             status deprecated;
           }
           enum "multicast" {
             description "Include multicast NLRI";
             status deprecated;
           }
           enum "any" {
             description "Include any kind of NLRI";
             status deprecated;
           }
         }
       }
       container bgp-error-tolerance {
         presence "enable bgp-error-tolerance";
         description "Handle BGP malformed updates softly";
         uses apply-advanced;
         leaf malformed-update-log-interval {
           description "Time used when logging malformed update";
           default "300";
           units "seconds";
           type union {
             type string {
               pattern "<.*>|$.*";
             }
             type uint32 {
               range "10 .. 65535";
             }
           }
         }
         choice malformed-routes-limit-choice {
           case case_1 {
             leaf malformed-route-limit {
               description "Maximum number of malformed routes from a peer";
               default "1000";
               type union {
                 type string {
                   pattern "<.*>|$.*";
                 }
                 type uint32 {
                   range "0 .. 4294967295";
                 }
               }
             }
           }
           case case_2 {
             leaf no-malformed-route-limit {
               description "No malformed route limit";
               type empty;
             }
           }
         }
       }
       container family {
         description "Protocol family for NLRIs in updates";
         uses apply-advanced;
         container inet {
           description "IPv4 NLRI parameters";
           uses apply-advanced;
           container labeled-unicast {
             description "Include labeled unicast NLRI";
             presence "enable labeled-unicast";
             uses bgp-afi-labeled;
           }
           container segment-routing-te {
             description "Include segment-routing TE policy";
             presence "enable segment-routing-te";
             uses bgp-afi-srte;
           }
           container transport {
             description "Include Classful Transport NLRI";
             presence "enable transport";
             uses bgp-afi-inet-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow-with-redirect-ip-action;
           }
           container any {
             description "Include unicast or multicast NLRI";
             presence "enable any";
             uses bgp-afi-default;
           }
         }
         container inet-vpn {
           description "IPv4 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow-with-redirect-ip-action;
           }
           container any {
             description "Include unicast or multicast NLRI";
             presence "enable any";
             uses bgp-afi-vpn;
           }
         }
         container inet6 {
           description "IPv6 NLRI parameters";
           uses apply-advanced;
           container labeled-unicast {
             description "Include labeled unicast NLRI";
             presence "enable labeled-unicast";
             uses bgp-afi-inet6-labeled;
           }
           container segment-routing-te {
             description "Include segment-routing TE policy";
             presence "enable segment-routing-te";
             uses bgp-afi-srte;
           }
           container transport {
             description "Include Classful Transport NLRI";
             presence "enable transport";
             uses bgp-afi-inet6-transport;
           }
           container unicast {
             description "Include unicast NLRI";
             presence "enable unicast";
             uses bgp-afi-topo;
           }
           container multicast {
             description "Include multicast NLRI";
             presence "enable multicast";
             uses bgp-afi-default;
           }
           container flow {
             description "Include flow NLRI";
             presence "enable flow";
             uses bgp-afi-flow;
           }
           container any {
             description "Include unicast or multicast NLRI";
             presence "enable any";
             uses bgp-afi-default;
           }
         }
         container inet6-vpn {
           description "IPv6 Layer 3 VPN NLRI parameters";
           uses apply-advanced;
           container unicast {
             description "Include unicast NLRI";
             presence "enable unicast";
             uses bgp-afi-l3vpn;
           }
           container multicast {
             description "Include multicast NLRI";
             presence "enable multicast";
             uses bgp-afi-vpn;
           }
           container flow {
             description "Include flow VPN NLRI";
             presence "enable flow";
             uses bgp-afi-flow;
           }
           container any {
             description "Include unicast or multicast NLRI";
             presence "enable any";
             uses bgp-afi-vpn;
           }
         }
         container iso-vpn {
           description "ISO Layer 3 VPN NLRI parameters";
           uses apply-advanced;
           container unicast {
             description "Include unicast NLRI";
             presence "enable unicast";
             uses bgp-afi-vpn-protection;
           }
         }
         container l2vpn {
           description "MPLS-based Layer 2 VPN and VPLS NLRI parameters";
           uses apply-advanced;
           container auto-discovery-only {
             description "Include auto-discovery NLRI for LDP Layer 2 VPN and VPLS";
             presence "enable auto-discovery-only";
             uses bgp-afi-default;
           }
           container auto-discovery-mspw {
             description "Include auto-discovery NLRI for LDP Signalled MultiSegment PW";
             presence "enable auto-discovery-mspw";
             uses bgp-afi-default;
           }
           container signaling {
             description "Include Layer 2 VPN and VPLS signaling NLRI";
             presence "enable signaling";
             uses bgp-afi-l2vpn;
           }
         }
         container evpn {
           description "EVPN NLRI parameters";
           uses apply-advanced;
           container signaling {
             description "Include EVPN signaling NLRI";
             presence "enable signaling";
             uses bgp-afi-default;
           }
         }
         container inet-mvpn {
           description "IPv4 MVPN NLRI parameters";
           uses apply-advanced;
           container signaling {
             description "Include IPv4 multicast VPN signaling NLRI";
             presence "enable signaling";
             uses bgp-afi-default;
           }
         }
         container inet6-mvpn {
           description "IPv6 MVPN NLRI parameters";
           uses apply-advanced;
           container signaling {
             description "Include IPv6 multicast VPN signaling NLRI";
             presence "enable signaling";
             uses bgp-afi-default;
           }
         }
         container inet-mdt {
           description "IPv4 Multicast Distribution Tree (MDT) NLRI parameters";
           uses apply-advanced;
           container signaling {
             description "Include IPv4 multicast VPN auto-discovery NLRI";
             presence "enable signaling";
             uses bgp-afi-default;
           }
         }
         container traffic-engineering {
           description "Traffic Engineering (BGP-TE) NLRI parameters";
           uses apply-advanced;
           container unicast {
             description "Include BGP-TE NLRI";
             presence "enable unicast";
             uses bgp-afi-default;
           }
         }
         container route-target {
           presence "enable route-target";
           description "Route target NLRI used for VPN route filtering";
           uses apply-advanced;
           container prefix-limit {
             description "Limit maximum number of prefixes from a peer";
             uses bgpaf-prefix-limit;
           }
           container accepted-prefix-limit {
             description "Limit maximum number of prefixes accepted from a peer";
             uses bgpaf-accepted-prefix-limit;
           }
           container proxy-generate {
             presence "enable proxy-generate";
             description "Generate route target NLRI for peers that don't support it";
             uses apply-advanced;
             leaf-list route-target-policy {
               ordered-by user;
               description "Limit VPN routes that are used to generate proxy route-target filters";
               type jt:policy-algebra;
             }
           }
           leaf external-paths {
             description "Number of external paths accepted for route filtering";
             type union {
               type string {
                 pattern "<.*>|$.*";
               }
               type uint32 {
                 range "1 .. 256";
               }
             }
           }
           leaf advertise-default {
             description "Advertise default and suppress more specific routes";
             type empty;
           }
           leaf damping {
             description "Enable route flap damping";
             type empty;
           }
           container graceful-restart {
             description "BGP graceful restart options";
             uses bgp-af-gr;
           }
           leaf local-ipv4-address {
             description "Local IPv4 address";
             type jt:ipv4addr;
           }
           container output-queue-priority {
             description "Default output-queue to assign updates to";
             uses bgp-output-queue-priority-class;
           }
           container route-refresh-priority {
             description "Default output-queue to assign route refreshes to";
             uses bgp-output-queue-priority-class;
           }
           container withdraw-priority {
             description "Default output-queue to assign withdrawn routes to";
             uses bgp-output-queue-priority-class;
           }
         }
         container fabric {
           description "Fabric NLRI parameters";
           status deprecated;
           uses apply-advanced;
           container unicast {
             description "Include unicast NLRI";
             presence "enable unicast";
             uses bgp-afi-default;
           }
         }
         container bridge {
           description "Bridge NLRI parameters";
           status deprecated;
           uses apply-advanced;
           container unicast {
             description "Include unicast NLRI";
             presence "enable unicast";
             uses bgp-afi-default;
           }
         }
         container bridge-vpn {
           description "Bridge VPN NLRI parameters";
           status deprecated;
           uses apply-advanced;
           container unicast {
             description "Include unicast NLRI";
             presence "enable unicast";
             uses bgp-afi-vpn;
           }
         }
         container fabric-vpn {
           description "Fabric VPN NLRI parameters";
           status deprecated;
           uses apply-advanced;
           container unicast {
             description "Include unicast NLRI";
             presence "enable unicast";
             uses bgp-afi-vpn;
           }
         }
         container inet-bgpmcast {
           description "IPv4 BGPMCAST NLRI parameters";
           uses apply-advanced;
           container signaling {
             description "Include IPv4 BGP multicast signaling NLRI";
             presence "enable signaling";
             uses bgp-afi-default;
           }
         }
         container inet6-bgpmcast {
           description "IPv6 BGPMCAST NLRI parameters";
           uses apply-advanced;
           container signaling {
             description "Include IPv6 BGP multicast signaling NLRI";
             presence "enable signaling";
             uses bgp-afi-default;
           }
         }
       }
       leaf authentication-key {
         description "MD5 authentication key";
         type string {
           length "1 .. 126";
         }
       }
       leaf authentication-algorithm {
         description "Authentication algorithm name";
         type enumeration {
           enum "md5" {
             description "Message Digest 5";
           }
           enum "hmac-sha-1-96" {
             description "Hash-based Message Authentication Code (SHA1) (96 bits)";
           }
           enum "aes-128-cmac-96" {
             description "Cipher-based Message Authentication Code (AES128) (96 bits)";
           }
           enum "ao" {
             description "TCP Authentication Option";
           }
         }
       }
       leaf tcpao-auth-mismatch {
         description "Continue without TCP-AO if any one TCP endpoint does not have TCP-AO configured";
         type enumeration {
           enum "allow-without-tcpao" {
             description "Allow the connection establishment without TCP-AO";
           }
         }
       }
       leaf authentication-key-chain {
         description "Key chain name";
         type string {
           length "1 .. 128";
         }
       }
       leaf-list export {
         ordered-by user;
         description "Export policy";
         type jt:policy-algebra;
       }
       container remove-private {
         presence "enable remove-private";
         description "Remove well-known private AS numbers";
         uses apply-advanced;
         container all {
           presence "enable all";
           description "Remove all private AS numbers and do not stop at the first public AS number";
           container replace {
             presence "enable replace";
             description "Replace private AS numbers with the BGP Group's local AS number";
             leaf nearest {
               description "Use closest public AS number to replace a private AS number";
               type empty;
             }
           }
         }
         leaf no-peer-loop-check {
           description "Remove peer loop-check";
           type empty;
         }
       }
       leaf cluster {
         description "Cluster identifier";
         type jt:areaid;
       }
       leaf no-client-reflect {
         description "Disable intracluster route redistribution";
         type empty;
       }
       leaf peer-as {
         description " Autonomous system number in plain number or 'higher 16bits'.'Lower 16 bits' (asdot notation) format";
         type string {
         }
       }
       container local-as {
         description "Local autonomous system number";
         leaf as-number {
           description " Autonomous system number in plain number or 'higher 16bits'.'Lower 16 bits' (asdot notation) format";
           type string {
           }
         }
         leaf loops {
           description "Maximum number of times this AS can be in an AS path";
           type union {
             type string {
               pattern "<.*>|$.*";
             }
             type int32 {
               range "1 .. 10";
             }
           }
         }
         leaf private {
           description "Hide this local AS in paths learned from this peering";
           type empty;
         }
         leaf alias {
           description "Treat this AS as an alias to the system AS";
           type empty;
         }
         leaf no-prepend-global-as {
           description "Do not prepend global autonomous-system number in advertised paths";
           type empty;
         }
       }
       leaf ipsec-sa {
         description "IPSec SA name";
         type string {
           length "1 .. 32";
         }
       }
       container graceful-shutdown {
         description "BGP peer graceful shutdown option";
         uses apply-advanced;
         container receiver {
           presence "enable receiver";
           description "BGP peer graceful-shutdown receiver";
           uses apply-advanced;
           leaf disable {
             description "Disable graceful-shutdown receiver";
             type empty;
           }
           leaf local-preference {
             description "Value of receiver LOCAL_PREF path attribute";
             type union {
               type uint32;
               type string {
                 pattern "<.*>|$.*";
               }
             }
           }
         }
         container sender {
           presence "enable sender";
           description "BGP peer graceful-shutdown sender";
           uses apply-advanced;
           leaf local-preference {
             description "Value of sender LOCAL_PREF path attribute";
             type union {
               type uint32;
               type string {
                 pattern "<.*>|$.*";
               }
             }
           }
         }
       }
       container shutdown {
         presence "enable shutdown";
         description "Shutdown";
         uses apply-advanced;
         leaf notify-message {
           description "Notification message";
           type string;
         }
       }
       leaf unconfigured-peer-graceful-restart {
         description "BGP unconfigured peer graceful restart options";
         type empty;
       }
       container graceful-restart {
         presence "enable graceful-restart";
         description "BGP graceful restart options";
         uses apply-advanced;
         choice enable-disable {
           case case_1 {
             leaf disable {
               description "Disable graceful restart";
               type empty;
             }
           }
         }
         leaf restart-time {
           description "Restart time used when negotiating with a peer";
           type union {
             type string {
               pattern "<.*>|$.*";
             }
             type uint32 {
               range "1 .. 1800";
             }
           }
         }
         leaf stale-routes-time {
           description "Maximum time for which stale routes are kept";
           type union {
             type string {
               pattern "<.*>|$.*";
             }
             type uint32 {
               range "1 .. 1800";
             }
           }
         }
         container long-lived {
           description "Long-lived graceful restart options";
           uses apply-advanced;
           container receiver {
             description "Long-lived graceful restart receiver (helper) options";
             uses apply-advanced;
             choice enable-disable {
               case case_1 {
                 leaf disable {
                   description "Disable receiver (helper) functionality";
                   type empty;
                 }
               }
             }
           }
           container advertise-to-non-llgr-neighbor {
             presence "enable advertise-to-non-llgr-neighbor";
             description "Advertise stale routes to non-LLGR neighbors";
             uses apply-advanced;
             leaf omit-no-export {
               description "Do not attach no-export community to stale routes";
               type empty;
             }
           }
         }
         leaf disable-notification-extensions {
           description "Disable notification extensions";
           type empty;
         }
         leaf forwarding-state-bit {
           description "Control forwarding-state flag negotiation";
           type enumeration {
             enum "as-rr-client" {
               description "As for a route reflector client";
             }
             enum "from-fib" {
               description "Always use state of associated FIB(s)";
             }
           }
         }
         leaf dont-help-shared-fate-bfd-down {
           description "Honor BFD-Down(C=0) if GR-restart not in progress";
           type empty;
         }
       }
       leaf include-mp-next-hop {
         description "Include NEXT-HOP attribute in multiprotocol updates";
         type empty;
       }
       leaf disable-4byte-as {
         description "Disable 4 byte AS capability advertisement";
         type empty;
       }
       container idle-after-switch-over {
         description "Stop peer session from coming up after nonstop-routing switch-over";
         choice idle-interval {
           case case_1 {
             leaf forever {
               description "Idle the peer until the user intervenes";
               type empty;
             }
           }
           case case_2 {
             leaf timeout {
               description "Timeout value, in seconds, for starting peer after switch over";
               type union {
                 type string {
                   pattern "<.*>|$.*";
                 }
                 type uint32 {
                   range "1 .. 4294967295";
                 }
               }
             }
           }
         }
       }
       container outbound-route-filter {
         description "Dynamically negotiated cooperative route filtering";
         uses apply-advanced;
         leaf bgp-orf-cisco-mode {
           description "Using BGP ORF capability code 130 and Prefix ORF type 128";
           type empty;
         }
         container extended-community {
           description "Extended community filtering";
           status deprecated;
           uses apply-advanced;
           choice accept-choice {
             leaf accept {
               description "Honor remote requests for extended community ORF";
               type empty;
             }
             leaf no-accept {
               description "Don't honor remote requests for extended community ORF";
               type empty;
             }
           }
           leaf vrf-filter {
             description "Request remote filtering using locally configured VRF import targets";
             type empty;
           }
         }
         container prefix-based {
           presence "enable prefix-based";
           description "Prefix-based outbound route filtering";
           uses apply-advanced;
           container accept {
             presence "enable accept";
             description "Honor Prefix-based ORFs from remote peers";
             uses apply-advanced;
             leaf inet {
               description "Honor IPv4 prefix filters";
               type empty;
             }
             leaf inet6 {
               description "Honor IPv6 prefix filters";
               type empty;
             }
           }
         }
       }
       container message-batching {
         description "DEPRECATED - Batching of outgoing messages";
         status deprecated;
         uses apply-advanced;
         choice enable-disable {
           case case_1 {
             leaf enable {
               description "Enable parameter";
               type empty;
             }
           }
           case case_2 {
             leaf disable {
               description "Disable parameter";
               type empty;
             }
           }
         }
         leaf interval {
           description "DEPRECATED - Interval over which to batch messages";
           default "250";
           units "milliseconds";
           type union {
             type string {
               pattern "<.*>|$.*";
             }
             type uint32 {
               range "100 .. 1000";
             }
           }
         }
       }
       container multipath {
         presence "enable multipath";
         description "Allow load sharing among multiple BGP paths";
         uses apply-advanced;
         leaf disable {
           description "Disable Multipath";
           type empty;
         }
         leaf multiple-as {
           description "Use paths received from different ASs";
           type empty;
         }
         leaf allow-protection {
           description "Allow protection for multipath legs";
           type empty;
         }
         leaf pause-computation-during-churn {
           description "Pause multipath job to absorb churn";
           type empty;
         }
         leaf list-nexthop {
           description "Use List-NH for homogenous nexthop-set also";
           type empty;
         }
       }
       leaf tcp-mss {
         description "Maximum TCP segment size";
         type union {
           type string {
             pattern "<.*>|$.*";
           }
           type uint32 {
             range "1 .. 4096";
           }
         }
       }
       leaf bgp-identifier {
         description "BGP Identifier";
         type jt:ipv4addr;
       }
       leaf tcp-aggressive-transmission {
         description "Enable aggressive transmission of pure TCP ACKs and retransmissions";
         type empty;
       }
       container bmp {
         description "Specific settings to override the routing-options settings";
         uses apply-advanced;
         leaf monitor {
           description "Enable/Disable monitoring";
           type enumeration {
             enum "enable" {
               description "Enable monitoring of BGP peer(s)";
             }
             enum "disable" {
               description "Disable monitoring of BGP peer(s)";
             }
           }
         }
         container route-monitoring {
           description "Control route monitoring settings";
           uses apply-advanced;
           leaf none {
             description "Do not send route monitoring messages";
             type empty;
           }
           container pre-policy {
             presence "enable pre-policy";
             description "Send pre-policy route monitoring messages";
             leaf exclude-non-feasible {
               description "Exclude looped routes, etc";
               type empty;
             }
           }
           container post-policy {
             presence "enable post-policy";
             description "Send post-policy route monitoring messages";
             leaf exclude-non-eligible {
               description "Exclude unresolved routes, etc.";
               type empty;
             }
           }
           container rib-out {
             presence "enable rib-out";
             description "Send adj-ribs-out route monitoring messages";
             leaf pre-policy {
               description "Send pre-policy adj-ribs-out route monitoring messages";
               type empty;
             }
             leaf post-policy {
               description "Send post-policy adj-ribs-out route monitoring messages";
               type empty;
             }
           }
         }
       }
       container advertise-bgp-static {
         presence "enable advertise-bgp-static";
         description "Advertise bgp-static routes";
         uses apply-advanced;
         leaf-list policy {
           ordered-by user;
           description "Static route advertisement policy";
           type jt:policy-algebra;
         }
       }
       leaf add-path-display-ipv4-address {
         description "Display add-path path-id in IPv4 address format";
         type empty;
       }
       container bfd-liveness-detection {
         description "Bidirectional Forwarding Detection (BFD) options";
         uses apply-advanced;
         leaf version {
           description "BFD protocol version number";
           default "automatic";
           type enumeration {
             enum "0" {
               description "BFD version 0 (deprecated)";
             }
             enum "1" {
               description "BFD version 1";
             }
             enum "automatic" {
               description "Choose BFD version automatically";
             }
           }
         }
         leaf minimum-interval {
           description "Minimum transmit and receive interval";
           units "milliseconds";
           type union {
             type string {
               pattern "<.*>|$.*";
             }
             type uint32 {
               range "1 .. 255000";
             }
           }
         }
         leaf minimum-transmit-interval {
           description "Minimum transmit interval";
           status deprecated;
           units "milliseconds";
           type union {
             type string {
               pattern "<.*>|$.*";
             }
             type uint32 {
               range "1 .. 255000";
             }
           }
         }
         leaf minimum-receive-interval {
           description "Minimum receive interval";
           units "milliseconds";
           type union {
             type string {
               pattern "<.*>|$.*";
             }
             type uint32 {
               range "1 .. 255000";
             }
           }
         }
         leaf multiplier {
           description "Detection time multiplier";
           default "3";
           type union {
             type string {
               pattern "<.*>|$.*";
             }
             type uint32 {
               range "1 .. 255";
             }
           }
         }
         choice adaptation-choice {
           case case_1 {
             leaf no-adaptation {
               description "Disable adaptation";
               type empty;
             }
           }
         }
         container transmit-interval {
           description "Transmit-interval options";
           uses apply-advanced;
           leaf minimum-interval {
             description "Minimum transmit interval";
             units "milliseconds";
             type union {
               type string {
                 pattern "<.*>|$.*";
               }
               type uint32 {
                 range "1 .. 255000";
               }
             }
           }
           leaf threshold {
             description "High transmit interval triggering a trap";
             units "milliseconds";
             type union {
               type uint32;
               type string {
                 pattern "<.*>|$.*";
               }
             }
           }
         }
         container detection-time {
           description "Detection-time options";
           uses apply-advanced;
           leaf threshold {
             description "High detection-time triggering a trap";
             units "milliseconds";
             type union {
               type uint32;
               type string {
                 pattern "<.*>|$.*";
               }
             }
           }
         }
         container authentication {
           description "Authentication options";
           uses apply-advanced;
           leaf key-chain {
             description "Key chain name";
             type string;
           }
           leaf algorithm {
             description "Algorithm name";
             type enumeration {
               enum "simple-password" {
                 description "Simple password";
               }
               enum "keyed-md5" {
                 description "Keyed message Digest 5";
               }
               enum "meticulous-keyed-md5" {
                 description "Meticulous keyed message Digest 5";
               }
               enum "keyed-sha-1" {
                 description "Keyed secure hash algorithm (SHA1) ";
               }
               enum "meticulous-keyed-sha-1" {
                 description "Meticulous keyed secure hash algorithm (SHA1) ";
               }
             }
           }
           leaf loose-check {
             description "Verify authentication only if authentication is negotiated";
             type empty;
           }
         }
         leaf session-mode {
           description "BFD single-hop or multihop session-mode";
           default "automatic";
           type enumeration {
             enum "automatic" {
               description "Choose session-mode automatically";
             }
             enum "single-hop" {
               description "Use single-hop";
             }
             enum "multihop" {
               description "Use multihop";
             }
           }
         }
         leaf holddown-interval {
           description "Time to hold the session-UP notification to the client";
           units "milliseconds";
           type union {
             type string {
               pattern "<.*>|$.*";
             }
             type uint32 {
               range "0 .. 255000";
             }
           }
         }
       }
       leaf as-override {
         description "Replace neighbor AS number with our AS number";
         type empty;
       }
       leaf-list allow {
         ordered-by user;
         description "Configure peer connections for specific networks";
         type jt:ipprefix;
       }
       list dynamic-neighbor {
         key name;
         ordered-by user;
         description "Configure peer options for specific networks";
         leaf name {
           description "Template name";
           type string;
         }
         uses apply-advanced;
         leaf-list allow {
           ordered-by user;
           description "Configure peer connections for specific networks";
           type jt:ipprefix;
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         container peer-auto-discovery {
           description "Configure auto-discovery options for BGP neighbors";
           uses apply-advanced;
           container family {
             description "Address family based neighbor auto-discovery parameters";
             container inet6 {
               uses apply-advanced;
               choice auto-discovery-type {
                 case case_1 {
                   container ipv6-nd {
                     presence "enable ipv6-nd";
                     description "Use ipv6 neighbor discovery to learn neighbor address";
                   }
                 }
               }
             }
           }
           list interface {
             key name;
             leaf name {
               description "Configure interfaces over which to discover bgp neighbors";
               type union {
                 type jt:interface-name;
                 type string {
                   pattern "<.*>|$.*";
                 }
               }
             }
             uses apply-advanced;
             choice enable-disable {
               case case_1 {
                 leaf disable {
                   description "Disable peer discovery on interface";
                   type empty;
                 }
               }
             }
           }
         }
       }
       container optimal-route-reflection {
         description "Enable optimal route reflection for this client group";
         uses apply-advanced;
         leaf igp-primary {
           description "Primary node identifier for this client group";
           type jt:ipv4addr;
         }
         leaf igp-backup {
           description "Backup node identifier for this client group";
           type jt:ipv4addr;
         }
       }
       leaf peer-as-list {
         description "Configure list of peer autonomous systems for unconfigured neighbors";
         type string;
       }
       leaf mvpn-iana-rt-import {
         description "Use IANA assigned rt-import type value for MVPN";
         status deprecated;
         type empty;
       }
       list neighbor {
         key name;
         ordered-by user;
         description "Configure a neighbor";
         leaf name {
           type jt:ipaddr-scoped;
         }
         uses apply-advanced;
         container traceoptions {
           description "Trace options for BGP";
           uses apply-advanced;
           container file {
             description "Trace file options";
             leaf filename {
               description "Name of file in which to write trace information";
               type string {
                 length "1 .. 1024";
               }
             }
             leaf replace {
               description "Replace trace file rather than appending to it";
               status deprecated;
               type empty;
             }
             leaf size {
               description "Maximum trace file size";
               type string;
             }
             leaf files {
               description "Maximum number of trace files";
               default "10";
               type union {
                 type string {
                   pattern "<.*>|$.*";
                 }
                 type uint32 {
                   range "2 .. 1000";
                 }
               }
             }
             leaf no-stamp {
               description "Do not timestamp trace file";
               status deprecated;
               type empty;
             }
             choice world-readable-choice {
               leaf world-readable {
                 description "Allow any user to read the log file";
                 type empty;
               }
               leaf no-world-readable {
                 description "Don't allow any user to read the log file";
                 type empty;
               }
             }
           }
           list flag {
             key name;
             ordered-by user;
             description "Tracing parameters";
             leaf name {
               type enumeration {
                 enum "damping" {
                   description "Trace BGP damping information";
                 }
                 enum "packets" {
                   description "Trace all BGP protocol packets";
                 }
                 enum "open" {
                   description "Trace BGP open packets";
                 }
                 enum "update" {
                   description "Trace BGP update packets";
                 }
                 enum "keepalive" {
                   description "Trace BGP keepalive packets";
                 }
                 enum "refresh" {
                   description "Trace BGP refresh packets";
                 }
                 enum "nsr-synchronization" {
                   description "Trace NSR synchronization events";
                 }
                 enum "bfd" {
                   description "Trace BFD events";
                 }
                 enum "4byte-as" {
                   description "Trace 4 byte AS events";
                 }
                 enum "add-path" {
                   description "Trace add-path events";
                 }
                 enum "graceful-restart" {
                   description "Trace Graceful Restart events";
                 }
                 enum "egress-te" {
                   description "Egress Peering Traffic-Engineering events";
                 }
                 enum "thread-io" {
                   description "Trace threaded I/O processing";
                 }
                 enum "sharding" {
                   description "Trace BGP rib sharding";
                 }
                 enum "thread-update-io" {
                   description "Trace threaded update I/O processing";
                 }
                 enum "route-validation" {
                   description "Trace route validation";
                 }
                 enum "ipsec" {
                   description "Trace ipsec";
                 }
                 enum "route" {
                   description "Trace routing information";
                 }
                 enum "normal" {
                   description "Trace normal events";
                 }
                 enum "general" {
                   description "Trace general events";
                 }
                 enum "state" {
                   description "Trace state transitions";
                 }
                 enum "policy" {
                   description "Trace policy processing";
                 }
                 enum "task" {
                   description "Trace routing protocol task processing";
                 }
                 enum "timer" {
                   description "Trace routing protocol timer processing";
                 }
                 enum "all" {
                   description "Trace everything";
                 }
               }
             }
             leaf send {
               description "Trace transmitted packets";
               type empty;
             }
             leaf receive {
               description "Trace received packets";
               type empty;
             }
             leaf detail {
               description "Trace detailed information";
               type empty;
             }
             leaf disable {
               description "Disable this trace flag";
               type empty;
             }
             container filter {
               description "Filter to apply to this flag";
               presence "enable filter";
               uses bgp_filter_obj;
             }
           }
         }
         leaf description {
           description "Text description";
           type string {
             length "1 .. 255";
           }
         }
         container metric-out {
           description "Route metric sent in MED";
           choice metric_param {
             case case_1 {
               leaf metric-value {
                 description "Metric value";
                 type union {
                   type string {
                     pattern "<.*>|$.*";
                   }
                   type uint32 {
                     range "0 .. 4294967295";
                   }
                 }
               }
             }
             case case_2 {
               container minimum-igp {
                 presence "enable minimum-igp";
                 description "Track the minimum IGP metric";
                 leaf metric-offset {
                   description "Metric offset for MED";
                   type union {
                     type int32;
                     type string {
                       pattern "<.*>|$.*";
                     }
                   }
                 }
               }
             }
             case case_3 {
               container igp {
                 presence "enable igp";
                 description "Track the IGP metric";
                 leaf metric-offset {
                   description "Metric offset for MED";
                   type union {
                     type int32;
                     type string {
                       pattern "<.*>|$.*";
                     }
                   }
                 }
                 leaf delay-med-update {
                   description "Delay updating MED when IGP metric increases";
                   type empty;
                 }
               }
             }
             case case_4 {
               container effective-aigp {
                 presence "enable effective-aigp";
                 description "Track the effective AIGP metric";
                 leaf metric-offset {
                   description "Metric offset for MED";
                   type union {
                     type int32;
                     type string {
                       pattern "<.*>|$.*";
                     }
                   }
                 }
               }
             }
             case case_5 {
               container minimum-effective-aigp {
                 presence "enable minimum-effective-aigp";
                 description "Track the minimum effective AIGP metric";
                 leaf metric-offset {
                   description "Metric offset for MED";
                   type union {
                     type int32;
                     type string {
                       pattern "<.*>|$.*";
                     }
                   }
                 }
               }
             }
           }
         }
         container multihop {
           presence "enable multihop";
           description "Configure an EBGP multihop session";
           uses apply-advanced;
           leaf ttl {
             description "TTL value for the session";
             type union {
               type string {
                 pattern "<.*>|$.*";
               }
               type uint8 {
                 range "1 .. 255";
               }
             }
           }
           leaf no-nexthop-change {
             description "Do not change next hop to self in advertisements";
             type empty;
           }
         }
         container ebgp-community-cleanup {
           presence "enable ebgp-community-cleanup";
           description "Community specific cleanup for eBGP peers";
           uses apply-advanced;
           leaf origin-validation {
             description "Origin Validation State receive behavior";
             type enumeration {
               enum "accept" {
                 description "Accept Origin Validation State Community";
               }
               enum "reject" {
                 description "Reject Origin Validation State Community";
               }
             }
           }
         }
         leaf route-server-client {
           description "Enable route server client behavior";
           type empty;
         }
         leaf accept-remote-nexthop {
           description "Allow import policy to specify a non-directly connected next-hop";
           type empty;
         }
         leaf preference {
           description "Preference value";
           type union {
             type uint32;
             type string {
               pattern "<.*>|$.*";
             }
           }
         }
         leaf local-preference {
           description "Value of LOCAL_PREF path attribute";
           type union {
             type uint32;
             type string {
               pattern "<.*>|$.*";
             }
           }
         }
         leaf local-address {
           description "Address of local end of BGP session";
           type jt:ipaddr;
         }
         leaf local-interface {
           description "Local interface for IPv6 link local EBGP peering";
           type union {
             type jt:interface-name;
             type string {
               pattern "<.*>|$.*";
             }
           }
         }
         leaf forwarding-context {
           description "Routing-instance used for data-forwarding and transport-session";
           type string {
           }
         }
         leaf hold-time {
           description "Hold time used when negotiating with a peer";
           type union {
             type string {
               pattern "<.*>|$.*";
             }
             type uint32 {
               range "0 .. 65535";
             }
           }
         }
         leaf minimum-hold-time {
           description "Minimum hold time accepted from the peer";
           type union {
             type string {
               pattern "<.*>|$.*";
             }
             type uint32 {
               range "3 .. 65535";
             }
           }
         }
         leaf passive {
           description "Do not send open messages to a peer";
           type empty;
         }
         leaf advertise-inactive {
           description "Advertise inactive routes";
           type empty;
         }
         choice advertise-peer-as-choice {
           leaf advertise-peer-as {
             description "Advertise routes received from the same autonomous system";
             type empty;
           }
           leaf no-advertise-peer-as {
             description "Don't advertise routes received from the same autonomous system";
             type empty;
           }
         }
         container advertise-external {
           presence "enable advertise-external";
           description "Advertise best external routes";
           leaf conditional {
             description "Route matches active route upto med-comparison rule";
             type empty;
           }
         }
         leaf keep {
           description "How to retain routes in the routing table";
           type enumeration {
             enum "all" {
               description "Retain all routes";
             }
             enum "none" {
               description "Retain no routes";
             }
           }
         }
         leaf rfc6514-compliant-safi129 {
           description "Compliant with RFC6514 SAFI129 format";
           type empty;
         }
         leaf no-aggregator-id {
           description "Set router ID in aggregator path attribute to 0";
           type empty;
         }
         leaf mtu-discovery {
           description "Enable TCP path MTU discovery";
           type empty;
         }
         leaf enforce-first-as {
           description "Enforce first AS in AS-path is the neighbor's AS";
           type empty;
         }
         leaf out-delay {
           description "How long before exporting routes from routing table";
           type union {
             type string {
               pattern "<.*>|$.*";
             }
             type uint32 {
               range "0 .. 65535";
             }
           }
         }
         leaf ttl {
           description "TTL value for the single-hop peer";
           type enumeration {
             enum "1" {
             }
             enum "255" {
             }
           }
         }
         leaf log-updown {
           description "Log a message for peer state transitions";
           type empty;
         }
         leaf damping {
           description "Enable route flap damping";
           type empty;
         }
         leaf-list import {
           ordered-by user;
           description "Import policy";
           type jt:policy-algebra;
         }
         leaf-list nlri {
           ordered-by user;
           description "NLRI type to include in updates";
           status deprecated;
           type enumeration {
             enum "unicast" {
               description "Include unicast NLRI";
               status deprecated;
             }
             enum "multicast" {
               description "Include multicast NLRI";
               status deprecated;
             }
             enum "any" {
               description "Include any kind of NLRI";
               status deprecated;
             }
           }
         }
         container bgp-error-tolerance {
           presence "enable bgp-error-tolerance";
           description "Handle BGP malformed updates softly";
           uses apply-advanced;
           leaf malformed-update-log-interval {
             description "Time used when logging malformed update";
             default "300";
             units "seconds";
             type union {
               type string {
                 pattern "<.*>|$.*";
               }
               type uint32 {
                 range "10 .. 65535";
               }
             }
           }
           choice malformed-routes-limit-choice {
             case case_1 {
               leaf malformed-route-limit {
                 description "Maximum number of malformed routes from a peer";
                 default "1000";
                 type union {
                   type string {
                     pattern "<.*>|$.*";
                   }
                   type uint32 {
                     range "0 .. 4294967295";
                   }
                 }
               }
             }
             case case_2 {
               leaf no-malformed-route-limit {
                 description "No malformed route limit";
                 type empty;
               }
             }
           }
         }
         container family {
           description "Protocol family for NLRIs in updates";
           uses apply-advanced;
           container inet {
             description "IPv4 NLRI parameters";
             uses apply-advanced;
             container labeled-unicast {
               description "Include labeled unicast NLRI";
               presence "enable labeled-unicast";
               uses bgp-afi-labeled;
             }
             container segment-routing-te {
               description "Include segment-routing TE policy";
               presence "enable segment-routing-te";
               uses bgp-afi-srte;
             }
             container transport {
               description "Include Classful Transport NLRI";
               presence "enable transport";
               uses bgp-afi-inet-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow-with-redirect-ip-action;
             }
             container any {
               description "Include unicast or multicast NLRI";
               presence "enable any";
               uses bgp-afi-default;
             }
           }
           container inet-vpn {
             description "IPv4 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow-with-redirect-ip-action;
             }
             container any {
               description "Include unicast or multicast NLRI";
               presence "enable any";
               uses bgp-afi-vpn;
             }
           }
           container inet6 {
             description "IPv6 NLRI parameters";
             uses apply-advanced;
             container labeled-unicast {
               description "Include labeled unicast NLRI";
               presence "enable labeled-unicast";
               uses bgp-afi-inet6-labeled;
             }
             container segment-routing-te {
               description "Include segment-routing TE policy";
               presence "enable segment-routing-te";
               uses bgp-afi-srte;
             }
             container transport {
               description "Include Classful Transport NLRI";
               presence "enable transport";
               uses bgp-afi-inet6-transport;
             }
             container unicast {
               description "Include unicast NLRI";
               presence "enable unicast";
               uses bgp-afi-topo;
             }
             container multicast {
               description "Include multicast NLRI";
               presence "enable multicast";
               uses bgp-afi-default;
             }
             container flow {
               description "Include flow NLRI";
               presence "enable flow";
               uses bgp-afi-flow;
             }
             container any {
               description "Include unicast or multicast NLRI";
               presence "enable any";
               uses bgp-afi-default;
             }
           }
           container inet6-vpn {
             description "IPv6 Layer 3 VPN NLRI parameters";
             uses apply-advanced;
             container unicast {
               description "Include unicast NLRI";
               presence "enable unicast";
               uses bgp-afi-l3vpn;
             }
             container multicast {
               description "Include multicast NLRI";
               presence "enable multicast";
               uses bgp-afi-vpn;
             }
             container flow {
               description "Include flow VPN NLRI";
               presence "enable flow";
               uses bgp-afi-flow;
             }
             container any {
               description "Include unicast or multicast NLRI";
               presence "enable any";
               uses bgp-afi-vpn;
             }
           }
           container iso-vpn {
             description "ISO Layer 3 VPN NLRI parameters";
             uses apply-advanced;
             container unicast {
               description "Include unicast NLRI";
               presence "enable unicast";
               uses bgp-afi-vpn-protection;
             }
           }
           container l2vpn {
             description "MPLS-based Layer 2 VPN and VPLS NLRI parameters";
             uses apply-advanced;
             container auto-discovery-only {
               description "Include auto-discovery NLRI for LDP Layer 2 VPN and VPLS";
               presence "enable auto-discovery-only";
               uses bgp-afi-default;
             }
             container auto-discovery-mspw {
               description "Include auto-discovery NLRI for LDP Signalled MultiSegment PW";
               presence "enable auto-discovery-mspw";
               uses bgp-afi-default;
             }
             container signaling {
               description "Include Layer 2 VPN and VPLS signaling NLRI";
               presence "enable signaling";
               uses bgp-afi-l2vpn;
             }
           }
           container evpn {
             description "EVPN NLRI parameters";
             uses apply-advanced;
             container signaling {
               description "Include EVPN signaling NLRI";
               presence "enable signaling";
               uses bgp-afi-default;
             }
           }
           container inet-mvpn {
             description "IPv4 MVPN NLRI parameters";
             uses apply-advanced;
             container signaling {
               description "Include IPv4 multicast VPN signaling NLRI";
               presence "enable signaling";
               uses bgp-afi-default;
             }
           }
           container inet6-mvpn {
             description "IPv6 MVPN NLRI parameters";
             uses apply-advanced;
             container signaling {
               description "Include IPv6 multicast VPN signaling NLRI";
               presence "enable signaling";
               uses bgp-afi-default;
             }
           }
           container inet-mdt {
             description "IPv4 Multicast Distribution Tree (MDT) NLRI parameters";
             uses apply-advanced;
             container signaling {
               description "Include IPv4 multicast VPN auto-discovery NLRI";
               presence "enable signaling";
               uses bgp-afi-default;
             }
           }
           container traffic-engineering {
             description "Traffic Engineering (BGP-TE) NLRI parameters";
             uses apply-advanced;
             container unicast {
               description "Include BGP-TE NLRI";
               presence "enable unicast";
               uses bgp-afi-default;
             }
           }
           container route-target {
             presence "enable route-target";
             description "Route target NLRI used for VPN route filtering";
             uses apply-advanced;
             container prefix-limit {
               description "Limit maximum number of prefixes from a peer";
               uses bgpaf-prefix-limit;
             }
             container accepted-prefix-limit {
               description "Limit maximum number of prefixes accepted from a peer";
               uses bgpaf-accepted-prefix-limit;
             }
             container proxy-generate {
               presence "enable proxy-generate";
               description "Generate route target NLRI for peers that don't support it";
               uses apply-advanced;
               leaf-list route-target-policy {
                 ordered-by user;
                 description "Limit VPN routes that are used to generate proxy route-target filters";
                 type jt:policy-algebra;
               }
             }
             leaf external-paths {
               description "Number of external paths accepted for route filtering";
               type union {
                 type string {
                   pattern "<.*>|$.*";
                 }
                 type uint32 {
                   range "1 .. 256";
                 }
               }
             }
             leaf advertise-default {
               description "Advertise default and suppress more specific routes";
               type empty;
             }
             leaf damping {
               description "Enable route flap damping";
               type empty;
             }
             container graceful-restart {
               description "BGP graceful restart options";
               uses bgp-af-gr;
             }
             leaf local-ipv4-address {
               description "Local IPv4 address";
               type jt:ipv4addr;
             }
             container output-queue-priority {
               description "Default output-queue to assign updates to";
               uses bgp-output-queue-priority-class;
             }
             container route-refresh-priority {
               description "Default output-queue to assign route refreshes to";
               uses bgp-output-queue-priority-class;
             }
             container withdraw-priority {
               description "Default output-queue to assign withdrawn routes to";
               uses bgp-output-queue-priority-class;
             }
           }
           container fabric {
             description "Fabric NLRI parameters";
             status deprecated;
             uses apply-advanced;
             container unicast {
               description "Include unicast NLRI";
               presence "enable unicast";
               uses bgp-afi-default;
             }
           }
           container bridge {
             description "Bridge NLRI parameters";
             status deprecated;
             uses apply-advanced;
             container unicast {
               description "Include unicast NLRI";
               presence "enable unicast";
               uses bgp-afi-default;
             }
           }
           container bridge-vpn {
             description "Bridge VPN NLRI parameters";
             status deprecated;
             uses apply-advanced;
             container unicast {
               description "Include unicast NLRI";
               presence "enable unicast";
               uses bgp-afi-vpn;
             }
           }
           container fabric-vpn {
             description "Fabric VPN NLRI parameters";
             status deprecated;
             uses apply-advanced;
             container unicast {
               description "Include unicast NLRI";
               presence "enable unicast";
               uses bgp-afi-vpn;
             }
           }
           container inet-bgpmcast {
             description "IPv4 BGPMCAST NLRI parameters";
             uses apply-advanced;
             container signaling {
               description "Include IPv4 BGP multicast signaling NLRI";
               presence "enable signaling";
               uses bgp-afi-default;
             }
           }
           container inet6-bgpmcast {
             description "IPv6 BGPMCAST NLRI parameters";
             uses apply-advanced;
             container signaling {
               description "Include IPv6 BGP multicast signaling NLRI";
               presence "enable signaling";
               uses bgp-afi-default;
             }
           }
         }
         leaf authentication-key {
           description "MD5 authentication key";
           type string {
             length "1 .. 126";
           }
         }
         leaf authentication-algorithm {
           description "Authentication algorithm name";
           type enumeration {
             enum "md5" {
               description "Message Digest 5";
             }
             enum "hmac-sha-1-96" {
               description "Hash-based Message Authentication Code (SHA1) (96 bits)";
             }
             enum "aes-128-cmac-96" {
               description "Cipher-based Message Authentication Code (AES128) (96 bits)";
             }
             enum "ao" {
               description "TCP Authentication Option";
             }
           }
         }
         leaf tcpao-auth-mismatch {
           description "Continue without TCP-AO if any one TCP endpoint does not have TCP-AO configured";
           type enumeration {
             enum "allow-without-tcpao" {
               description "Allow the connection establishment without TCP-AO";
             }
           }
         }
         leaf authentication-key-chain {
           description "Key chain name";
           type string {
             length "1 .. 128";
           }
         }
         leaf-list export {
           ordered-by user;
           description "Export policy";
           type jt:policy-algebra;
         }
         container remove-private {
           presence "enable remove-private";
           description "Remove well-known private AS numbers";
           uses apply-advanced;
           container all {
             presence "enable all";
             description "Remove all private AS numbers and do not stop at the first public AS number";
             container replace {
               presence "enable replace";
               description "Replace private AS numbers with the BGP Group's local AS number";
               leaf nearest {
                 description "Use closest public AS number to replace a private AS number";
                 type empty;
               }
             }
           }
           leaf no-peer-loop-check {
             description "Remove peer loop-check";
             type empty;
           }
         }
         leaf cluster {
           description "Cluster identifier";
           type jt:areaid;
         }
         leaf no-client-reflect {
           description "Disable intracluster route redistribution";
           type empty;
         }
         leaf peer-as {
           description " Autonomous system number in plain number or 'higher 16bits'.'Lower 16 bits' (asdot notation) format";
           type string {
           }
         }
         container local-as {
           description "Local autonomous system number";
           leaf as-number {
             description " Autonomous system number in plain number or 'higher 16bits'.'Lower 16 bits' (asdot notation) format";
             type string {
             }
           }
           leaf loops {
             description "Maximum number of times this AS can be in an AS path";
             type union {
               type string {
                 pattern "<.*>|$.*";
               }
               type int32 {
                 range "1 .. 10";
               }
             }
           }
           leaf private {
             description "Hide this local AS in paths learned from this peering";
             type empty;
           }
           leaf alias {
             description "Treat this AS as an alias to the system AS";
             type empty;
           }
           leaf no-prepend-global-as {
             description "Do not prepend global autonomous-system number in advertised paths";
             type empty;
           }
         }
         leaf ipsec-sa {
           description "IPSec SA name";
           type string {
             length "1 .. 32";
           }
         }
         container graceful-shutdown {
           description "BGP peer graceful shutdown option";
           uses apply-advanced;
           container receiver {
             presence "enable receiver";
             description "BGP peer graceful-shutdown receiver";
             uses apply-advanced;
             leaf disable {
               description "Disable graceful-shutdown receiver";
               type empty;
             }
             leaf local-preference {
               description "Value of receiver LOCAL_PREF path attribute";
               type union {
                 type uint32;
                 type string {
                   pattern "<.*>|$.*";
                 }
               }
             }
           }
           container sender {
             presence "enable sender";
             description "BGP peer graceful-shutdown sender";
             uses apply-advanced;
             leaf local-preference {
               description "Value of sender LOCAL_PREF path attribute";
               type union {
                 type uint32;
                 type string {
                   pattern "<.*>|$.*";
                 }
               }
             }
           }
         }
         container shutdown {
           presence "enable shutdown";
           description "Shutdown";
           uses apply-advanced;
           leaf notify-message {
             description "Notification message";
             type string;
           }
         }
         leaf unconfigured-peer-graceful-restart {
           description "BGP unconfigured peer graceful restart options";
           type empty;
         }
         container graceful-restart {
           presence "enable graceful-restart";
           description "BGP graceful restart options";
           uses apply-advanced;
           choice enable-disable {
             case case_1 {
               leaf disable {
                 description "Disable graceful restart";
                 type empty;
               }
             }
           }
           leaf restart-time {
             description "Restart time used when negotiating with a peer";
             type union {
               type string {
                 pattern "<.*>|$.*";
               }
               type uint32 {
                 range "1 .. 1800";
               }
             }
           }
           leaf stale-routes-time {
             description "Maximum time for which stale routes are kept";
             type union {
               type string {
                 pattern "<.*>|$.*";
               }
               type uint32 {
                 range "1 .. 1800";
               }
             }
           }
           container long-lived {
             description "Long-lived graceful restart options";
             uses apply-advanced;
             container receiver {
               description "Long-lived graceful restart receiver (helper) options";
               uses apply-advanced;
               choice enable-disable {
                 case case_1 {
                   leaf disable {
                     description "Disable receiver (helper) functionality";
                     type empty;
                   }
                 }
               }
             }
             container advertise-to-non-llgr-neighbor {
               presence "enable advertise-to-non-llgr-neighbor";
               description "Advertise stale routes to non-LLGR neighbors";
               uses apply-advanced;
               leaf omit-no-export {
                 description "Do not attach no-export community to stale routes";
                 type empty;
               }
             }
           }
           leaf disable-notification-extensions {
             description "Disable notification extensions";
             type empty;
           }
           leaf forwarding-state-bit {
             description "Control forwarding-state flag negotiation";
             type enumeration {
               enum "as-rr-client" {
                 description "As for a route reflector client";
               }
               enum "from-fib" {
                 description "Always use state of associated FIB(s)";
               }
             }
           }
           leaf dont-help-shared-fate-bfd-down {
             description "Honor BFD-Down(C=0) if GR-restart not in progress";
             type empty;
           }
         }
         leaf include-mp-next-hop {
           description "Include NEXT-HOP attribute in multiprotocol updates";
           type empty;
         }
         leaf disable-4byte-as {
           description "Disable 4 byte AS capability advertisement";
           type empty;
         }
         container idle-after-switch-over {
           description "Stop peer session from coming up after nonstop-routing switch-over";
           choice idle-interval {
             case case_1 {
               leaf forever {
                 description "Idle the peer until the user intervenes";
                 type empty;
               }
             }
             case case_2 {
               leaf timeout {
                 description "Timeout value, in seconds, for starting peer after switch over";
                 type union {
                   type string {
                     pattern "<.*>|$.*";
                   }
                   type uint32 {
                     range "1 .. 4294967295";
                   }
                 }
               }
             }
           }
         }
         container outbound-route-filter {
           description "Dynamically negotiated cooperative route filtering";
           uses apply-advanced;
           leaf bgp-orf-cisco-mode {
             description "Using BGP ORF capability code 130 and Prefix ORF type 128";
             type empty;
           }
           container extended-community {
             description "Extended community filtering";
             status deprecated;
             uses apply-advanced;
             choice accept-choice {
               leaf accept {
                 description "Honor remote requests for extended community ORF";
                 type empty;
               }
               leaf no-accept {
                 description "Don't honor remote requests for extended community ORF";
                 type empty;
               }
             }
             leaf vrf-filter {
               description "Request remote filtering using locally configured VRF import targets";
               type empty;
             }
           }
           container prefix-based {
             presence "enable prefix-based";
             description "Prefix-based outbound route filtering";
             uses apply-advanced;
             container accept {
               presence "enable accept";
               description "Honor Prefix-based ORFs from remote peers";
               uses apply-advanced;
               leaf inet {
                 description "Honor IPv4 prefix filters";
                 type empty;
               }
               leaf inet6 {
                 description "Honor IPv6 prefix filters";
                 type empty;
               }
             }
           }
         }
         container message-batching {
           description "DEPRECATED - Batching of outgoing messages";
           status deprecated;
           uses apply-advanced;
           choice enable-disable {
             case case_1 {
               leaf enable {
                 description "Enable parameter";
                 type empty;
               }
             }
             case case_2 {
               leaf disable {
                 description "Disable parameter";
                 type empty;
               }
             }
           }
           leaf interval {
             description "DEPRECATED - Interval over which to batch messages";
             default "250";
             units "milliseconds";
             type union {
               type string {
                 pattern "<.*>|$.*";
               }
               type uint32 {
                 range "100 .. 1000";
               }
             }
           }
         }
         container multipath {
           presence "enable multipath";
           description "Allow load sharing among multiple BGP paths";
           uses apply-advanced;
           leaf disable {
             description "Disable Multipath";
             type empty;
           }
           leaf multiple-as {
             description "Use paths received from different ASs";
             type empty;
           }
           leaf allow-protection {
             description "Allow protection for multipath legs";
             type empty;
           }
           leaf pause-computation-during-churn {
             description "Pause multipath job to absorb churn";
             type empty;
           }
           leaf list-nexthop {
             description "Use List-NH for homogenous nexthop-set also";
             type empty;
           }
         }
         leaf tcp-mss {
           description "Maximum TCP segment size";
           type union {
             type string {
               pattern "<.*>|$.*";
             }
             type uint32 {
               range "1 .. 4096";
             }
           }
         }
         leaf bgp-identifier {
           description "BGP Identifier";
           type jt:ipv4addr;
         }
         leaf tcp-aggressive-transmission {
           description "Enable aggressive transmission of pure TCP ACKs and retransmissions";
           type empty;
         }
         container bmp {
           description "Specific settings to override the routing-options settings";
           uses apply-advanced;
           leaf monitor {
             description "Enable/Disable monitoring";
             type enumeration {
               enum "enable" {
                 description "Enable monitoring of BGP peer(s)";
               }
               enum "disable" {
                 description "Disable monitoring of BGP peer(s)";
               }
             }
           }
           container route-monitoring {
             description "Control route monitoring settings";
             uses apply-advanced;
             leaf none {
               description "Do not send route monitoring messages";
               type empty;
             }
             container pre-policy {
               presence "enable pre-policy";
               description "Send pre-policy route monitoring messages";
               leaf exclude-non-feasible {
                 description "Exclude looped routes, etc";
                 type empty;
               }
             }
             container post-policy {
               presence "enable post-policy";
               description "Send post-policy route monitoring messages";
               leaf exclude-non-eligible {
                 description "Exclude unresolved routes, etc.";
                 type empty;
               }
             }
             container rib-out {
               presence "enable rib-out";
               description "Send adj-ribs-out route monitoring messages";
               leaf pre-policy {
                 description "Send pre-policy adj-ribs-out route monitoring messages";
                 type empty;
               }
               leaf post-policy {
                 description "Send post-policy adj-ribs-out route monitoring messages";
                 type empty;
               }
             }
           }
         }
         container advertise-bgp-static {
           presence "enable advertise-bgp-static";
           description "Advertise bgp-static routes";
           uses apply-advanced;
           leaf-list policy {
             ordered-by user;
             description "Static route advertisement policy";
             type jt:policy-algebra;
           }
         }
         leaf add-path-display-ipv4-address {
           description "Display add-path path-id in IPv4 address format";
           type empty;
         }
         container bfd-liveness-detection {
           description "Bidirectional Forwarding Detection (BFD) options";
           uses apply-advanced;
           leaf version {
             description "BFD protocol version number";
             default "automatic";
             type enumeration {
               enum "0" {
                 description "BFD version 0 (deprecated)";
               }
               enum "1" {
                 description "BFD version 1";
               }
               enum "automatic" {
                 description "Choose BFD version automatically";
               }
             }
           }
           leaf minimum-interval {
             description "Minimum transmit and receive interval";
             units "milliseconds";
             type union {
               type string {
                 pattern "<.*>|$.*";
               }
               type uint32 {
                 range "1 .. 255000";
               }
             }
           }
           leaf minimum-transmit-interval {
             description "Minimum transmit interval";
             status deprecated;
             units "milliseconds";
             type union {
               type string {
                 pattern "<.*>|$.*";
               }
               type uint32 {
                 range "1 .. 255000";
               }
             }
           }
           leaf minimum-receive-interval {
             description "Minimum receive interval";
             units "milliseconds";
             type union {
               type string {
                 pattern "<.*>|$.*";
               }
               type uint32 {
                 range "1 .. 255000";
               }
             }
           }
           leaf multiplier {
             description "Detection time multiplier";
             default "3";
             type union {
               type string {
                 pattern "<.*>|$.*";
               }
               type uint32 {
                 range "1 .. 255";
               }
             }
           }
           choice adaptation-choice {
             case case_1 {
               leaf no-adaptation {
                 description "Disable adaptation";
                 type empty;
               }
             }
           }
           container transmit-interval {
             description "Transmit-interval options";
             uses apply-advanced;
             leaf minimum-interval {
               description "Minimum transmit interval";
               units "milliseconds";
               type union {
                 type string {
                   pattern "<.*>|$.*";
                 }
                 type uint32 {
                   range "1 .. 255000";
                 }
               }
             }
             leaf threshold {
               description "High transmit interval triggering a trap";
               units "milliseconds";
               type union {
                 type uint32;
                 type string {
                   pattern "<.*>|$.*";
                 }
               }
             }
           }
           container detection-time {
             description "Detection-time options";
             uses apply-advanced;
             leaf threshold {
               description "High detection-time triggering a trap";
               units "milliseconds";
               type union {
                 type uint32;
                 type string {
                   pattern "<.*>|$.*";
                 }
               }
             }
           }
           container authentication {
             description "Authentication options";
             uses apply-advanced;
             leaf key-chain {
               description "Key chain name";
               type string;
             }
             leaf algorithm {
               description "Algorithm name";
               type enumeration {
                 enum "simple-password" {
                   description "Simple password";
                 }
                 enum "keyed-md5" {
                   description "Keyed message Digest 5";
                 }
                 enum "meticulous-keyed-md5" {
                   description "Meticulous keyed message Digest 5";
                 }
                 enum "keyed-sha-1" {
                   description "Keyed secure hash algorithm (SHA1) ";
                 }
                 enum "meticulous-keyed-sha-1" {
                   description "Meticulous keyed secure hash algorithm (SHA1) ";
                 }
               }
             }
             leaf loose-check {
               description "Verify authentication only if authentication is negotiated";
               type empty;
             }
           }
           leaf session-mode {
             description "BFD single-hop or multihop session-mode";
             default "automatic";
             type enumeration {
               enum "automatic" {
                 description "Choose session-mode automatically";
               }
               enum "single-hop" {
                 description "Use single-hop";
               }
               enum "multihop" {
                 description "Use multihop";
               }
             }
           }
           leaf holddown-interval {
             description "Time to hold the session-UP notification to the client";
             units "milliseconds";
             type union {
               type string {
                 pattern "<.*>|$.*";
               }
               type uint32 {
                 range "0 .. 255000";
               }
             }
           }
         }
         leaf as-override {
           description "Replace neighbor AS number with our AS number";
           type empty;
         }
         container egress-te-node-segment {
           description "Configure BGP-Peer-Node segment";
           uses apply-advanced;
           container label {
             description "BGP-Peer-Node SID label from static label pool";
             uses apply-advanced;
             leaf label-value {
               description "BGP-Peer-Node SID label value from static label pool";
               type union {
                 type string {
                   pattern "<.*>|$.*";
                 }
                 type uint32 {
                   range "16 .. 1048575";
                 }
               }
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
               }
             }
           }
         }
         list egress-te-adj-segment {
           key name;
           description "Configure BGP-Peer-Adj segment";
           leaf name {
             description "The BGP-Adj-Set segment name";
             type string {
             }
           }
           uses apply-advanced;
           container label {
             description "BGP-Peer-Adj SID label from static label pool";
             uses apply-advanced;
             leaf label-value {
               description "BGP-Peer-Adj SID label value from static label pool";
               type union {
                 type string {
                   pattern "<.*>|$.*";
                 }
                 type uint32 {
                   range "16 .. 1048575";
                 }
               }
             }
           }
           container next-hop {
             description "Address of directly connected next-hop to use";
             uses apply-advanced;
             leaf next-hop-addr {
               description "Address of directly connected next-hop";
               type jt:ipaddr;
             }
           }
           container egress-te-set {
             description "Configure as a member of a SET segment";
             uses apply-advanced;
             leaf set-name {
               description "Set name";
               type string {
               }
             }
             leaf weight {
               description "Weight for set segment";
               type union {
                 type string {
                   pattern "<.*>|$.*";
                 }
                 type uint32 {
                   range "1 .. 255";
                 }
               }
             }
           }
           container egress-te-backup-segment {
             description "Backup segment for FRR";
             uses apply-advanced;
             container label {
               description "Backup segment label from static label pool";
               uses apply-advanced;
               leaf label-value {
                 description "Backup segment label value from static label pool";
                 type union {
                   type string {
                     pattern "<.*>|$.*";
                   }
                   type uint32 {
                     range "16 .. 1048575";
                   }
                 }
               }
             }
           }
           container egress-te-backup-ip-forward {
             presence "enable egress-te-backup-ip-forward";
             description "Use IP-forward backup path for Egress TE";
             uses apply-advanced;
             leaf instance-name {
               description "Routing-instance to use as IP forward backup-path";
               type string {
               }
             }
           }
           container te-link-attribute {
             presence "enable te-link-attribute";
             description "Link attribute";
             uses apply-advanced;
             leaf te-metric {
               description "TE Metric value";
               default "1";
               type union {
                 type string {
                   pattern "<.*>|$.*";
                 }
                 type uint32 {
                   range "1 .. 4294967295";
                 }
               }
             }
             leaf igp-metric {
               description "IGP Metric value";
               default "1";
               type union {
                 type string {
                   pattern "<.*>|$.*";
                 }
                 type uint32 {
                   range "1 .. 16777215";
                 }
               }
             }
             leaf delay-metric {
               description "Delay Metric";
               units "microseconds";
               type union {
                 type string {
                   pattern "<.*>|$.*";
                 }
                 type uint32 {
                   range "1 .. 16777215";
                 }
               }
             }
             leaf-list admin-group {
               ordered-by user;
               description "Administrative groups";
               type string;
               max-elements 16;
             }
           }
         }
         leaf vpn-apply-export {
           description "Apply BGP export policy when exporting VPN routes";
           type empty;
         }
         container egress-te {
           presence "enable egress-te";
           description "Use Egress Peering traffic engineering";
           uses apply-advanced;
           leaf install-address {
             description "Address to use in egress-te created inet route";
             type jt:ipaddr;
           }
           container rib {
             description "Select primary table for Egress-TE routes";
             uses apply-advanced;
             leaf inet.0 {
               description "Install Egress-TE routes in inet.0";
               type empty;
             }
             leaf inet6.0 {
               description "Install Egress-TE routes in inet6.0";
               type empty;
             }
           }
           leaf no-install {
             description "Avoid installation to FIB or resolving over";
             type empty;
           }
           leaf-list import {
             ordered-by user;
             description "Import policy to set attributes";
             type jt:policy-algebra;
           }
           leaf backup-path {
             description "The 'egress-te-backup-paths template' to use for this peer";
             type string {
             }
           }
         }
         leaf advertise-prefix-sid {
           description "Advertise prefix sid to E-BGP peers";
           type empty;
         }
         leaf accept-prefix-sid {
           description "Accept prefix sid from E-BGP peers";
           type empty;
         }
         leaf advertise-srgb {
           description "Advertise SRGB TLV";
           type empty;
         }
         leaf tcp-connect-port {
           description "TCP port number to connect with peer on";
           type union {
             type string {
               pattern "<.*>|$.*";
             }
             type uint16 {
               range "1 .. 65535";
             }
           }
         }
       }
       leaf vpn-apply-export {
         description "Apply BGP export policy when exporting VPN routes";
         type empty;
       }
       container egress-te {
         presence "enable egress-te";
         description "Use Egress Peering traffic engineering";
         uses apply-advanced;
         leaf install-address {
           description "Address to use in egress-te created inet route";
           type jt:ipaddr;
         }
         container rib {
           description "Select primary table for Egress-TE routes";
           uses apply-advanced;
           leaf inet.0 {
             description "Install Egress-TE routes in inet.0";
             type empty;
           }
           leaf inet6.0 {
             description "Install Egress-TE routes in inet6.0";
             type empty;
           }
         }
         leaf no-install {
           description "Avoid installation to FIB or resolving over";
           type empty;
         }
         leaf-list import {
           ordered-by user;
           description "Import policy to set attributes";
           type jt:policy-algebra;
         }
         leaf backup-path {
           description "The 'egress-te-backup-paths template' to use for this peer";
           type string {
           }
         }
       }
       leaf advertise-prefix-sid {
         description "Advertise prefix sid to E-BGP peers";
         type empty;
       }
       leaf accept-prefix-sid {
         description "Accept prefix sid from E-BGP peers";
         type empty;
       }
       leaf advertise-srgb {
         description "Advertise SRGB TLV";
         type empty;
       }
       leaf tcp-connect-port {
         description "TCP port number to connect with peer on";
         type union {
           type string {
             pattern "<.*>|$.*";
           }
           type uint16 {
             range "1 .. 65535";
           }
         }
       }
     }
     container traffic-statistics-labeled-path {
       presence "enable traffic-statistics-labeled-path";
       description "Collect periodic ingress labeled statistics for BGP label-switched paths ";
       uses apply-advanced;
       container file {
         description "Statistics file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       leaf interval {
         description "Time interval to collect statistics";
         units "seconds";
         type union {
           type string {
             pattern "<.*>|$.*";
           }
           type int32 {
             range "60 .. 65535";
           }
         }
       }
     }
     container source-packet-routing {
       description "Enable Source Packet Routing (SPRING)";
       uses apply-advanced;
       container srgb {
         description "Set the SRGB global block in SPRING";
         leaf start-label {
           description "Start range for SRGB label block";
           type union {
             type string {
               pattern "<.*>|$.*";
             }
             type uint32;
           }
         }
         leaf index-range {
           description "Index to the SRGB start label block";
           type union {
             type string {
               pattern "<.*>|$.*";
             }
             type uint32;
           }
         }
       }
       container srv6 {
         description "Enable IPv6 Segment Routing (SRv6)";
         uses apply-advanced;
         list locator {
           key name;
           ordered-by user;
           description "SRv6 Locator";
           leaf name {
             description "Locator name";
             type string;
           }
           uses apply-advanced;
           leaf end-dt4-sid {
             description "End dt4 sid with 128 bit address";
             type jt:ipv6addr;
           }
           leaf end-dt6-sid {
             description "End dt6 sid with 128 bit address";
             type jt:ipv6addr;
           }
           leaf end-dt46-sid {
             description "End dt46 sid with 128 bit address";
             type jt:ipv6addr;
           }
         }
       }
     }
     choice enable-disable {
       case case_1 {
         leaf disable {
           description "Disable BGP";
           type empty;
         }
       }
     }
     choice precision-timers-choice {
       leaf precision-timers {
         description "Use precision timers for scheduling keepalives";
         type empty;
       }
       leaf no-precision-timers {
         description "Don't use precision timers for scheduling keepalives";
         type empty;
       }
     }
     container snmp-options {
       description "Customize SNMP behaviors specifically for BGP MIBs";
       uses apply-advanced;
       leaf backward-traps-only-from-established {
         description "Limit traps for backward transitions to only those moving from Established state.";
         type empty;
       }
       leaf emit-inet-address-length-in-oid {
         description "Emit Length in OID for InetAddress MIB type.";
         type empty;
       }
     }
     leaf route-age-bgp-view {
       description "Maintain BGP route's age based on Update messages only";
       type empty;
     }
     leaf prioritize-route-queueing {
       description "Let route-queue building happen without getting throttled";
       type empty;
     }
     container traceoptions {
       description "Trace options for BGP";
       uses apply-advanced;
       container file {
         description "Trace file options";
         leaf filename {
           description "Name of file in which to write trace information";
           type string {
             length "1 .. 1024";
           }
         }
         leaf replace {
           description "Replace trace file rather than appending to it";
           status deprecated;
           type empty;
         }
         leaf size {
           description "Maximum trace file size";
           type string;
         }
         leaf files {
           description "Maximum number of trace files";
           default "10";
           type union {
             type string {
               pattern "<.*>|$.*";
             }
             type uint32 {
               range "2 .. 1000";
             }
           }
         }
         leaf no-stamp {
           description "Do not timestamp trace file";
           status deprecated;
           type empty;
         }
         choice world-readable-choice {
           leaf world-readable {
             description "Allow any user to read the log file";
             type empty;
           }
           leaf no-world-readable {
             description "Don't allow any user to read the log file";
             type empty;
           }
         }
       }
       list flag {
         key name;
         ordered-by user;
         description "Tracing parameters";
         leaf name {
           type enumeration {
             enum "damping" {
               description "Trace BGP damping information";
             }
             enum "packets" {
               description "Trace all BGP protocol packets";
             }
             enum "open" {
               description "Trace BGP open packets";
             }
             enum "update" {
               description "Trace BGP update packets";
             }
             enum "keepalive" {
               description "Trace BGP keepalive packets";
             }
             enum "refresh" {
               description "Trace BGP refresh packets";
             }
             enum "nsr-synchronization" {
               description "Trace NSR synchronization events";
             }
             enum "bfd" {
               description "Trace BFD events";
             }
             enum "4byte-as" {
               description "Trace 4 byte AS events";
             }
             enum "add-path" {
               description "Trace add-path events";
             }
             enum "graceful-restart" {
               description "Trace Graceful Restart events";
             }
             enum "egress-te" {
               description "Egress Peering Traffic-Engineering events";
             }
             enum "thread-io" {
               description "Trace threaded I/O processing";
             }
             enum "sharding" {
               description "Trace BGP rib sharding";
             }
             enum "thread-update-io" {
               description "Trace threaded update I/O processing";
             }
             enum "route-validation" {
               description "Trace route validation";
             }
             enum "ipsec" {
               description "Trace ipsec";
             }
             enum "route" {
               description "Trace routing information";
             }
             enum "normal" {
               description "Trace normal events";
             }
             enum "general" {
               description "Trace general events";
             }
             enum "state" {
               description "Trace state transitions";
             }
             enum "policy" {
               description "Trace policy processing";
             }
             enum "task" {
               description "Trace routing protocol task processing";
             }
             enum "timer" {
               description "Trace routing protocol timer processing";
             }
             enum "all" {
               description "Trace everything";
             }
           }
         }
         leaf send {
           description "Trace transmitted packets";
           type empty;
         }
         leaf receive {
           description "Trace received packets";
           type empty;
         }
         leaf detail {
           description "Trace detailed information";
           type empty;
         }
         leaf disable {
           description "Disable this trace flag";
           type empty;
         }
         container filter {
           description "Filter to apply to this flag";
           presence "enable filter";
           uses bgp_filter_obj;
         }
       }
     }
     leaf description {
       description "Text description";
       type string {
         length "1 .. 255";
       }
     }
     container metric-out {
       description "Route metric sent in MED";
       choice metric_param {
         case case_1 {
           leaf metric-value {
             description "Metric value";
             type union {
               type string {
                 pattern "<.*>|$.*";
               }
               type uint32 {
                 range "0 .. 4294967295";
               }
             }
           }
         }
         case case_2 {
           container minimum-igp {
             presence "enable minimum-igp";
             description "Track the minimum IGP metric";
             leaf metric-offset {
               description "Metric offset for MED";
               type union {
                 type int32;
                 type string {
                   pattern "<.*>|$.*";
                 }
               }
             }
           }
         }
         case case_3 {
           container igp {
             presence "enable igp";
             description "Track the IGP metric";
             leaf metric-offset {
               description "Metric offset for MED";
               type union {
                 type int32;
                 type string {
                   pattern "<.*>|$.*";
                 }
               }
             }
             leaf delay-med-update {
               description "Delay updating MED when IGP metric increases";
               type empty;
             }
           }
         }
         case case_4 {
           container effective-aigp {
             presence "enable effective-aigp";
             description "Track the effective AIGP metric";
             leaf metric-offset {
               description "Metric offset for MED";
               type union {
                 type int32;
                 type string {
                   pattern "<.*>|$.*";
                 }
               }
             }
           }
         }
         case case_5 {
           container minimum-effective-aigp {
             presence "enable minimum-effective-aigp";
             description "Track the minimum effective AIGP metric";
             leaf metric-offset {
               description "Metric offset for MED";
               type union {
                 type int32;
                 type string {
                   pattern "<.*>|$.*";
                 }
               }
             }
           }
         }
       }
     }
     container multihop {
       presence "enable multihop";
       description "Configure an EBGP multihop session";
       uses apply-advanced;
       leaf ttl {
         description "TTL value for the session";
         type union {
           type string {
             pattern "<.*>|$.*";
           }
           type uint8 {
             range "1 .. 255";
           }
         }
       }
       leaf no-nexthop-change {
         description "Do not change next hop to self in advertisements";
         type empty;
       }
     }
     container ebgp-community-cleanup {
       presence "enable ebgp-community-cleanup";
       description "Community specific cleanup for eBGP peers";
       uses apply-advanced;
       leaf origin-validation {
         description "Origin Validation State receive behavior";
         type enumeration {
           enum "accept" {
             description "Accept Origin Validation State Community";
           }
           enum "reject" {
             description "Reject Origin Validation State Community";
           }
         }
       }
     }
     leaf route-server-client {
       description "Enable route server client behavior";
       type empty;
     }
     leaf accept-remote-nexthop {
       description "Allow import policy to specify a non-directly connected next-hop";
       type empty;
     }
     leaf preference {
       description "Preference value";
       type union {
         type uint32;
         type string {
           pattern "<.*>|$.*";
         }
       }
     }
     leaf local-preference {
       description "Value of LOCAL_PREF path attribute";
       type union {
         type uint32;
         type string {
           pattern "<.*>|$.*";
         }
       }
     }
     leaf local-address {
       description "Address of local end of BGP session";
       type jt:ipaddr;
     }
     leaf local-interface {
       description "Local interface for IPv6 link local EBGP peering";
       type union {
         type jt:interface-name;
         type string {
           pattern "<.*>|$.*";
         }
       }
     }
     leaf forwarding-context {
       description "Routing-instance used for data-forwarding and transport-session";
       type string {
       }
     }
     leaf hold-time {
       description "Hold time used when negotiating with a peer";
       type union {
         type string {
           pattern "<.*>|$.*";
         }
         type uint32 {
           range "0 .. 65535";
         }
       }
     }
     leaf minimum-hold-time {
       description "Minimum hold time accepted from the peer";
       type union {
         type string {
           pattern "<.*>|$.*";
         }
         type uint32 {
           range "3 .. 65535";
         }
       }
     }
     leaf passive {
       description "Do not send open messages to a peer";
       type empty;
     }
     leaf advertise-inactive {
       description "Advertise inactive routes";
       type empty;
     }
     choice advertise-peer-as-choice {
       leaf advertise-peer-as {
         description "Advertise routes received from the same autonomous system";
         type empty;
       }
       leaf no-advertise-peer-as {
         description "Don't advertise routes received from the same autonomous system";
         type empty;
       }
     }
     container advertise-external {
       presence "enable advertise-external";
       description "Advertise best external routes";
       leaf conditional {
         description "Route matches active route upto med-comparison rule";
         type empty;
       }
     }
     leaf keep {
       description "How to retain routes in the routing table";
       type enumeration {
         enum "all" {
           description "Retain all routes";
         }
         enum "none" {
           description "Retain no routes";
         }
       }
     }
     leaf rfc6514-compliant-safi129 {
       description "Compliant with RFC6514 SAFI129 format";
       type empty;
     }
     leaf no-aggregator-id {
       description "Set router ID in aggregator path attribute to 0";
       type empty;
     }
     leaf mtu-discovery {
       description "Enable TCP path MTU discovery";
       type empty;
     }
     leaf enforce-first-as {
       description "Enforce first AS in AS-path is the neighbor's AS";
       type empty;
     }
     leaf out-delay {
       description "How long before exporting routes from routing table";
       type union {
         type string {
           pattern "<.*>|$.*";
         }
         type uint32 {
           range "0 .. 65535";
         }
       }
     }
     leaf ttl {
       description "TTL value for the single-hop peer";
       type enumeration {
         enum "1" {
         }
         enum "255" {
         }
       }
     }
     leaf log-updown {
       description "Log a message for peer state transitions";
       type empty;
     }
     leaf damping {
       description "Enable route flap damping";
       type empty;
     }
     leaf-list import {
       ordered-by user;
       description "Import policy";
       type jt:policy-algebra;
     }
     leaf-list nlri {
       ordered-by user;
       description "NLRI type to include in updates";
       status deprecated;
       type enumeration {
         enum "unicast" {
           description "Include unicast NLRI";
           status deprecated;
         }
         enum "multicast" {
           description "Include multicast NLRI";
           status deprecated;
         }
         enum "any" {
           description "Include any kind of NLRI";
           status deprecated;
         }
       }
     }
     container bgp-error-tolerance {
       presence "enable bgp-error-tolerance";
       description "Handle BGP malformed updates softly";
       uses apply-advanced;
       leaf malformed-update-log-interval {
         description "Time used when logging malformed update";
         default "300";
         units "seconds";
         type union {
           type string {
             pattern "<.*>|$.*";
           }
           type uint32 {
             range "10 .. 65535";
           }
         }
       }
       choice malformed-routes-limit-choice {
         case case_1 {
           leaf malformed-route-limit {
             description "Maximum number of malformed routes from a peer";
             default "1000";
             type union {
               type string {
                 pattern "<.*>|$.*";
               }
               type uint32 {
                 range "0 .. 4294967295";
               }
             }
           }
         }
         case case_2 {
           leaf no-malformed-route-limit {
             description "No malformed route limit";
             type empty;
           }
         }
       }
     }
     leaf authentication-key {
       description "MD5 authentication key";
       type string {
         length "1 .. 126";
       }
     }
     leaf authentication-algorithm {
       description "Authentication algorithm name";
       default "hmac-sha-1-96";
       type enumeration {
         enum "md5" {
           description "Message Digest 5";
         }
         enum "hmac-sha-1-96" {
           description "Hash-based Message Authentication Code (SHA1) (96 bits)";
         }
         enum "aes-128-cmac-96" {
           description "Cipher-based Message Authentication Code (AES128) (96 bits)";
         }
         enum "ao" {
           description "TCP Authentication Option";
         }
       }
     }
     leaf tcpao-auth-mismatch {
       description "Continue without TCP-AO if any one TCP endpoint does not have TCP-AO configured";
       type enumeration {
         enum "allow-without-tcpao" {
           description "Allow the connection establishment without TCP-AO";
         }
       }
     }
     leaf authentication-key-chain {
       description "Key chain name";
       type string {
         length "1 .. 128";
       }
     }
     leaf-list export {
       ordered-by user;
       description "Export policy";
       type jt:policy-algebra;
     }
     container remove-private {
       presence "enable remove-private";
       description "Remove well-known private AS numbers";
       uses apply-advanced;
       container all {
         presence "enable all";
         description "Remove all private AS numbers and do not stop at the first public AS number";
         container replace {
           presence "enable replace";
           description "Replace private AS numbers with the BGP Group's local AS number";
           leaf nearest {
             description "Use closest public AS number to replace a private AS number";
             type empty;
           }
         }
       }
       leaf no-peer-loop-check {
         description "Remove peer loop-check";
         type empty;
       }
     }
     leaf cluster {
       description "Cluster identifier";
       type jt:areaid;
     }
     leaf no-client-reflect {
       description "Disable intracluster route redistribution";
       type empty;
     }
     leaf peer-as {
       description " Autonomous system number in plain number or 'higher 16bits'.'Lower 16 bits' (asdot notation) format";
       type string {
       }
     }
     container local-as {
       description "Local autonomous system number";
       leaf as-number {
         description " Autonomous system number in plain number or 'higher 16bits'.'Lower 16 bits' (asdot notation) format";
         type string {
         }
       }
       leaf loops {
         description "Maximum number of times this AS can be in an AS path";
         type union {
           type string {
             pattern "<.*>|$.*";
           }
           type int32 {
             range "1 .. 10";
           }
         }
       }
       leaf private {
         description "Hide this local AS in paths learned from this peering";
         type empty;
       }
       leaf alias {
         description "Treat this AS as an alias to the system AS";
         type empty;
       }
       leaf no-prepend-global-as {
         description "Do not prepend global autonomous-system number in advertised paths";
         type empty;
       }
     }
     leaf ipsec-sa {
       description "IPSec SA name";
       type string {
         length "1 .. 32";
       }
     }
     container graceful-shutdown {
       description "BGP peer graceful shutdown option";
       uses apply-advanced;
       container receiver {
         presence "enable receiver";
         description "BGP peer graceful-shutdown receiver";
         uses apply-advanced;
         leaf disable {
           description "Disable graceful-shutdown receiver";
           type empty;
         }
         leaf local-preference {
           description "Value of receiver LOCAL_PREF path attribute";
           type union {
             type uint32;
             type string {
               pattern "<.*>|$.*";
             }
           }
         }
       }
       container sender {
         presence "enable sender";
         description "BGP peer graceful-shutdown sender";
         uses apply-advanced;
         leaf local-preference {
           description "Value of sender LOCAL_PREF path attribute";
           type union {
             type uint32;
             type string {
               pattern "<.*>|$.*";
             }
           }
         }
       }
     }
     container shutdown {
       presence "enable shutdown";
       description "Shutdown";
       uses apply-advanced;
       leaf notify-message {
         description "Notification message";
         type string;
       }
     }
     leaf unconfigured-peer-graceful-restart {
       description "BGP unconfigured peer graceful restart options";
       type empty;
     }
     container graceful-restart {
       presence "enable graceful-restart";
       description "BGP graceful restart options";
       uses apply-advanced;
       choice enable-disable {
         case case_1 {
           leaf disable {
             description "Disable graceful restart";
             type empty;
           }
         }
       }
       leaf restart-time {
         description "Restart time used when negotiating with a peer";
         type union {
           type string {
             pattern "<.*>|$.*";
           }
           type uint32 {
             range "1 .. 1800";
           }
         }
       }
       leaf stale-routes-time {
         description "Maximum time for which stale routes are kept";
         type union {
           type string {
             pattern "<.*>|$.*";
           }
           type uint32 {
             range "1 .. 1800";
           }
         }
       }
       container long-lived {
         description "Long-lived graceful restart options";
         uses apply-advanced;
         container receiver {
           description "Long-lived graceful restart receiver (helper) options";
           uses apply-advanced;
           choice enable-disable {
             case case_1 {
               leaf disable {
                 description "Disable receiver (helper) functionality";
                 type empty;
               }
             }
           }
         }
         container advertise-to-non-llgr-neighbor {
           presence "enable advertise-to-non-llgr-neighbor";
           description "Advertise stale routes to non-LLGR neighbors";
           uses apply-advanced;
           leaf omit-no-export {
             description "Do not attach no-export community to stale routes";
             type empty;
           }
         }
       }
       leaf disable-notification-extensions {
         description "Disable notification extensions";
         type empty;
       }
       leaf forwarding-state-bit {
         description "Control forwarding-state flag negotiation";
         type enumeration {
           enum "as-rr-client" {
             description "As for a route reflector client";
           }
           enum "from-fib" {
             description "Always use state of associated FIB(s)";
           }
         }
       }
       leaf dont-help-shared-fate-bfd-down {
         description "Honor BFD-Down(C=0) if GR-restart not in progress";
         type empty;
       }
     }
     leaf include-mp-next-hop {
       description "Include NEXT-HOP attribute in multiprotocol updates";
       type empty;
     }
     leaf disable-4byte-as {
       description "Disable 4 byte AS capability advertisement";
       type empty;
     }
     container idle-after-switch-over {
       description "Stop peer session from coming up after nonstop-routing switch-over";
       choice idle-interval {
         case case_1 {
           leaf forever {
             description "Idle the peer until the user intervenes";
             type empty;
           }
         }
         case case_2 {
           leaf timeout {
             description "Timeout value, in seconds, for starting peer after switch over";
             type union {
               type string {
                 pattern "<.*>|$.*";
               }
               type uint32 {
                 range "1 .. 4294967295";
               }
             }
           }
         }
       }
     }
     container outbound-route-filter {
       description "Dynamically negotiated cooperative route filtering";
       uses apply-advanced;
       leaf bgp-orf-cisco-mode {
         description "Using BGP ORF capability code 130 and Prefix ORF type 128";
         type empty;
       }
       container extended-community {
         description "Extended community filtering";
         status deprecated;
         uses apply-advanced;
         choice accept-choice {
           leaf accept {
             description "Honor remote requests for extended community ORF";
             type empty;
           }
           leaf no-accept {
             description "Don't honor remote requests for extended community ORF";
             type empty;
           }
         }
         leaf vrf-filter {
           description "Request remote filtering using locally configured VRF import targets";
           type empty;
         }
       }
       container prefix-based {
         presence "enable prefix-based";
         description "Prefix-based outbound route filtering";
         uses apply-advanced;
         container accept {
           presence "enable accept";
           description "Honor Prefix-based ORFs from remote peers";
           uses apply-advanced;
           leaf inet {
             description "Honor IPv4 prefix filters";
             type empty;
           }
           leaf inet6 {
             description "Honor IPv6 prefix filters";
             type empty;
           }
         }
       }
     }
     container message-batching {
       description "DEPRECATED - Batching of outgoing messages";
       status deprecated;
       uses apply-advanced;
       choice enable-disable {
         case case_1 {
           leaf enable {
             description "Enable parameter";
             type empty;
           }
         }
         case case_2 {
           leaf disable {
             description "Disable parameter";
             type empty;
           }
         }
       }
       leaf interval {
         description "DEPRECATED - Interval over which to batch messages";
         default "250";
         units "milliseconds";
         type union {
           type string {
             pattern "<.*>|$.*";
           }
           type uint32 {
             range "100 .. 1000";
           }
         }
       }
     }
     container multipath {
       presence "enable multipath";
       description "Allow load sharing among multiple BGP paths";
       uses apply-advanced;
       leaf disable {
         description "Disable Multipath";
         type empty;
       }
       leaf multiple-as {
         description "Use paths received from different ASs";
         type empty;
       }
       leaf allow-protection {
         description "Allow protection for multipath legs";
         type empty;
       }
       leaf pause-computation-during-churn {
         description "Pause multipath job to absorb churn";
         type empty;
       }
       leaf list-nexthop {
         description "Use List-NH for homogenous nexthop-set also";
         type empty;
       }
     }
     leaf tcp-mss {
       description "Maximum TCP segment size";
       type union {
         type string {
           pattern "<.*>|$.*";
         }
         type uint32 {
           range "1 .. 4096";
         }
       }
     }
     leaf bgp-identifier {
       description "BGP Identifier";
       type jt:ipv4addr;
     }
     leaf tcp-aggressive-transmission {
       description "Enable aggressive transmission of pure TCP ACKs and retransmissions";
       type empty;
     }
     container bmp {
       description "Specific settings to override the routing-options settings";
       uses apply-advanced;
       leaf monitor {
         description "Enable/Disable monitoring";
         type enumeration {
           enum "enable" {
             description "Enable monitoring of BGP peer(s)";
           }
           enum "disable" {
             description "Disable monitoring of BGP peer(s)";
           }
         }
       }
       container route-monitoring {
         description "Control route monitoring settings";
         uses apply-advanced;
         leaf none {
           description "Do not send route monitoring messages";
           type empty;
         }
         container pre-policy {
           presence "enable pre-policy";
           description "Send pre-policy route monitoring messages";
           leaf exclude-non-feasible {
             description "Exclude looped routes, etc";
             type empty;
           }
         }
         container post-policy {
           presence "enable post-policy";
           description "Send post-policy route monitoring messages";
           leaf exclude-non-eligible {
             description "Exclude unresolved routes, etc.";
             type empty;
           }
         }
         container rib-out {
           presence "enable rib-out";
           description "Send adj-ribs-out route monitoring messages";
           leaf pre-policy {
             description "Send pre-policy adj-ribs-out route monitoring messages";
             type empty;
           }
           leaf post-policy {
             description "Send post-policy adj-ribs-out route monitoring messages";
             type empty;
           }
         }
       }
     }
     container advertise-bgp-static {
       presence "enable advertise-bgp-static";
       description "Advertise bgp-static routes";
       uses apply-advanced;
       leaf-list policy {
         ordered-by user;
         description "Static route advertisement policy";
         type jt:policy-algebra;
       }
     }
     leaf add-path-display-ipv4-address {
       description "Display add-path path-id in IPv4 address format";
       type empty;
     }
     container bfd-liveness-detection {
       description "Bidirectional Forwarding Detection (BFD) options";
       uses apply-advanced;
       leaf version {
         description "BFD protocol version number";
         default "automatic";
         type enumeration {
           enum "0" {
             description "BFD version 0 (deprecated)";
           }
           enum "1" {
             description "BFD version 1";
           }
           enum "automatic" {
             description "Choose BFD version automatically";
           }
         }
       }
       leaf minimum-interval {
         description "Minimum transmit and receive interval";
         units "milliseconds";
         type union {
           type string {
             pattern "<.*>|$.*";
           }
           type uint32 {
             range "1 .. 255000";
           }
         }
       }
       leaf minimum-transmit-interval {
         description "Minimum transmit interval";
         status deprecated;
         units "milliseconds";
         type union {
           type string {
             pattern "<.*>|$.*";
           }
           type uint32 {
             range "1 .. 255000";
           }
         }
       }
       leaf minimum-receive-interval {
         description "Minimum receive interval";
         units "milliseconds";
         type union {
           type string {
             pattern "<.*>|$.*";
           }
           type uint32 {
             range "1 .. 255000";
           }
         }
       }
       leaf multiplier {
         description "Detection time multiplier";
         default "3";
         type union {
           type string {
             pattern "<.*>|$.*";
           }
           type uint32 {
             range "1 .. 255";
           }
         }
       }
       choice adaptation-choice {
         case case_1 {
           leaf no-adaptation {
             description "Disable adaptation";
             type empty;
           }
         }
       }
       container transmit-interval {
         description "Transmit-interval options";
         uses apply-advanced;
         leaf minimum-interval {
           description "Minimum transmit interval";
           units "milliseconds";
           type union {
             type string {
               pattern "<.*>|$.*";
             }
             type uint32 {
               range "1 .. 255000";
             }
           }
         }
         leaf threshold {
           description "High transmit interval triggering a trap";
           units "milliseconds";
           type union {
             type uint32;
             type string {
               pattern "<.*>|$.*";
             }
           }
         }
       }
       container detection-time {
         description "Detection-time options";
         uses apply-advanced;
         leaf threshold {
           description "High detection-time triggering a trap";
           units "milliseconds";
           type union {
             type uint32;
             type string {
               pattern "<.*>|$.*";
             }
           }
         }
       }
       container authentication {
         description "Authentication options";
         uses apply-advanced;
         leaf key-chain {
           description "Key chain name";
           type string;
         }
         leaf algorithm {
           description "Algorithm name";
           type enumeration {
             enum "simple-password" {
               description "Simple password";
             }
             enum "keyed-md5" {
               description "Keyed message Digest 5";
             }
             enum "meticulous-keyed-md5" {
               description "Meticulous keyed message Digest 5";
             }
             enum "keyed-sha-1" {
               description "Keyed secure hash algorithm (SHA1) ";
             }
             enum "meticulous-keyed-sha-1" {
               description "Meticulous keyed secure hash algorithm (SHA1) ";
             }
           }
         }
         leaf loose-check {
           description "Verify authentication only if authentication is negotiated";
           type empty;
         }
       }
       leaf session-mode {
         description "BFD single-hop or multihop session-mode";
         default "automatic";
         type enumeration {
           enum "automatic" {
             description "Choose session-mode automatically";
           }
           enum "single-hop" {
             description "Use single-hop";
           }
           enum "multihop" {
             description "Use multihop";
           }
         }
       }
       leaf holddown-interval {
         description "Time to hold the session-UP notification to the client";
         units "milliseconds";
         type union {
           type string {
             pattern "<.*>|$.*";
           }
           type uint32 {
             range "0 .. 255000";
           }
         }
       }
     }
     container output-queue-priority {
       description "BGP output queue priority scheduler for updates";
       uses apply-advanced;
       container expedited {
         presence "enable expedited";
         description "Expedited queue; highest priority";
         leaf update-tokens {
           description "Number of tokens";
           type union {
             type string {
               pattern "<.*>|$.*";
             }
             type uint32 {
               range "1 .. 100";
             }
           }
         }
       }
       list priority {
         key name;
         description "Output queue priority 1..16; higher is better";
         leaf name {
           description "Output queue priority; higher is better";
           type union {
             type string {
               pattern "<.*>|$.*";
             }
             type uint32 {
               range "1 .. 16";
             }
           }
         }
         leaf update-tokens {
           description "Number of tokens";
           type union {
             type string {
               pattern "<.*>|$.*";
             }
             type uint32 {
               range "1 .. 100";
             }
           }
         }
       }
       container defaults {
         description "Map policy's priority class and BGP output-queue";
         uses apply-advanced;
         container low {
           description "Assign the 'low' priority class to this output-queue";
           uses bgp-output-queue-priority-class;
         }
         container medium {
           description "Assign the 'medium' priority class to this output-queue";
           uses bgp-output-queue-priority-class;
         }
         container high {
           description "Assign the 'high' priority class to this output-queue";
           uses bgp-output-queue-priority-class;
         }
       }
     }
     container multipath-build-priority {
       description "Configure the multipath build priority";
       uses apply-advanced;
       choice multipath-priority {
         case case_1 {
           leaf low {
             description "Do multipath build with low priority";
             type empty;
           }
         }
         case case_2 {
           leaf medium {
             description "Do multipath build with medium priority";
             type empty;
           }
         }
       }
     }
     leaf send-addpath-optimization {
       description "Enable BGP addpath advertisement optimization";
       type empty;
     }
     container defaults {
       uses apply-advanced;
       container ebgp {
         description "Options impacting external BGP default behaviors";
         uses apply-advanced;
         container no-policy {
           description "Default ebgp behaviors in the absence of configured policy";
           uses apply-advanced;
           leaf receive {
             description "Default ebgp receive behavior";
             type enumeration {
               enum "accept" {
                 description "By default, accept routes from all address families";
               }
               enum "reject" {
                 description "By default, reject routes from IPv4/IPv6 unicast address families";
               }
               enum "reject-always" {
                 description "By default, reject routes from all address families";
               }
             }
           }
           leaf advertise {
             description "Default ebgp advertise behavior";
             type enumeration {
               enum "accept" {
                 description "By default, advertise routes for all address families";
               }
               enum "reject" {
                 description "By default, do not advertise routes from IPv4/IPv6 unicast address families";
               }
               enum "reject-always" {
                 description "By default, do not advertise routes from any address families";
               }
             }
           }
         }
       }
     }
   }
   grouping bgp-af-gr {
     uses apply-advanced;
     container long-lived {
       description "Long-lived graceful restart options";
       uses apply-advanced;
       container restarter {
         description "Long-lived graceful restart restarter options";
         uses apply-advanced;
         choice enable-disable {
           case case_1 {
             leaf disable {
               description "Disable restarter functionality";
               type empty;
             }
           }
         }
         leaf stale-time {
           description "Stale time in seconds or dhms notation (1..16777215)";
           type string;
         }
       }
       container extended-route-retention {
         description "Extended route retention (LLGR-helper extended) options";
         uses apply-advanced;
         choice enable-disable {
           case case_1 {
             leaf disable {
               description "Disable extended-route-retention (LLGR-helper) functionality";
               type empty;
             }
           }
         }
         leaf retention-time {
           description "Retention time in seconds or dhms notation (1..16777215)";
           type string;
         }
         leaf-list retention-policy {
           ordered-by user;
           description "Retention policy for Extended Route Retention";
           type jt:policy-algebra;
         }
       }
     }
     leaf forwarding-state-bit {
       description "Control forwarding-state flag negotiation";
       type enumeration {
         enum "set" {
           description "Always set";
         }
         enum "from-fib" {
           description "Use state of associated FIB(s)";
         }
       }
     }
   }
   grouping bgp-afi-default {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
   }
   grouping apath-options {
     description "Number of paths to advertise";
     uses apply-advanced;
     leaf receive {
       description "Receive multiple paths from peer";
       type empty;
     }
     container send {
       presence "enable send";
       description "Send multiple paths to peer";
       uses apply-advanced;
       container path-selection-mode {
         description "Configure how to select add-path routes";
         uses apply-advanced;
         choice mode {
           case case_1 {
             leaf all-paths {
               description "Advertise all paths allowed by path count";
               type empty;
             }
           }
           case case_2 {
             leaf equal-cost-paths {
               description "Advertise equal cost paths";
               type empty;
             }
           }
         }
       }
       leaf-list prefix-policy {
         ordered-by user;
         description "Perform add-path only for prefixes that match policy";
         type jt:policy-algebra;
       }
       leaf path-count {
         description "Number of paths to advertise";
         type union {
           type string {
             pattern "<.*>|$.*";
           }
           type int32 {
             range "2 .. 64";
           }
         }
       }
       leaf include-backup-path {
         description "Number of backup paths to advertise";
         type union {
           type string {
             pattern "<.*>|$.*";
           }
           type int32 {
             range "1 .. 2";
           }
         }
       }
       leaf multipath {
         description "Include only multipath contributor routes";
         type empty;
       }
     }
   }
   grouping bgp-afi-flow {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     leaf allow-policy-add-nexthop {
       description "Allow policy to add nexthop to a route without nexthop";
       status deprecated;
       type empty;
     }
   }
   grouping bgp-afi-flow-with-redirect-ip-action {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     leaf-list no-validate {
       ordered-by user;
       description "Bypass validation procedure for routes that match policy";
       type jt:policy-algebra;
     }
     leaf strip-nexthop {
       description "Strip the next-hop from the outgoing flow update";
       type empty;
     }
     container legacy-redirect-ip-action {
       presence "enable legacy-redirect-ip-action";
       description "Configure legacy redirect to IP support";
       uses apply-advanced;
       leaf receive {
         description "Accept legacy encoded redirect-to-ip action attribute";
         type empty;
       }
       leaf send {
         description "Advertise Redirect action as legacy redirect attribute";
         type empty;
       }
     }
     leaf secondary-independent-resolution {
       description "Resolve FLOW routes in VRF table independent of VPN FLOW route";
       type empty;
     }
   }
   grouping bgp-afi-inet-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container protection {
       presence "enable protection";
       description "Compute backup path for active nexthop failure";
     }
   }
   grouping bgp-afi-inet6-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-group-label {
       description "Advertise prefixes with unique labels per group";
       type empty;
     }
     container traffic-statistics {
       description "Collect statistics for BGP label-switched paths";
       presence "enable traffic-statistics";
       uses bgpaf-traffic-statistics;
     }
     container rib {
       description "Select table used by labeled unicast routes";
       uses apply-advanced;
       leaf inet6.3 {
         description "Use inet6.3 to exchange labeled unicast routes";
         type empty;
       }
     }
     container explicit-null {
       presence "enable explicit-null";
       description "Advertise explicit null";
       leaf connected-only {
         description "Advertise explicit null only for connected routes";
         type empty;
       }
     }
     container protection {
       presence "enable protection";
       description "Compute backup path for active nexthop failure";
     }
     list topology {
       key name;
       ordered-by user;
       description "Multi topology routing tables";
       leaf name {
         description "Topology name";
         type string {
         }
       }
       uses apply-advanced;
       leaf community {
         description "Community to identify multi topology routes";
         type string;
       }
     }
   }
   grouping bgp-afi-inet6-transport {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     container lu-export {
       presence "enable lu-export";
       description "Install Classful Transport routes in inet6.3";
       uses apply-advanced;
     }
     container protection {
       presence "enable protection";
       description "Compute backup path for active nexthop failure";
     }
   }
   grouping bgp-afi-l2vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-afi-l3vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
     leaf accept-local-nexthop {
       description "Enable processing of routes with own nexthop";
       type empty;
     }
     leaf accept-own {
       description "Enable processing of routes with own originator-id or nexthop";
       type empty;
     }
   }
   grouping bgp-afi-labeled {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     leaf per-prefix-label {
       description "Allocate a unique label to each advertised prefix";
       type empty;
     }
     leaf per-group-label {
       description "Advertise prefixes with unique labels per group";
       type empty;
     }
     container traffic-statistics {
       description "Collect statistics for BGP label-switched paths";
       presence "enable traffic-statistics";
       uses bgpaf-traffic-statistics;
     }
     list topology {
       key name;
       ordered-by user;
       description "Multi topology routing tables";
       leaf name {
         description "Topology name";
         type string {
         }
       }
       uses apply-advanced;
       leaf community {
         description "Community to identify multi topology routes";
         type string;
       }
     }
     container rib {
       description "Select table used by labeled unicast routes";
       uses rib-inet3;
     }
     container explicit-null {
       presence "enable explicit-null";
       description "Advertise explicit null";
       leaf connected-only {
         description "Advertise explicit null only for connected routes";
         type empty;
       }
     }
     container protection {
       presence "enable protection";
       description "Compute backup path for active nexthop failure";
       uses apply-advanced;
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
     leaf resolve-vpn {
       description "Install received NLRI in inet.3 also";
       type empty;
     }
     container entropy-label {
       presence "enable entropy-label";
       description "Use entropy label for entropy label capable BGP LSPs";
       uses apply-advanced;
       leaf-list import {
         ordered-by user;
         description "Policy to select BGP LSPs to use entropy label";
         type jt:policy-algebra;
       }
       leaf no-next-hop-validation {
         description "Don't validate next hop field against route next hop";
         type empty;
       }
     }
   }
   grouping bgp-afi-srte {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     leaf damping {
       description "Enable route flap damping";
       type empty;
     }
     container loops {
       description "Allow local AS in received AS paths";
       uses bgpaf-loops;
     }
     container graceful-restart {
       description "BGP graceful restart options";
       uses bgp-af-gr;
     }
     leaf no-install {
       description "Dont install received routes in forwarding";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
   }
   grouping bgp-afi-topo {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container protection {
       presence "enable protection";
       description "Compute backup path for active nexthop failure";
     }
     list topology {
       key name;
       ordered-by user;
       description "Multi topology routing tables";
       leaf name {
         description "Topology name";
         type string {
         }
       }
       uses apply-advanced;
       leaf community {
         description "Community to identify multi topology routes";
         type string;
       }
     }
   }
   grouping bgp-afi-vpn {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
   }
   grouping bgp-afi-vpn-protection {
     uses apply-advanced;
     container prefix-limit {
       description "Limit maximum number of prefixes from a peer";
       uses bgpaf-prefix-limit;
     }
     container accepted-prefix-limit {
       description "Limit maximum number of prefixes accepted from a peer";
       uses bgpaf-accepted-prefix-limit;
     }
     container rib-group {
       description "Routing table group";
       uses rib_group_inet_type;
     }
     container add-path {
       description "Advertise multiple paths to peer";
       uses apath-options;
     }
     container aigp {
       description "Allow sending and receiving of AIGP attribute";
       presence "enable aigp";
       uses bgpaf-aigp-options;
     }
     leaf damping {
       description "Enable route flap damping";
       type empty;
     }
     leaf local-ipv4-address {
       description "Local IPv4 address";
       type jt:ipv4addr;
     }
     container loops {
       description "Allow local AS in received AS paths";
       uses bgpaf-loops;
     }
     container delay-route-advertisements {
       presence "enable delay-route-advertisements";
       description "Delay route updates for this family until FIB-sync";
       uses apply-advanced;
       leaf always-wait-for-krt-drain {
         description "Wait for KRT-queue drain for more-specific prefixes";
         type empty;
       }
       container minimum-delay {
         description "Minumum-delay to ensure KRT sees the route flash";
         uses apply-advanced;
         leaf routing-uptime {
           description "Min delay(sec) advertisement after RPD start";
           type union {
             type string {
               pattern "<.*>|$.*";
             }
             type uint32 {
               range "1 .. 36000";
             }
           }
         }
         leaf inbound-convergence {
           description "Min delay(sec) advertisement after source-peer sent all routes";
           type union {
             type string {
               pattern "<.*>|$.*";
             }
             type uint32 {
               range "1 .. 36000";
             }
           }
         }
       }
       container maximum-delay {
         description "Maximum delay deferring routes";
         uses apply-advanced;
         leaf route-age {
           description "Max delay(sec) advertisement route age";
           type union {
             type string {
               pattern "<.*>|$.*";
             }
             type uint32 {
               range "1 .. 36000";
             }
           }
         }
         leaf routing-uptime {
           description "Max delay(sec) advertisement after RPD start";
           type union {
             type string {
               pattern "<.*>|$.*";
             }
             type uint32 {
               range "1 .. 36000";
             }
           }
         }
       }
     }
     container nexthop-resolution {
       description "Configure nexthop resolution properties";
       uses apply-advanced;
       leaf no-resolution {
         description "Consider nexthop good without resolution attempt";
         type empty;
       }
       leaf preserve-nexthop-hierarchy {
         description "Attempt preserving resolved nexthop chain in forwarding";
         type empty;
       }
     }
     container defer-initial-multipath-build {
       presence "enable defer-initial-multipath-build";
       description "Defer initial multipath build until EOR is received";
       uses apply-advanced;
       leaf maximum-delay {
         description "Max delay(sec) multipath build after peer is up";
         type union {
           type string {
             pattern "<.*>|$.*";
           }
           type uint32 {
             range "1 .. 3600";
           }
         }
       }
     }
     container graceful-restart {
       description "BGP graceful restart options";
       uses bgp-af-gr;
     }
     leaf extended-nexthop {
       description "Extended nexthop encoding";
       type empty;
     }
     leaf extended-nexthop-color {
       description "Resolve using extended color nexthop";
       type empty;
     }
     leaf extended-nexthop-tunnel {
       description "Use BGP tunnel attribute";
       type empty;
     }
     leaf no-install {
       description "Dont install received routes in forwarding";
       type empty;
     }
     leaf route-age-bgp-view {
       description "Maintain BGP route's age based on Update messages only";
       type empty;
     }
     container output-queue-priority {
       description "Default output-queue to assign updates to";
       uses bgp-output-queue-priority-class;
     }
     container route-refresh-priority {
       description "Default output-queue to assign route refreshes to";
       uses bgp-output-queue-priority-class;
     }
     container withdraw-priority {
       description "Default output-queue to assign withdrawn routes to";
       uses bgp-output-queue-priority-class;
     }
     leaf advertise-srv6-service {
       description "Advertise SRv6 service";
       type empty;
     }
     leaf accept-srv6-service {
       description "Accept SRv6 service";
       type empty;
     }
     container aggregate-label {
       presence "enable aggregate-label";
       description "Aggregate labels of incoming routes with the same FEC";
       uses apply-advanced;
       leaf community {
         description "Community to identify the FEC of incoming routes";
         type string;
       }
     }
     container egress-protection {
       presence "enable egress-protection";
       description "Egress router protection";
       uses apply-advanced;
       container context-identifier {
         description "Context identifier";
         uses apply-advanced;
         leaf context-id {
           description "IP address";
           type jt:ipv4addr;
         }
       }
       leaf-list keep-import {
         ordered-by user;
         description "Import policy";
         type jt:policy-algebra;
       }
     }
   }
   grouping bgp-output-queue-priority-class {
     choice class {
       case case_1 {
         leaf priority {
           description "Output queue priority; higher is better";
           type union {
             type string {
               pattern "<.*>|$.*";
             }
             type uint32 {
               range "1 .. 16";
             }
           }
         }
       }
       case case_2 {
         leaf expedited {
           description "Expedited queue; highest priority";
           type empty;
         }
       }
     }
   }
   grouping bgp_filter_obj {
     description "Filter to apply to tracing";
     leaf match-on {
       description "Argument on which to match";
       type enumeration {
         enum "prefix" {
           description "Filter based on prefix";
         }
       }
     }
     leaf-list policy {
       ordered-by user;
       description "Filter policy";
       type jt:policy-algebra;
     }
   }
   grouping bgpaf-accepted-prefix-limit {
     uses apply-advanced;
     leaf maximum {
       description "Maximum number of prefixes accepted from a peer";
       type union {
         type string {
           pattern "<.*>|$.*";
         }
         type uint32 {
           range "1 .. 4294967295";
         }
       }
     }
     container teardown {
       presence "enable teardown";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-aigp-options {
     uses apply-advanced;
     leaf disable {
       description "Disable sending and receiving of AIGP attribute";
       type empty;
     }
   }
   grouping bgpaf-loops {
     uses apply-advanced;
     leaf loops {
       description "AS-Path loop count";
       type union {
         type string {
           pattern "<.*>|$.*";
         }
         type int32 {
           range "1 .. 10";
         }
       }
     }
   }
   grouping bgpaf-prefix-limit {
     uses apply-advanced;
     leaf maximum {
       description "Maximum number of prefixes from a peer";
       type union {
         type string {
           pattern "<.*>|$.*";
         }
         type uint32 {
           range "1 .. 4294967295";
         }
       }
     }
     container teardown {
       presence "enable teardown";
       description "Clear peer connection on reaching limit";
       uses apply-advanced;
       leaf limit-threshold {
         description "Percentage of prefix-limit to start warnings";
         type union {
           type string {
             pattern "<.*>|$.*";
           }
           type uint32 {
             range "1 .. 100";
           }
         }
       }
       container idle-timeout {
         presence "enable idle-timeout";
         description "Timeout before attempting to restart peer";
         choice idle-parm {
           case case_1 {
             leaf forever {
               description "Idle the peer until the user intervenes";
               type empty;
             }
           }
           case case_2 {
             leaf timeout {
               description "Timeout value, in minutes, for restarting peer";
               type union {
                 type string {
                   pattern "<.*>|$.*";
                 }
                 type uint32 {
                   range "1 .. 2400";
                 }
               }
             }
           }
         }
       }
     }
     container drop-excess {
       presence "enable drop-excess";
       description "Drop routes from peer on reaching limit";
       uses apply-advanced;
       leaf limit-threshold {
         description "Percentage of prefix-limit to start warnings";
         type union {
           type string {
             pattern "<.*>|$.*";
           }
           type uint32 {
             range "1 .. 100";
           }
         }
       }
     }
     container hide-excess {
       presence "enable hide-excess";
       description "Hide routes from peer on reaching limit";
       uses apply-advanced;
       leaf limit-threshold {
         description "Percentage of prefix-limit to start warnings";
         type union {
           type string {
             pattern "<.*>|$.*";
           }
           type uint32 {
             range "1 .. 100";
           }
         }
       }
     }
   }
   grouping bgpaf-traffic-statistics {
     uses apply-advanced;
     leaf labeled-path {
       description "Ingress labeled path statistics";
       type empty;
     }
     container file {
       description "Statistics file options";
       leaf filename {
         description "Name of file in which to write trace information";
         type string {
           length "1 .. 1024";
         }
       }
       leaf replace {
         description "Replace trace file rather than appending to it";
         status deprecated;
         type empty;
       }
       leaf size {
         description "Maximum trace file size";
         type string;
       }
       leaf files {
         description "Maximum number of trace files";
         default "10";
         type union {
           type string {
             pattern "<.*>|$.*";
           }
           type uint32 {
             range "2 .. 1000";
           }
         }
       }
       leaf no-stamp {
         description "Do not timestamp trace file";
         status deprecated;
         type empty;
       }
       choice world-readable-choice {
         leaf world-readable {
           description "Allow any user to read the log file";
           type empty;
         }
         leaf no-world-readable {
           description "Don't allow any user to read the log file";
           type empty;
         }
       }
     }
     leaf interval {
       description "Time to collect statistics (seconds)";
       type union {
         type string {
           pattern "<.*>|$.*";
         }
         type int32 {
           range "60 .. 65535";
         }
       }
     }
   }
   grouping macro-data-type {
     leaf name {
       description "Keyword part of the keyword-value pair";
       type string;
     }
     leaf value {
       description "Value part of the keyword-value pair";
       type string;
     }
   }
   grouping rib-inet3 {
     uses apply-advanced;
     container inet.3 {
       presence "enable inet.3";
       description "Use inet.3 to exchange labeled unicast routes";
       uses apply-advanced;
     }
   }
   grouping rib_group_inet_type {
     description "Routing table group";
     leaf ribgroup-name {
       description "Name of the routing table group";
       type string;
     }
   }
 }
