/*
 * Copyright (c) 2022 Juniper Networks, Inc.
 * All rights reserved.
 */
 module junos-nfx-rpc-security {
   namespace "http://yang.juniper.net/junos-nfx/rpc/security";

   prefix security;

   import junos-common-types {
     prefix jt;
     revision-date 2022-01-01;
   }

   organization "Juniper Networks, Inc.";

   contact "yang-support@juniper.net";

   description "Junos RPC YANG module for security command(s)";

   revision 2022-01-01 {
     description "Junos: 22.4R1.10";
   }

   rpc get-security-alarm-information {
     description "Show active security alarm information";
     input {
       leaf alarm-id {
         description "Alarm ID filter";
         type union {
           type uint32;
           type string {
             pattern "<.*>|$.*";
           }
         }
       }
       leaf-list alarm-type {
         ordered-by user;
         description "Alarm type filter";
         type enumeration {
           enum "authentication" {
             description "Authentication alarms";
           }
           enum "cryptographic-self-test" {
             description "Cryptographic self-test alarms";
           }
           enum "decryption-failures" {
             description "Decryption failure alarms";
           }
           enum "encryption-failures" {
             description "Encryption failure alarms";
           }
           enum "ike-phase1-failures" {
             description "IKE Phase 1 failure alarms";
           }
           enum "ike-phase2-failures" {
             description "IKE Phase 2 failure alarms";
           }
           enum "key-generation-self-test" {
             description "Key generation self-test alarms";
           }
           enum "non-cryptographic-self-test" {
             description "Non-cryptographic self-test alarms";
           }
           enum "policy" {
             description "Policy alarms";
           }
           enum "replay-attacks" {
             description "Replay attack alarms";
           }
           enum "idp" {
             description "IDP attack alarms";
           }
         }
       }
       leaf newer-than {
         description "Alarms newer than filter (YYYY-MM-DD.HH:MM:SS)";
         type jt:time;
       }
       leaf older-than {
         description "Alarms older than filter (YYYY-MM-DD.HH:MM:SS)";
         type jt:time;
       }
       leaf process {
         description "Process that generated the alarm filter";
         type string;
       }
       leaf severity {
         description "Severity of the alarm filter";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf style {
         type enumeration {
           enum "detail" {
             description "Show detail alarm information";
           }
         }
       }
     }
     output {
       choice output_c {
         case output-tag {
           leaf output {
             type string;
           }
         }
         case actual-tag {
           anyxml security-alarm-information;
         }
         case multichassis-tag {
           anyxml multi-routing-engine-results;
         }
       }
     }
   }
   rpc get-security-log-information {
     description "Show auditable security log information";
     input {
       leaf destination-address {
         description "Destination address and optional prefix length";
         type jt:ipprefix-optional;
       }
       leaf destination-port {
         description "Destination port";
         type union {
           type uint32;
           type string {
             pattern "<.*>|$.*";
           }
         }
       }
       leaf event-id {
         description "Event ID filter";
         type string;
       }
       leaf interface-name {
         description "Name of interface";
         type string;
       }
       leaf older-than {
         description "Events older than filter (YYYY-MM-DD.HH:MM:SS)";
         type jt:time;
       }
       leaf policy-name {
         description "Policy name filter";
         type string;
       }
       leaf process {
         description "Process that generated the event";
         type string;
       }
       leaf protocol {
         description "Protocol filter";
         type string;
       }
       leaf newer-than {
         description "Events newer than filter (YYYY-MM-DD.HH:MM:SS)";
         type jt:time;
       }
       leaf result {
         type enumeration {
           enum "failure" {
             description "Event was a failure";
           }
           enum "success" {
             description "Event was successful";
           }
         }
       }
       leaf severity {
         description "Severity of the event";
         type enumeration {
           enum "alert" {
             description "Alert severity";
           }
           enum "crit" {
             description "Critical severity";
           }
           enum "debug" {
             description "Debug severity";
           }
           enum "emerg" {
             description "Emergency severity";
           }
           enum "err" {
             description "Error severity";
           }
           enum "info" {
             description "Information severity";
           }
           enum "notice" {
             description "Notice severity";
           }
           enum "warning" {
             description "Warning severity";
           }
         }
       }
       leaf source-address {
         description "Source address and optional prefix length";
         type jt:ipprefix-optional;
       }
       leaf source-port {
         description "Source port";
         type union {
           type uint32;
           type string {
             pattern "<.*>|$.*";
           }
         }
       }
       leaf username {
         description "Username filter";
         type string;
       }
       leaf sort-by {
         description "Sort by selected field";
         default "time";
         type enumeration {
           enum "destination-address" {
             description "Sort by destination address";
           }
           enum "destination-port" {
             description "Sort by destination port";
           }
           enum "interface-name" {
             description "Sort by interface name";
           }
           enum "policy-name" {
             description "Sort by policy name";
           }
           enum "protocol" {
             description "Sort by protocol";
           }
           enum "source-address" {
             description "Sort by source address";
           }
           enum "source-port" {
             description "Sort by source port";
           }
           enum "time" {
             description "Sort by time of event arrival";
           }
           enum "username" {
             description "Sort by event user name ";
           }
         }
       }
       leaf direction {
         default "ascending";
         type enumeration {
           enum "ascending" {
             description "Sort in ascending order";
           }
           enum "descending" {
             description "Sort in descending order";
           }
         }
       }
       leaf style {
         type enumeration {
           enum "detail" {
             description "Show detail alarm information";
           }
         }
       }
     }
     output {
       choice output_c {
         case output-tag {
           leaf output {
             type string;
           }
         }
         case actual-tag {
           anyxml security-log-information;
         }
         case multichassis-tag {
           anyxml multi-routing-engine-results;
         }
       }
     }
   }
   rpc get-security-hpl-infile {
     description "Show security logs in binary format";
     input {
       leaf file_name {
         description "Name of the binary log file to be displayed ";
         type string {
           length "1 .. 256";
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       choice output_c {
         case output-tag {
           leaf output {
             type string;
           }
         }
         case actual-tag {
           anyxml show-hpl-infile;
         }
         case multichassis-tag {
           anyxml multi-routing-engine-results;
         }
       }
     }
   }
   rpc get-security-hpl-infile-last {
     description "Show recent security logs in binary format";
     input {
       leaf seconds {
         description "Number of seconds of binary logs to display";
         type union {
           type uint32;
           type string {
             pattern "<.*>|$.*";
           }
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       choice output_c {
         case output-tag {
           leaf output {
             type string;
           }
         }
         case actual-tag {
           anyxml show-hpl-infile;
         }
         case multichassis-tag {
           anyxml multi-routing-engine-results;
         }
       }
     }
   }
   rpc get-security-stream-hpl-infile {
     description "Show security logs stream file";
     input {
       leaf file-name {
         description "Name of the stream log file to be displayed ";
         type string {
           length "1 .. 256";
         }
         mandatory true;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       choice output_c {
         case output-tag {
           leaf output {
             type string;
           }
         }
         case actual-tag {
           anyxml show-hpl-infile;
         }
         case multichassis-tag {
           anyxml multi-routing-engine-results;
         }
       }
     }
   }
   rpc get-security-log-query {
     description "Query logs from database";
     input {
       leaf category {
         description "Category name";
         type enumeration {
           enum "all" {
             description "Category all";
           }
           enum "utm" {
             description "Utm";
           }
           enum "fw-auth" {
             description "Fw-auth";
           }
           enum "screen" {
             description "Screen";
           }
           enum "alg" {
             description "Alg";
           }
           enum "nat" {
             description "Nat";
           }
           enum "flow" {
             description "Flow";
           }
           enum "sctp" {
             description "Sctp";
           }
           enum "gtp" {
             description "Gtp";
           }
           enum "ipsec" {
             description "Ipsec";
           }
           enum "idp" {
             description "Idp";
           }
           enum "rtlog" {
             description "Rtlog";
           }
           enum "pst-ds-lite" {
             description "Pst-ds-lite";
           }
           enum "appqos" {
             description "Appqos";
           }
           enum "secintel" {
             description "Secintel";
           }
           enum "aamw" {
             description "AAMW";
           }
         }
         mandatory true;
       }
       leaf count {
         description "Number of logs to be queried";
         type union {
           type uint32;
           type string {
             pattern "<.*>|$.*";
           }
         }
       }
       leaf src-ip {
         description "Filter source ip";
         type jt:ipaddr;
       }
       leaf dst-ip {
         description "Filter destination ip";
         type jt:ipaddr;
       }
       leaf src-port {
         description "Filter source port";
         type union {
           type string {
             pattern "<.*>|$.*";
           }
           type uint16 {
             range "1 .. 65535";
           }
         }
       }
       leaf dst-port {
         description "Filter destination port";
         type union {
           type string {
             pattern "<.*>|$.*";
           }
           type uint16 {
             range "1 .. 65535";
           }
         }
       }
       leaf application {
         description "Filter application";
         type string {
           length "1 .. 64";
         }
       }
       leaf user {
         description "Filter user";
         type string {
           length "1 .. 64";
         }
       }
       leaf service {
         description "Filter service";
         type string {
           length "1 .. 64";
         }
       }
       leaf event-type {
         description "Filter event-type";
         type string {
           length "1 .. 64";
         }
       }
       leaf start-time {
         description "Earliest timestamp to include in output (YYYY-MM-DDTHH:MM:SS)";
         type jt:time;
       }
       leaf stop-time {
         description "Latest timestamp to include in output (YYYY-MM-DDTHH:MM:SS)";
         type jt:time;
       }
     }
     output {
       choice output_c {
         case output-tag {
           leaf output {
             type string;
           }
         }
         case actual-tag {
           anyxml show-hpl-infile;
         }
         case multichassis-tag {
           anyxml multi-routing-engine-results;
         }
       }
     }
   }
   rpc get-security-log-profile-template {
     description "Show security log profile template info";
     input {
       leaf template-name {
         description "Specify the rtlog profile template name";
         type enumeration {
           enum "sd-wan" {
             description "Template sd-wan";
           }
           enum "unified-ngfw" {
             description "Template unified-ngfw";
           }
           enum "traditional-firewall" {
             description "Template traditional-firewall";
           }
         }
         mandatory true;
       }
     }
     output {
       choice output_c {
         case output-tag {
           leaf output {
             type string;
           }
         }
         case actual-tag {
           anyxml security-log-profile-template;
         }
         case multichassis-tag {
           anyxml multi-routing-engine-results;
         }
       }
     }
   }
   rpc get-security-log-profile-config {
     description "Show security log profile config info";
     input {
       leaf profile-name {
         description "Specify the rtlog profile name";
         type string {
           length "1 .. 64";
         }
         mandatory true;
       }
     }
     output {
       choice output_c {
         case output-tag {
           leaf output {
             type string;
           }
         }
         case actual-tag {
           anyxml security-log-profile-config;
         }
         case multichassis-tag {
           anyxml multi-routing-engine-results;
         }
       }
     }
   }
   rpc get-tpm-status {
     description "Show TPM status";
     input {
       choice daemon-select {
         case logical-system {
           leaf logical-system {
             description "Name of logical system, or 'all'";
             type string {
             }
           }
         }
       }
     }
     output {
       choice output_c {
         case output-tag {
           leaf output {
             type string;
           }
         }
         case actual-tag {
           anyxml tpm-status;
         }
         case multichassis-tag {
           anyxml multi-routing-engine-results;
         }
       }
     }
   }
   rpc get-hsm-status {
     description "Show HSM status";
     output {
       choice output_c {
         case output-tag {
           leaf output {
             type string;
           }
         }
         case actual-tag {
           anyxml hsm-status;
         }
         case multichassis-tag {
           anyxml multi-routing-engine-results;
         }
       }
     }
   }
   rpc get-pki-certificate-request {
     description "Show PKCS-10 certificate request information";
     input {
       uses command-forwarding;
       choice daemon-select {
         case logical-system {
         }
       }
       leaf certificate-id {
         description "Certificate identifier";
         type string {
           length "1 .. 32";
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-ca-certificate {
     description "Show certificate-authority certificate information";
     input {
       uses command-forwarding;
       choice daemon-select {
         case logical-system {
         }
       }
       choice ca-cert-choice {
         case ca-profile {
           leaf ca-profile {
             description "Certificate authority profile";
             type string {
               length "1 .. 32";
             }
           }
         }
         case ca-profile-group {
           leaf ca-profile-group {
             description "Show CA profile group";
             type string {
               length "1 .. 32";
             }
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-node-local-local-certificate {
     description "Show router certificate information";
     input {
       uses command-forwarding;
       choice daemon-select {
         case logical-system {
         }
       }
       choice certificate-choice {
         case certificate-id {
           leaf certificate-id {
             description "Certificate identifier";
             type string {
               length "1 .. 32";
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-node-local-certificate-request {
     description "Show PKCS-10 certificate request information";
     input {
       uses command-forwarding;
       choice daemon-select {
         case logical-system {
         }
       }
       leaf certificate-id {
         description "Certificate identifier";
         type string {
           length "1 .. 32";
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-local-certificate {
     description "Show router certificate information";
     input {
       uses command-forwarding;
       choice daemon-select {
         case logical-system {
         }
       }
       choice certificate-choice {
         case certificate-id {
           leaf certificate-id {
             description "Certificate identifier";
             type string {
               length "1 .. 32";
             }
           }
         }
         case system-generated {
           leaf system-generated {
             description "Autogenerated self-signed certificate";
             type empty;
           }
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pki-certificate-info-list;
         }
         case multichassis-tag {
           anyxml multi-routing-engine-results;
         }
       }
     }
   }
   rpc get-pki-crl {
     description "Show certificate revocation list information";
     input {
       uses command-forwarding;
       choice daemon-select {
         case logical-system {
         }
       }
       leaf ca-profile {
         description "Certificate authority profile";
         type string {
           length "1 .. 32";
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml x509-pkid-crl-information-list;
         }
         case multichassis-tag {
           anyxml multi-routing-engine-results;
         }
       }
     }
   }
   rpc get-pki-statistics {
     description "Show PKI related statistics";
     input {
       uses command-forwarding;
       choice daemon-select {
         case logical-system {
         }
       }
       leaf level {
         default "brief";
         type enumeration {
           enum "brief" {
             description "Display brief output";
           }
           enum "detail" {
             description "Display detailed output";
           }
         }
       }
     }
     output {
       choice output_c {
         case output-tag {
           leaf output {
             type string;
           }
         }
         case actual-tag {
           anyxml pki-statistics;
         }
         case multichassis-tag {
           anyxml multi-routing-engine-results;
         }
       }
     }
   }
   rpc get-pending-redistribution-cmds {
     description "Show tunnel migration commands in the pending state";
     input {
       uses command-forwarding;
       leaf gateway-name {
         description "Gateway name";
         type string {
           length "1 .. 32";
         }
       }
     }
     output {
       choice output_c {
         case output-tag {
           leaf output {
             type string;
           }
         }
         case actual-tag {
           anyxml pending-redistribution-cmds;
         }
         case multichassis-tag {
           anyxml multi-routing-engine-results;
         }
       }
     }
   }
   rpc get-security-associations-information {
     description "Show IPSec security association information";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf sa-type {
         description "Show IPSec security association by type";
         type enumeration {
           enum "shortcut" {
             description "Show Shortcut SAs";
           }
         }
       }
       leaf show-index-ipsec-security-association {
         description "Index of security association";
         type union {
           type string {
             pattern "<.*>|$.*";
           }
           type uint32 {
             range "1 .. 4294967295";
           }
         }
       }
       leaf show-srg-id-ipsec-security-association {
         description "Index of srg-id";
         type union {
           type string {
             pattern "<.*>|$.*";
           }
           type uint32 {
             range "1 .. 20";
           }
         }
       }
       leaf show-vpnname-ipsec-security-association {
         description "VPN name";
         default "all";
         type string;
       }
       leaf show-trafficselectorname-ipsec-security-association {
         description "Traffic-selector name";
         default "all";
         type string;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
       leaf service-set {
         description "Restrict output to one service set";
         default "all";
         type string {
         }
       }
     }
     output {
       choice output_c {
         case output-tag {
           leaf output {
             type string;
           }
         }
         case actual-tag {
           anyxml security-associations-information;
         }
         case multichassis-tag {
           anyxml multi-routing-engine-results;
         }
       }
     }
   }
   rpc get-ha-link-encryptioninformation {
     description "Show IPSec security association for HA Link Encryption";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
       leaf show-vpnname-ipsec-security-association {
         description "VPN name";
         default "all";
         type string;
       }
     }
     output {
       choice output_c {
         case output-tag {
           leaf output {
             type string;
           }
         }
         case actual-tag {
           anyxml security-associations-information;
         }
         case multichassis-tag {
           anyxml multi-routing-engine-results;
         }
       }
     }
   }
   rpc get-control-plane-security-associations-information {
     description "Show IPSec control plane security association information";
     input {
       uses command-forwarding;
       leaf level {
         default "brief";
         type enumeration {
           enum "brief" {
             description "Display brief output";
           }
           enum "detail" {
             description "Display detailed output";
           }
         }
       }
       leaf show-saname-ipsec-control-plane-security-association {
         description "SA name";
         default "all";
         type string;
       }
       leaf show-ha-link-ipsec-statistics {
         description "Show statistics for ha-link encryption tunnel";
         type empty;
       }
     }
     output {
       choice output_c {
         case output-tag {
           leaf output {
             type string;
           }
         }
         case actual-tag {
           anyxml control-plane-security-associations-information;
         }
         case multichassis-tag {
           anyxml multi-routing-engine-results;
         }
       }
     }
   }
   rpc get-ipsec-statistics-information {
     description "Show IPSec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf show-index-ipsec-statistics {
         description "Index of Security Association";
         type union {
           type string {
             pattern "<.*>|$.*";
           }
           type uint32 {
             range "1 .. 4294967295";
           }
         }
       }
       leaf show-ha-link-encryption-ipsec-stats {
         description "Show statistics for ha-link encryption tunnel";
         type empty;
       }
       leaf show-srg-ipsec-statistics {
         description "Show statistics for srg";
         type union {
           type string {
             pattern "<.*>|$.*";
           }
           type uint32 {
             range "1 .. 20";
           }
         }
       }
       leaf service-set {
         description "Name of service set";
         default "all";
         type string;
       }
     }
     output {
       choice output_c {
         case output-tag {
           leaf output {
             type string;
           }
         }
         case actual-tag {
           anyxml usp-ipsec-total-statistics-information;
         }
         case multichassis-tag {
           anyxml multi-routing-engine-results;
         }
       }
     }
   }
   rpc get-inactive-tunnels {
     description "Inactive-tunnels";
     input {
       uses command-forwarding;
       leaf level {
         default "brief";
         type enumeration {
           enum "brief" {
             description "Display brief output";
           }
           enum "detail" {
             description "Display detailed output";
           }
         }
       }
       leaf family {
         description "Show IPSec security association information by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
       leaf show-srg-id-ipsec-security-association {
         description "Index of srg-id";
         type union {
           type string {
             pattern "<.*>|$.*";
           }
           type uint32 {
             range "1 .. 20";
           }
         }
       }
       leaf show-vpnname-ipsec-security-association {
         description "VPN name";
         default "all";
         type string;
       }
       leaf sa-type {
         description "Show inactive IPSec SAs by type";
         type enumeration {
           enum "shortcut" {
             description "Show Shortcut SAs";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml ipsec-unestablished-tunnel-information;
         }
         case multichassis-tag {
           anyxml multi-routing-engine-results;
         }
       }
     }
   }
   rpc get-l2-ha-inactive-tunnels {
     description "Show inactive IPSec security association for HA Link Encryption";
     input {
       uses command-forwarding;
       leaf level {
         default "brief";
         type enumeration {
           enum "brief" {
             description "Display brief output";
           }
           enum "detail" {
             description "Display detailed output";
           }
         }
       }
       leaf show-index-ipsec-security-association {
         description "Index of security association";
         type union {
           type string {
             pattern "<.*>|$.*";
           }
           type uint32 {
             range "1 .. 4294967295";
           }
         }
       }
       leaf show-vpnname-ipsec-security-association {
         description "VPN name";
         default "all";
         type string;
       }
     }
     output {
       choice output_c {
         case output-tag {
           leaf output {
             type string;
           }
         }
         case actual-tag {
           anyxml ipsec-unestablished-tunnel-information;
         }
         case multichassis-tag {
           anyxml multi-routing-engine-results;
         }
       }
     }
   }
   rpc get-ipsec-next-hop-tunnel-information {
     description "Show manual and auto next-hop-tunnel entries";
     input {
       uses command-forwarding;
       leaf interface-name {
         description "Name of secure tunnel logical interface";
         default "all";
         type string;
       }
       leaf family {
         description "Show IPSec next-hop-tunnel entries by family";
         default "inet";
         type enumeration {
           enum "inet" {
             description "Show IPv4";
           }
           enum "inet6" {
             description "Show IPv6";
           }
         }
       }
       leaf show-index-ipsec-security-association {
         description "Index of security association";
         type union {
           type string {
             pattern "<.*>|$.*";
           }
           type uint32 {
             range "1 .. 4294967295";
           }
         }
       }
     }
     output {
       choice output_c {
         case output-tag {
           leaf output {
             type string;
           }
         }
         case actual-tag {
           anyxml usp-ipsec-next-hop-tunnel-information;
         }
         case multichassis-tag {
           anyxml multi-routing-engine-results;
         }
       }
     }
   }
   rpc get-ipsec-traffic-selector-information {
     description "Show traffic-selector information for a st0 interface";
     input {
       uses command-forwarding;
       leaf interface-name {
         description "Name of secure tunnel logical interface";
         type string;
         mandatory true;
       }
       leaf source-address {
         description "Source IP address";
         type jt:ipprefix-mandatory;
       }
       leaf destination-address {
         description "Destination IP address";
         type jt:ipprefix-mandatory;
       }
       leaf protocol {
         description "TS protocol id";
         type string;
       }
       leaf source-port {
         description "TS source port number";
         type string;
       }
       leaf destination-port {
         description "TS destination port number";
         type string;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml usp-ipsec-traffic-selector-information;
         }
         case multichassis-tag {
           anyxml multi-routing-engine-results;
         }
       }
     }
   }
   rpc get-ipsec-tunnel-event-statistics {
     description "Show tunnel event statstics";
     output {
       choice output_c {
         case output-tag {
           leaf output {
             type string;
           }
         }
         case actual-tag {
           anyxml ipsec-tunnel-event-statistics;
         }
         case multichassis-tag {
           anyxml multi-routing-engine-results;
         }
       }
     }
   }
   rpc get-ipsec-tunnel-distribution {
     description "Show tunnel distribution";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf level {
         default "brief";
         type enumeration {
           enum "brief" {
             description "Display brief IPsec tunnel-distribution (default)";
           }
           enum "summary" {
             description "Display IPsec tunnel-distribution summary info";
           }
           enum "summary-cpuload" {
             description "Display IPsec tunnel-distribution summary info with CPU load";
           }
         }
       }
       leaf srg-id {
         description "Index of srg-id";
         type union {
           type string {
             pattern "<.*>|$.*";
           }
           type uint32 {
             range "1 .. 20";
           }
         }
       }
     }
     output {
       choice output_c {
         case output-tag {
           leaf output {
             type string;
           }
         }
         case actual-tag {
           anyxml ipsec-tunnel-distribution-information;
         }
         case multichassis-tag {
           anyxml multi-routing-engine-results;
         }
       }
     }
   }
   rpc get-pre-shared-key {
     description "Show IKE pre-shared key information for a particular group-ike-id user";
     input {
       uses command-forwarding;
       leaf user-id {
         description "IKE user-id value";
         type string {
           length "1 .. 255";
         }
         mandatory true;
       }
       choice ike-psk {
         case master-key {
           leaf master-key {
             description "Master pre-shared key";
             type string {
               length "1 .. 255";
             }
             mandatory true;
           }
         }
         case gateway-name {
           leaf gateway-name {
             description "Gateway name";
             type string {
               length "1 .. 32";
             }
           }
         }
       }
     }
     output {
       choice output_c {
         case output-tag {
           leaf output {
             type string;
           }
         }
         case actual-tag {
           anyxml ike-show-pre-shared-key-information;
         }
         case multichassis-tag {
           anyxml multi-routing-engine-results;
         }
       }
     }
   }
   rpc get-ike-config-management-statistics {
     description "Show IKE configuration management daemon statistics";
     input {
       uses command-forwarding;
       leaf level {
         default "brief";
         type enumeration {
           enum "brief" {
             description "Display brief(Non-zero) output";
           }
           enum "detail" {
             description "Display detailed(including zeros) output";
           }
         }
       }
     }
     output {
       choice output_c {
         case output-tag {
           leaf output {
             type string;
           }
         }
         case actual-tag {
           anyxml ike-config-management-statistics-information;
         }
         case multichassis-tag {
           anyxml multi-routing-engine-results;
         }
       }
     }
   }
   rpc get-ike-config-management-snmp-stats {
     description "Show SNMP walk/get/get-next statistics";
     input {
       leaf level {
         default "brief";
         type enumeration {
           enum "brief" {
             description "Display brief(Non-zero) output";
           }
           enum "detail" {
             description "Display detailed(including zeros) output";
           }
         }
       }
     }
     output {
       choice output_c {
         case output-tag {
           leaf output {
             type string;
           }
         }
         case actual-tag {
           anyxml ike-config-management-snmp-stats;
         }
         case multichassis-tag {
           anyxml multi-routing-engine-results;
         }
       }
     }
   }
   rpc get-ike-config-management-memory-stats {
     description "Show IKEMD memory statistics";
     input {
       leaf level {
         default "brief";
         type enumeration {
           enum "brief" {
             description "Display brief(Non-zero) output";
           }
           enum "detail" {
             description "Display detailed(including zeros) output";
           }
         }
       }
     }
     output {
       choice output_c {
         case output-tag {
           leaf output {
             type string;
           }
         }
         case actual-tag {
           anyxml ike-config-management-memory-stats;
         }
         case multichassis-tag {
           anyxml multi-routing-engine-results;
         }
       }
     }
   }
   rpc get-ike-config-management-manual-sa-stats {
     description "Show manual-sa config related statistics";
     input {
       leaf level {
         default "brief";
         type enumeration {
           enum "brief" {
             description "Display brief(Non-zero) output";
           }
           enum "detail" {
             description "Display detailed(including zeros) output";
           }
         }
       }
     }
     output {
       choice output_c {
         case output-tag {
           leaf output {
             type string;
           }
         }
         case actual-tag {
           anyxml ike-config-management-manual-sa-stats;
         }
         case multichassis-tag {
           anyxml multi-routing-engine-results;
         }
       }
     }
   }
   rpc get-ike-security-associations-information {
     description "Show IKE security association information";
     input {
       uses command-forwarding;
       leaf peer-address {
         description "IP address of the peer";
         type jt:ipaddr;
       }
       leaf level {
         default "brief";
         type enumeration {
           enum "brief" {
             description "Show brief output (default)";
           }
           enum "detail" {
             description "Show detailed output";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
       leaf family {
         description "Show IKE security association by family";
         default "inet";
         type enumeration {
           enum "inet" {
             description "Show IPv4";
           }
           enum "inet6" {
             description "Show IPv6";
           }
         }
       }
       leaf show-index-ike-security-association {
         description "Index of security association";
         type union {
           type string {
             pattern "<.*>|$.*";
           }
           type uint32 {
             range "1 .. 4294967295";
           }
         }
       }
       leaf show-srg-id-ike-security-association {
         description "Index of srg-id";
         type union {
           type string {
             pattern "<.*>|$.*";
           }
           type uint32 {
             range "1 .. 20";
           }
         }
       }
       leaf sa-type {
         description "Show IKE security association by type";
         type enumeration {
           enum "shortcut" {
             description "Show Shortcut SAs";
           }
         }
       }
     }
     output {
       choice output_c {
         case output-tag {
           leaf output {
             type string;
           }
         }
         case actual-tag {
           anyxml ike-security-associations-information;
         }
         case multichassis-tag {
           anyxml multi-routing-engine-results;
         }
       }
     }
   }
   rpc get-l2-ha-ike-security-associations-information {
     description "Show IKE security association for HA Link Encryption";
     input {
       uses command-forwarding;
       leaf peer-address {
         description "IP address of the peer";
         type jt:ipaddr;
       }
       leaf level {
         default "brief";
         type enumeration {
           enum "brief" {
             description "Show brief output (default)";
           }
           enum "detail" {
             description "Show detailed output";
           }
         }
       }
       leaf show-index-ike-security-association {
         description "Index of security association";
         type union {
           type string {
             pattern "<.*>|$.*";
           }
           type uint32 {
             range "1 .. 4294967295";
           }
         }
       }
     }
     output {
       choice output_c {
         case output-tag {
           leaf output {
             type string;
           }
         }
         case actual-tag {
           anyxml ike-security-associations-information;
         }
         case multichassis-tag {
           anyxml multi-routing-engine-results;
         }
       }
     }
   }
   rpc get-ike-active-peers-information {
     description "Show IKE active peers ";
     input {
       uses command-forwarding;
       leaf level {
         default "brief";
         type enumeration {
           enum "brief" {
             description "Display brief output";
           }
           enum "detail" {
             description "Display detailed output";
           }
           enum "stats" {
             description "Display detailed output along with stats";
           }
         }
       }
       leaf peer-address {
         description "IP of peer";
         type jt:ipaddr;
       }
       leaf local-address {
         description "Local gateway IP address";
         type jt:ipaddr;
       }
       leaf port {
         description "Port number of peer";
         type union {
           type string {
             pattern "<.*>|$.*";
           }
           type uint32 {
             range "1 .. 65535";
           }
         }
       }
       leaf local-port {
         description "Local gateway port number";
         type union {
           type string {
             pattern "<.*>|$.*";
           }
           type uint32 {
             range "1 .. 65535";
           }
         }
       }
       leaf ha-link-encryption {
         description "Show IKE active peers for HA link encryption";
         type empty;
       }
       leaf ike-id {
         description "IKE ID";
         default "all";
         type string;
       }
       leaf local-ike-id {
         description "Local gateway IKE ID";
         default "all";
         type string;
       }
       leaf srg-id {
         description "Index of srg-id";
         type union {
           type string {
             pattern "<.*>|$.*";
           }
           type uint32 {
             range "1 .. 20";
           }
         }
       }
       leaf routing-instance {
         description "Name of the local gateway routing-instance";
         default "all";
         type string;
       }
       leaf aaa-username {
         description "AAA username";
         default "all";
         type string;
       }
       leaf debug {
         description "Show additional peer-entry debug information";
         type empty;
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml ike-active-peers-information;
         }
         case multichassis-tag {
           anyxml multi-routing-engine-results;
         }
       }
     }
   }
   rpc get-config-ike-debug {
     description "Show current enabled IKE debug information";
     output {
       choice output_c {
         case output-tag {
           leaf output {
             type string;
           }
         }
         case actual-tag {
           anyxml security-ike-debug-info;
         }
         case multichassis-tag {
           anyxml multi-routing-engine-results;
         }
       }
     }
   }
   rpc get-iked-tunnel-mapping-information {
     description "Display tunnel mapping info for site-to-site tunnels";
     input {
       uses command-forwarding;
       leaf level {
         default "brief";
         type enumeration {
           enum "brief" {
             description "Display brief tunnel-mapping (default)";
           }
           enum "summary" {
             description "Display tunnel-mapping summary info";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml iked-tunnel-mapping-information;
         }
         case multichassis-tag {
           anyxml multi-routing-engine-results;
         }
       }
     }
   }
   rpc get-gvpn-security-associations-information {
     description "Show IPSec security association information";
     input {
       uses command-forwarding;
       leaf level {
         default "brief";
         type enumeration {
           enum "brief" {
             description "Display brief output";
           }
           enum "detail" {
             description "Display detailed output";
           }
         }
       }
       leaf show-gvpn-index-ipsec-security-association {
         description "Index of security association";
         default "0";
         type union {
           type uint32;
           type string {
             pattern "<.*>|$.*";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
       leaf group-id {
         description "Group VPN identification number";
         type union {
           type string {
             pattern "<.*>|$.*";
           }
           type uint32 {
             range "1 .. 4294967295";
           }
         }
       }
       leaf service-set {
         description "Service set name";
         type string {
         }
       }
     }
     output {
       choice output_c {
         case output-tag {
           leaf output {
             type string;
           }
         }
         case actual-tag {
           anyxml ipsec-security-associations-information;
         }
         case multichassis-tag {
           anyxml multi-routing-engine-results;
         }
       }
     }
   }
   rpc get-gvpn-ipsec-statistics-information {
     description "Show IPSec statistics";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf service-set {
         description "Name of service set";
         type string {
         }
       }
       leaf show-gvpn-index-ipsec-statistics {
         description "Index of Security Association";
         default "0";
         type union {
           type uint32;
           type string {
             pattern "<.*>|$.*";
           }
         }
       }
     }
     output {
       choice output_c {
         case output-tag {
           leaf output {
             type string;
           }
         }
         case actual-tag {
           anyxml usp-ipsec-total-statistics-information;
         }
         case multichassis-tag {
           anyxml multi-routing-engine-results;
         }
       }
     }
   }
   rpc get-gvpn-inactive-tunnels {
     description "Inactive-tunnels";
     input {
       uses command-forwarding;
       leaf level {
         default "brief";
         type enumeration {
           enum "brief" {
             description "Display brief output";
           }
           enum "detail" {
             description "Display detailed output";
           }
         }
       }
       leaf group-id {
         description "Group VPN identification number";
         type union {
           type string {
             pattern "<.*>|$.*";
           }
           type uint32 {
             range "1 .. 4294967295";
           }
         }
       }
       leaf service-set {
         description "Service set name";
         type string {
         }
       }
     }
     output {
       choice output_c {
         case output-tag {
           leaf output {
             type string;
           }
         }
         case actual-tag {
           anyxml ipsec-unestablished-tunnel-information;
         }
         case multichassis-tag {
           anyxml multi-routing-engine-results;
         }
       }
     }
   }
   rpc get-gvpn-ike-security-associations-information {
     description "Show IKE security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
       leaf service-set {
         description "Service set name";
         type string {
         }
       }
     }
     output {
       choice output_c {
         case output-tag {
           leaf output {
             type string;
           }
         }
         case actual-tag {
           anyxml ike-security-associations-information;
         }
         case multichassis-tag {
           anyxml multi-routing-engine-results;
         }
       }
     }
   }
   rpc get-gvpn-kek-security-associations-information {
     description "Show KEK security association information";
     input {
       uses command-forwarding;
       leaf level {
         default "brief";
         type enumeration {
           enum "brief" {
             description "Show brief output (default)";
           }
           enum "detail" {
             description "Show detailed output";
           }
         }
       }
       leaf peer-address {
         description "IP address of the peer";
         type jt:ipaddr;
       }
       leaf index {
         description "Index of security association";
         default "0";
         type union {
           type uint32;
           type string {
             pattern "<.*>|$.*";
           }
         }
       }
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml ike-security-associations-information;
         }
         case multichassis-tag {
           anyxml multi-routing-engine-results;
         }
       }
     }
   }
   rpc get-gvpn-policy-information {
     description "Show group vpn policies";
     input {
       uses command-forwarding;
       choice groupchoice {
         description "Specify a group by name or ID";
         case group-id {
           leaf group-id {
             description "Group VPN identification number";
             type union {
               type string {
                 pattern "<.*>|$.*";
               }
               type uint32 {
                 range "1 .. 4294967295";
               }
             }
           }
         }
         case vpn {
           leaf vpn {
             description "Group VPN Name";
             type string {
               length "1 .. 32";
             }
           }
         }
       }
     }
     output {
       choice output_c {
         case output-tag {
           leaf output {
             type string;
           }
         }
         case actual-tag {
           anyxml gvpn-policy-information;
         }
         case multichassis-tag {
           anyxml multi-routing-engine-results;
         }
       }
     }
   }
   rpc get-security-group-vpn-server-registered-members {
     description "Show group VPN registered members for group VPN server";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-address {
           leaf peer-address {
             description "Peer IP address";
             type jt:ipaddr;
           }
         }
       }
       leaf level {
         default "brief";
         type enumeration {
           enum "brief" {
             description "Show brief output (default)";
           }
           enum "detail" {
             description "Show detailed output";
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml security-group-vpn-server-registered-members;
         }
         case multichassis-tag {
           anyxml multi-routing-engine-results;
         }
       }
     }
   }
   rpc get-security-group-vpn-server-kek-sa {
     description "Show KEK security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml security-group-vpn-server-kek-sa;
         }
         case multichassis-tag {
           anyxml multi-routing-engine-results;
         }
       }
     }
   }
   rpc get-security-group-vpn-server-security-information {
     description "Show IPSec security association information for group VPN server";
     input {
       uses command-forwarding;
       leaf level {
         default "brief";
         type enumeration {
           enum "brief" {
             description "Show brief output (default)";
           }
           enum "detail" {
             description "Show detailed output";
           }
         }
       }
       choice group_choice {
         description "Specify group or group-id filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml security-group-vpn-server-security-information;
         }
         case multichassis-tag {
           anyxml multi-routing-engine-results;
         }
       }
     }
   }
   rpc get-security-group-vpn-server-ike-security-associations-information {
     description "Show IKE security association information";
     input {
       uses command-forwarding;
       leaf level {
         default "brief";
         type enumeration {
           enum "brief" {
             description "Show brief output (default)";
           }
           enum "detail" {
             description "Show detailed output";
           }
         }
       }
       choice group_index_choice {
         description "Specify peer-address, group, group-id or index filter";
         case peer-address {
           leaf peer-address {
             description "Peer IP address";
             type jt:ipaddr;
           }
         }
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case index {
           leaf index {
             description "Index of security association";
             type union {
               type uint32;
               type string {
                 pattern "<.*>|$.*";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml security-group-vpn-server-ike-security-associations-information;
         }
         case multichassis-tag {
           anyxml multi-routing-engine-results;
         }
       }
     }
   }
   rpc get-security-group-vpn-svr-svr-cluster-info {
     description "Show group vpn server cluster information";
     input {
       uses command-forwarding;
       leaf level {
         default "brief";
         type enumeration {
           enum "brief" {
             description "Show brief output (default)";
           }
           enum "detail" {
             description "Show detailed output";
           }
         }
       }
       choice group_cluster_index_choice {
         description "Specify group, group-id or peer gateway filter";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
         case peer-gateway {
           leaf peer-gateway {
             description "Show specified peer server gateway name";
             type string {
               length "1 .. 32";
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml server-cluster-information;
         }
         case multichassis-tag {
           anyxml multi-routing-engine-results;
         }
       }
     }
   }
   rpc get-security-group-vpn-server-stats {
     description "Show group server statistics";
     input {
       uses command-forwarding;
       choice group_choice {
         description "Specify a group by name or id";
         case group {
           leaf group {
             description "Show specified group";
             type string {
               length "1 .. 32";
             }
           }
         }
         case group-id {
           leaf group-id {
             description "Show specified group id";
             type union {
               type string {
                 pattern "<.*>|$.*";
               }
               type uint32 {
                 range "1 .. 65535";
               }
             }
           }
         }
       }
       leaf fpc {
         description "FPC slot number";
         type union {
           type string {
             pattern "<.*>|$.*";
           }
           type uint32;
         }
       }
       leaf pic {
         description "PIC slot number";
         type union {
           type string {
             pattern "<.*>|$.*";
           }
           type uint32;
         }
       }
       leaf kmd-instance {
         description "Name of KMD instance or 'all'";
         default "all";
         type string {
         }
       }
     }
     output {
       choice output_c {
         case output-tag {
           leaf output {
             type string;
           }
         }
         case actual-tag {
           anyxml security-group-vpn-server-stats;
         }
         case multichassis-tag {
           anyxml multi-routing-engine-results;
         }
       }
     }
   }
   rpc get-internal-security-association {
     description "Show internal security association";
     output {
       choice output_c {
         case output-tag {
           leaf output {
             type string;
           }
         }
         case actual-tag {
           anyxml internal-sa-information;
         }
         case multichassis-tag {
           anyxml multi-routing-engine-results;
         }
       }
     }
   }
   rpc get-idp-application-system-cache {
     description "Show IDP application system cache";
     output {
       choice output_c {
         case output-tag {
           leaf output {
             type string;
           }
         }
         case actual-tag {
           anyxml idp-application-system-cache-information;
         }
         case multichassis-tag {
           anyxml multi-routing-engine-results;
         }
       }
     }
   }
   rpc get-idp-active-policy {
     description "Show active IDP policy";
     status deprecated;
     output {
       choice output_c {
         case output-tag {
           leaf output {
             type string;
           }
         }
         case actual-tag {
           anyxml idp-version-information;
         }
         case multichassis-tag {
           anyxml multi-routing-engine-results;
         }
       }
     }
   }
   rpc get-idp-policy-commit-status {
     description "Show the status of ongoing policy compilation and load";
     input {
       uses command-forwarding;
       choice re-selector-idpd {
         case re0 {
         }
         case re1 {
         }
       }
       leaf clear {
         description "Clears the policy commit status";
         type empty;
       }
     }
     output {
       choice output_c {
         case output-tag {
           leaf output {
             type string;
           }
         }
         case actual-tag {
           anyxml idp-policy-commit-status;
         }
         case multichassis-tag {
           anyxml multi-routing-engine-results;
         }
       }
     }
   }
   rpc get-idp-security-package-proxy-information {
     description "Show proxy profile details";
     output {
       choice output_c {
         case output-tag {
           leaf output {
             type string;
           }
         }
         case actual-tag {
           anyxml idp-security-package-proxy-profile;
         }
         case multichassis-tag {
           anyxml multi-routing-engine-results;
         }
       }
     }
   }
   rpc get-idp-security-package-information {
     description "Show the version of currently installed security-package";
     input {
       uses command-forwarding;
       choice re-selector-idpd {
         case re0 {
         }
         case re1 {
         }
       }
     }
     output {
       choice output_c {
         case output-tag {
           leaf output {
             type string;
           }
         }
         case actual-tag {
           anyxml idp-security-package-information;
         }
         case multichassis-tag {
           anyxml multi-routing-engine-results;
         }
       }
     }
   }
   rpc get-idp-jist-package-information {
     description "Show the version of currently installed JIST package";
     input {
       uses command-forwarding;
       choice re-selector-idpd {
         case re0 {
         }
         case re1 {
         }
       }
     }
     output {
       choice output_c {
         case output-tag {
           leaf output {
             type string;
           }
         }
         case actual-tag {
           anyxml idp-jist-package-information;
         }
         case multichassis-tag {
           anyxml multi-routing-engine-results;
         }
       }
     }
   }
   rpc get-idp-recent-security-package-information {
     description "List ten most recent security package versions";
     input {
       uses command-forwarding;
       choice re-selector-idpd {
         case re0 {
         }
         case re1 {
         }
       }
     }
     output {
       choice output_c {
         case output-tag {
           leaf output {
             type string;
           }
         }
         case actual-tag {
           anyxml idp-recent-security-package-information;
         }
         case multichassis-tag {
           anyxml multi-routing-engine-results;
         }
       }
     }
   }
   rpc get-idp-memory-information {
     description "Show IDP data plane memory statistics";
     output {
       choice output_c {
         case output-tag {
           leaf output {
             type string;
           }
         }
         case actual-tag {
           anyxml idp-memory-information;
         }
         case multichassis-tag {
           anyxml multi-routing-engine-results;
         }
       }
     }
   }
   rpc get-idp-subscriber-policy-list {
     description "Show the currently used policies";
     input {
       uses command-forwarding;
     }
     output {
       choice output_c {
         case output-tag {
           leaf output {
             type string;
           }
         }
         case actual-tag {
           anyxml idp-subscriber-policy-list;
         }
         case multichassis-tag {
           anyxml multi-routing-engine-results;
         }
       }
     }
   }
   rpc get-idp-policy-template-information {
     description "Show available policy templates";
     output {
       choice output_c {
         case output-tag {
           leaf output {
             type string;
           }
         }
         case actual-tag {
           anyxml idp-policy-template-information;
         }
         case multichassis-tag {
           anyxml multi-routing-engine-results;
         }
       }
     }
   }
   rpc get-idp-status-information {
     description "Show IDP status";
     output {
       choice output_c {
         case output-tag {
           leaf output {
             type string;
           }
         }
         case actual-tag {
           anyxml idp-status-information;
         }
         case multichassis-tag {
           anyxml multi-routing-engine-results;
         }
       }
     }
   }
   rpc get-idp-detail-status-information {
     description "Show IDP detail status";
     output {
       choice output_c {
         case output-tag {
           leaf output {
             type string;
           }
         }
         case actual-tag {
           anyxml idp-detail-status-information;
         }
         case multichassis-tag {
           anyxml multi-routing-engine-results;
         }
       }
     }
   }
   rpc get-idp-predefined-attack-groups {
     description "Show predefined attack groups";
     output {
       choice output_c {
         case output-tag {
           leaf output {
             type string;
           }
         }
         case actual-tag {
           anyxml idp-predefined-attack-groups;
         }
         case multichassis-tag {
           anyxml multi-routing-engine-results;
         }
       }
     }
   }
   rpc get-idp-predefined-attack-group-filters {
     description "Configure filters";
     input {
       uses command-forwarding;
       choice re-selector-idpd {
         case re0 {
         }
         case re1 {
         }
       }
       leaf category {
         description "Category of attack group";
         type string;
       }
     }
     output {
       choice output_c {
         case output-tag {
           leaf output {
             type string;
           }
         }
         case actual-tag {
           anyxml idp-predefined-attack-group-filters;
         }
         case multichassis-tag {
           anyxml multi-routing-engine-results;
         }
       }
     }
   }
   rpc get-idp-predefined-attacks {
     description "Show predefined attacks";
     output {
       choice output_c {
         case output-tag {
           leaf output {
             type string;
           }
         }
         case actual-tag {
           anyxml idp-predefined-attacks;
         }
         case multichassis-tag {
           anyxml multi-routing-engine-results;
         }
       }
     }
   }
   rpc get-idp-predefined-attack-filters {
     description "Configure filters";
     input {
       uses command-forwarding;
       choice re-selector-idpd {
         case re0 {
         }
         case re1 {
         }
       }
       leaf category {
         description "Category of attack";
         type string;
       }
       leaf severity {
         description "Severity of attack";
         type enumeration {
           enum "info" {
             description "Provide information of attack when it matches";
           }
           enum "warning" {
             description "The attack is a minor one";
           }
           enum "minor" {
             description "The attack is a minor one";
           }
           enum "major" {
             description "The attack is a major one";
           }
           enum "critical" {
             description "The attack is a critical one";
           }
         }
       }
       leaf direction {
         description "Direction of attack";
         type enumeration {
           enum "client-to-server" {
             description "Select attacks from client to server";
           }
           enum "server-to-client" {
             description "Select attacks from server to client";
           }
           enum "any" {
             description "Select attacks which can occur in either direction";
           }
           enum "exclude-client-to-server" {
             description "Filter out attacks from client to server";
           }
           enum "exclude-server-to-client" {
             description "Filter out attacks from server to client";
           }
           enum "exclude-any" {
             description "Filter out attacks which are in any direction";
           }
         }
       }
     }
     output {
       choice output_c {
         case output-tag {
           leaf output {
             type string;
           }
         }
         case actual-tag {
           anyxml idp-predefined-attack-filters;
         }
         case multichassis-tag {
           anyxml multi-routing-engine-results;
         }
       }
     }
   }
   rpc get-idp-counter-information {
     description "Show IDP counters";
     output {
       choice output_c {
         case output-tag {
           leaf output {
             type string;
           }
         }
         case actual-tag {
           anyxml idp-counter-information;
         }
         case multichassis-tag {
           anyxml multi-routing-engine-results;
         }
       }
     }
   }
   rpc get-idp-counters-packet {
     description "Show IDP Packet counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-tcp-reass {
     description "Show IDP Reassembler counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-ips {
     description "Show IPS counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-flow {
     description "Show IDP Flow counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-dfa {
     description "Show IDP DFA counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-log {
     description "Show IDP Log counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-pol-mngr {
     description "Show IDP Policy counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-packet-log {
     description "Show IDP Packet capture counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-appid {
     description "Show Application Identification counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-ssl-inspection {
     description "Show SSL Inspection counters";
     status deprecated;
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-memory {
     description "Show IDP memory counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-action {
     description "Show IDP policy action counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-pdf-decoder {
     description "Show the PDF decoder counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-counters-http-decoder {
     description "Show the HTTP decoder counters";
     input {
       uses command-forwarding;
       choice lsys {
         case logical-system {
         }
         case tenant {
         }
       }
     }
     output {
       choice output_c {
         case output-tag {
           leaf output {
             type string;
           }
         }
         case multichassis-tag {
           anyxml multi-routing-engine-results;
         }
       }
     }
   }
   rpc get-idp-applications-information {
     description "Show IDP application statistics";
     output {
       choice output_c {
         case output-tag {
           leaf output {
             type string;
           }
         }
         case actual-tag {
           anyxml idp-applications-information;
         }
         case multichassis-tag {
           anyxml multi-routing-engine-results;
         }
       }
     }
   }
   rpc get-idp-attack-table-information {
     description "Show IDP attack table";
     input {
       uses command-forwarding;
       choice lsys {
         case logical-system {
         }
         case tenant {
         }
       }
     }
     output {
       choice output_c {
         case output-tag {
           leaf output {
             type string;
           }
         }
         case actual-tag {
           anyxml idp-attack-table-information;
         }
         case multichassis-tag {
           anyxml multi-routing-engine-results;
         }
       }
     }
   }
   rpc get-idp-attack-context-information {
     description "Show IDP attack contexts";
     input {
       uses command-forwarding;
       choice lsys {
         case logical-system {
         }
         case tenant {
         }
       }
     }
     output {
       choice output_c {
         case output-tag {
           leaf output {
             type string;
           }
         }
         case actual-tag {
           anyxml idp-attack-context-information;
         }
         case multichassis-tag {
           anyxml multi-routing-engine-results;
         }
       }
     }
   }
   rpc get-idp-attack-deprecated-list-information {
     description "Show IDP attack deprecated-list";
     output {
       choice output_c {
         case output-tag {
           leaf output {
             type string;
           }
         }
         case actual-tag {
           anyxml idp-attack-deprecated-list-information;
         }
         case multichassis-tag {
           anyxml multi-routing-engine-results;
         }
       }
     }
   }
   rpc get-idp-policy-deprecated-attack-information {
     description "Show IDP attack deprecated-list for the configured policy";
     input {
       leaf policy {
         description "IDP policy name";
         type string;
         mandatory true;
       }
     }
     output {
       choice output_c {
         case output-tag {
           leaf output {
             type string;
           }
         }
         case actual-tag {
           anyxml idp-policy-deprecated-attack-information;
         }
         case multichassis-tag {
           anyxml multi-routing-engine-results;
         }
       }
     }
   }
   rpc get-idp-all-policy-deprecated-attack-information {
     description "Show IDP attack deprecated-list for all the idp policies in use";
     input {
       leaf logical-system {
         description "Name of logical system";
         type string {
         }
       }
       leaf tenant {
         description "Name of tenant";
         type string {
         }
       }
     }
     output {
       choice output_c {
         case output-tag {
           leaf output {
             type string;
           }
         }
         case actual-tag {
           anyxml idp-all-policy-deprecated-attack-information;
         }
         case multichassis-tag {
           anyxml multi-routing-engine-results;
         }
       }
     }
   }
   rpc get-idp-attack-description-information {
     description "Show description of specified attack";
     input {
       leaf attack-name {
         description "Attack name";
         type string;
         mandatory true;
       }
     }
     output {
       choice output_c {
         case output-tag {
           leaf output {
             type string;
           }
         }
         case actual-tag {
           anyxml idp-attack-description-information;
         }
         case multichassis-tag {
           anyxml multi-routing-engine-results;
         }
       }
     }
   }
   rpc get-idp-attack-detail-information {
     description "Show details of specified attack";
     input {
       leaf attack-name {
         description "Attack name";
         type string;
         mandatory true;
       }
     }
     output {
       choice output_c {
         case output-tag {
           leaf output {
             type string;
           }
         }
         case actual-tag {
           anyxml idp-attack-detail-information;
         }
         case multichassis-tag {
           anyxml multi-routing-engine-results;
         }
       }
     }
   }
   rpc get-idp-attack-group-entry-detail-information {
     description "Show detail of all attack and group";
     input {
       leaf offset {
         description "Offset value to start with (0 to any number)";
         type union {
           type uint32;
           type string {
             pattern "<.*>|$.*";
           }
         }
       }
       leaf limit {
         description "Number of entries to display";
         type union {
           type string {
             pattern "<.*>|$.*";
           }
           type int32 {
             range "1 .. 50";
           }
         }
       }
     }
     output {
       choice output_c {
         case output-tag {
           leaf output {
             type string;
           }
         }
         case actual-tag {
           anyxml idp-attack-group-entry-detail-information;
         }
         case multichassis-tag {
           anyxml multi-routing-engine-results;
         }
       }
     }
   }
   rpc get-idp-attack-group-entry-filters-information {
     description "Show detail of all attack and group which match the provided filters";
     input {
       leaf-list category {
         ordered-by user;
         description "Category of attack";
         type string;
       }
       leaf-list type-attack {
         ordered-by user;
         description "Type of attack";
         type enumeration {
           enum "0" {
             description "Static attack";
           }
           enum "1" {
             description "Dynamic attack";
           }
         }
       }
       leaf-list recommended-action {
         ordered-by user;
         description "Recommended action";
         type enumeration {
           enum "0" {
             description "None";
           }
           enum "1" {
             description "Close client and server";
           }
           enum "2" {
             description "Close client";
           }
           enum "3" {
             description "Close server";
           }
           enum "4" {
             description "Ignore";
           }
           enum "5" {
             description "Drop";
           }
           enum "6" {
             description "Drop packet";
           }
         }
       }
       leaf-list attack-type {
         ordered-by user;
         description "Attack type";
         type enumeration {
           enum "0" {
             description "Attack type - signature";
           }
           enum "1" {
             description "Attack type - anomaly";
           }
           enum "2" {
             description "Attack type - chain";
           }
         }
       }
       leaf-list performance {
         ordered-by user;
         description "Performance category type";
         type enumeration {
           enum "0" {
             description "Performance 0 - unknown";
           }
           enum "1" {
             description "Performance 1 - low";
           }
           enum "5" {
             description "Performance 5 - medium ";
           }
           enum "9" {
             description "Performance 9 - high";
           }
         }
       }
       leaf-list severity {
         ordered-by user;
         description "Severity of attack";
         type enumeration {
           enum "0" {
             description "Info attack";
           }
           enum "1" {
             description "Warning attack";
           }
           enum "2" {
             description "Minor attack";
           }
           enum "3" {
             description "Major attack";
           }
           enum "4" {
             description "Critical attack`";
           }
         }
       }
       leaf-list direction {
         ordered-by user;
         description "Direction of attack";
         type enumeration {
           enum "0" {
             description "Select attacks from client to server";
           }
           enum "1" {
             description "Select attacks from server to client";
           }
           enum "2" {
             description "Select attacks which can occur in either direction";
           }
         }
       }
       leaf-list recommended {
         ordered-by user;
         description "Recommended attack or not";
         type enumeration {
           enum "0" {
             description "Non recommended attack";
           }
           enum "1" {
             description "Recommended attack";
           }
         }
       }
       leaf-list group-name {
         ordered-by user;
         description "Group name";
         type string;
       }
       leaf-list group-type {
         ordered-by user;
         description "Group type";
         type enumeration {
           enum "0" {
             description "Predefined group";
           }
           enum "1" {
             description "Custom attack";
           }
           enum "2" {
             description "Custom attack group";
           }
           enum "3" {
             description "Predefined attack";
           }
         }
       }
       leaf-list service {
         ordered-by user;
         description "Attack service type";
         type string;
       }
       leaf-list cve-id {
         ordered-by user;
         description "Cve identifier";
         type string;
       }
       leaf-list certificate {
         ordered-by user;
         description "Certificate identifier";
         type string;
       }
       leaf-list bug-id {
         ordered-by user;
         description "Bug identifier";
         type string;
       }
       leaf-list false-positive {
         ordered-by user;
         description "Attack falsepositive type";
         type enumeration {
           enum "0" {
             description "Falsepositive category - unknown";
           }
           enum "1" {
             description "Falsepositive category - occassionally";
           }
           enum "2" {
             description "Falsepositive category - frequently";
           }
           enum "3" {
             description "Falsepositive category - rarely";
           }
         }
       }
       leaf limit {
         description "Number of entries to display";
         type union {
           type string {
             pattern "<.*>|$.*";
           }
           type int32 {
             range "1 .. 50";
           }
         }
       }
       leaf offset {
         description "Offset to start with (0 to any number)";
         type union {
           type uint32;
           type string {
             pattern "<.*>|$.*";
           }
         }
       }
     }
     output {
       choice output_c {
         case output-tag {
           leaf output {
             type string;
           }
         }
         case actual-tag {
           anyxml idp-attack-group-entry-filters-information;
         }
         case multichassis-tag {
           anyxml multi-routing-engine-results;
         }
       }
     }
   }
   rpc get-idp-group-attacklist-information {
     description "Shows list of all attacks present in the attack group specified";
     input {
       choice filter-choice {
         case predefined-group {
           leaf predefined-group {
             description "Predefined group name";
             type string;
           }
         }
         case custom-group {
           leaf custom-group {
             description "Custom group name";
             type string;
           }
         }
         case dynamic-group {
           leaf dynamic-group {
             description "Dynamic group name";
             type string;
           }
         }
         case policy {
           leaf policy {
             description "IDP policy name";
             type string;
           }
         }
       }
       leaf recursive {
         description "To show attack list recursively";
         type empty;
       }
     }
     output {
       choice output_c {
         case output-tag {
           leaf output {
             type string;
           }
         }
         case actual-tag {
           anyxml idp-group-attacklist-information;
         }
         case multichassis-tag {
           anyxml multi-routing-engine-results;
         }
       }
     }
   }
   rpc get-idp-group-forattack-information {
     description "Shows list of predefined attack-groups to which the predefined-attack belongs";
     input {
       leaf attack-name {
         description "Attack name";
         type string;
         mandatory true;
       }
     }
     output {
       choice output_c {
         case output-tag {
           leaf output {
             type string;
           }
         }
         case actual-tag {
           anyxml idp-group-forattack-information;
         }
         case multichassis-tag {
           anyxml multi-routing-engine-results;
         }
       }
     }
   }
   rpc get-idp-attack-type-anomaly-test-service {
     description "Test name";
     input {
       leaf service {
         description "Service name";
         type string;
       }
     }
     output {
       choice output_c {
         case output-tag {
           leaf output {
             type string;
           }
         }
         case actual-tag {
           anyxml idp-attack-type-anomaly-test-service;
         }
         case multichassis-tag {
           anyxml multi-routing-engine-results;
         }
       }
     }
   }
   rpc get-idp-ssl-session-cache-information {
     description "Session ID cache";
     output {
       choice output_c {
         case output-tag {
           leaf output {
             type string;
           }
         }
         case actual-tag {
           anyxml get-idp-ssl-session-cache-information;
         }
         case multichassis-tag {
           anyxml multi-routing-engine-results;
         }
       }
     }
   }
   rpc get-idp-ssl-key-information {
     description "Show SSL keys";
     input {
       uses command-forwarding;
       leaf key-name {
         description "Key name";
         type string {
           length "1 .. 31";
         }
       }
     }
     output {
       choice output_c {
         case output-tag {
           leaf output {
             type string;
           }
         }
         case actual-tag {
           anyxml idp-ssl-key-information;
         }
         case multichassis-tag {
           anyxml multi-routing-engine-results;
         }
       }
     }
   }
   rpc get-idp-lsys-policy-association {
     description "Show IDP policy association";
     output {
       choice output_c {
         case output-tag {
           leaf output {
             type string;
           }
         }
         case actual-tag {
           anyxml idp-lsys-policy-association;
         }
         case multichassis-tag {
           anyxml multi-routing-engine-results;
         }
       }
     }
   }
   rpc get-eedebug-action-profile {
     description "Show current datapath-debug action profile";
     output {
       choice output_c {
         case output-tag {
           leaf output {
             type string;
           }
         }
         case actual-tag {
           anyxml eedebug-all-action-profile;
         }
         case multichassis-tag {
           anyxml multi-routing-engine-results;
         }
       }
     }
   }
   rpc get-eedebug-events {
     description "Show current registered data path events";
     output {
       choice output_c {
         case output-tag {
           leaf output {
             type string;
           }
         }
         case actual-tag {
           anyxml eedebug-all-events;
         }
         case multichassis-tag {
           anyxml multi-routing-engine-results;
         }
       }
     }
   }
   rpc get-eedebug-counters {
     description "Show datapath counters";
     output {
       choice output_c {
         case output-tag {
           leaf output {
             type string;
           }
         }
         case actual-tag {
           anyxml eedebug-all-counters;
         }
         case multichassis-tag {
           anyxml multi-routing-engine-results;
         }
       }
     }
   }
   rpc get-eedebug-capture {
     description "Show datapath debug capture file";
     output {
       choice output_c {
         case output-tag {
           leaf output {
             type string;
           }
         }
         case actual-tag {
           anyxml eedebug-capture-output;
         }
         case multichassis-tag {
           anyxml multi-routing-engine-results;
         }
       }
     }
   }
   rpc get-alg-status {
     description "Show ALG status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-status;
         }
         case multichassis-tag {
           anyxml multi-routing-engine-results;
         }
       }
     }
   }
   rpc get-alg-h323-counters {
     description "Show H323 counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-h323-counters;
         }
         case multichassis-tag {
           anyxml multi-routing-engine-results;
         }
       }
     }
   }
   rpc get-alg-mgcp-call-information {
     description "Show MGCP calls";
     input {
       uses command-forwarding;
       leaf endpoint {
         description "Show MGCP call endpoint";
         type string {
           length "1 .. 63";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-mgcp-call-information;
         }
         case multichassis-tag {
           anyxml multi-routing-engine-results;
         }
       }
     }
   }
   rpc get-alg-mgcp-counter-information {
     description "Show MGCP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-mgcp-counter-information;
         }
         case multichassis-tag {
           anyxml multi-routing-engine-results;
         }
       }
     }
   }
   rpc get-alg-mgcp-endpoint-information {
     description "Show MGCP endpoints";
     input {
       uses command-forwarding;
       leaf endpoint-name {
         description "Show MGCP endpoint with identifier";
         type string {
           length "1 .. 63";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-mgcp-endpoint-information;
         }
         case multichassis-tag {
           anyxml multi-routing-engine-results;
         }
       }
     }
   }
   rpc get-alg-msrpc-uuid2oid-table {
     description "Show MSRPC UUID to OID table";
     output {
       choice output_c {
         case output-tag {
           leaf output {
             type string;
           }
         }
         case actual-tag {
           anyxml alg-msrpc-uuid2oid-table;
         }
         case multichassis-tag {
           anyxml multi-routing-engine-results;
         }
       }
     }
   }
   rpc get-alg-sccp-calls {
     description "Show SCCP calls";
     input {
       uses command-forwarding;
       leaf level {
         default "brief";
         type enumeration {
           enum "detail" {
             description "Display detailed call information";
           }
           enum "brief" {
             description "Display brief call information (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-sccp-calls;
         }
         case multichassis-tag {
           anyxml multi-routing-engine-results;
         }
       }
     }
   }
   rpc get-alg-sccp-counters {
     description "Show SCCP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-sccp-counters;
         }
         case multichassis-tag {
           anyxml multi-routing-engine-results;
         }
       }
     }
   }
   rpc get-alg-sip-call-information {
     description "Show SIP calls";
     input {
       uses command-forwarding;
       leaf level {
         default "brief";
         type enumeration {
           enum "detail" {
             description "Display detailed call information";
           }
           enum "brief" {
             description "Display brief call information (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-sip-call-information;
         }
         case multichassis-tag {
           anyxml multi-routing-engine-results;
         }
       }
     }
   }
   rpc get-alg-sip-counter-information {
     description "Show SIP counters";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml alg-sip-counter-information;
         }
         case multichassis-tag {
           anyxml multi-routing-engine-results;
         }
       }
     }
   }
   rpc get-alg-sip-rate-information {
     description "Show SIP rate";
     output {
       choice output_c {
         case output-tag {
           leaf output {
             type string;
           }
         }
         case actual-tag {
           anyxml alg-sip-rate-information;
         }
         case multichassis-tag {
           anyxml multi-routing-engine-results;
         }
       }
     }
   }
   rpc get-alg-ike-esp-state {
     description "Show all IKE-ESP ALG state information";
     output {
       choice output_c {
         case output-tag {
           leaf output {
             type string;
           }
         }
         case actual-tag {
           anyxml alg-ike-esp-show;
         }
         case multichassis-tag {
           anyxml multi-routing-engine-results;
         }
       }
     }
   }
   rpc get-alg-ike-esp-summary {
     description "Show IKE-ESP ALG summary";
     output {
       choice output_c {
         case output-tag {
           leaf output {
             type string;
           }
         }
         case actual-tag {
           anyxml alg-ike-esp-show-summary;
         }
         case multichassis-tag {
           anyxml multi-routing-engine-results;
         }
       }
     }
   }
   rpc get-appfw-rule-set {
     description "Show security application firewall rule-set";
     input {
       uses command-forwarding;
       choice rule-set-choice {
         case rule-set-name {
           leaf rule-set-name {
             description "Show the rule-set information matching the given rule-set name";
             type string {
               length "1 .. 64";
             }
             mandatory true;
           }
         }
         case all {
           leaf all {
             description "Show all rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml security-appfw-rule-set;
         }
         case multichassis-tag {
           anyxml multi-routing-engine-results;
         }
       }
     }
   }
   rpc get-application-firewall-shadow-rules {
     description "Show security application firewall shadow-rules in one rule-set";
     input {
       uses command-forwarding;
       leaf rule-set-name {
         description "Rule-set name";
         type string {
           length "1 .. 64";
         }
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml appfw-shadow-rules;
         }
         case multichassis-tag {
           anyxml multi-routing-engine-results;
         }
       }
     }
   }
   rpc get-application-firewall-match-rule {
     description "Show matching rules in one rule-set";
     input {
       uses command-forwarding;
       leaf rule-set-name {
         description "Rule-set name";
         type string {
           length "1 .. 64";
         }
         mandatory true;
       }
       leaf dynamic-application {
         description "Dynamic application name";
         type string;
         mandatory true;
       }
       leaf encrypted {
         description "Specify encrypted or plain-text rules";
         default "any";
         type enumeration {
           enum "yes" {
             description "Encrypted rule";
           }
           enum "no" {
             description "Non-encrypted rule";
           }
           enum "any" {
             description "Encrypted and non-encrypted rule";
           }
         }
       }
       leaf result-count {
         description "Number of rules to show";
         default "1";
         type union {
           type string {
             pattern "<.*>|$.*";
           }
           type uint32 {
             range "1 .. 128000";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml appfw-match-rule;
         }
         case multichassis-tag {
           anyxml multi-routing-engine-results;
         }
       }
     }
   }
   rpc get-avt-counters {
     description "Show Application tracking counters";
     output {
       choice output_c {
         case output-tag {
           leaf output {
             type string;
           }
         }
         case actual-tag {
           anyxml avt-counters;
         }
         case multichassis-tag {
           anyxml multi-routing-engine-results;
         }
       }
     }
   }
   rpc get-utmd-status {
     description "Show security utm status";
     output {
       choice output_c {
         case output-tag {
           leaf output {
             type string;
           }
         }
         case actual-tag {
           anyxml utmd-status;
         }
         case multichassis-tag {
           anyxml multi-routing-engine-results;
         }
       }
     }
   }
   rpc get-utmd-session {
     description "Show security utm session";
     output {
       choice output_c {
         case output-tag {
           leaf output {
             type string;
           }
         }
         case actual-tag {
           anyxml utmd-session;
         }
         case multichassis-tag {
           anyxml multi-routing-engine-results;
         }
       }
     }
   }
   rpc get-anti-virus {
     description "Show anti-virus information";
     output {
       choice output_c {
         case output-tag {
           leaf output {
             type string;
           }
         }
         case multichassis-tag {
           anyxml multi-routing-engine-results;
         }
       }
     }
   }
   rpc get-anti-virus-statistics {
     description "Show anti-virus statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml anti-virus-statistics;
         }
         case multichassis-tag {
           anyxml multi-routing-engine-results;
         }
       }
     }
   }
   rpc get-anti-virus-status {
     description "Show anti-virus status";
     output {
       choice output_c {
         case output-tag {
           leaf output {
             type string;
           }
         }
         case actual-tag {
           anyxml anti-virus-status;
         }
         case multichassis-tag {
           anyxml multi-routing-engine-results;
         }
       }
     }
   }
   rpc get-anti-virus-status-detail {
     description "Show anti-virus detailed status";
     output {
       choice output_c {
         case output-tag {
           leaf output {
             type string;
           }
         }
         case actual-tag {
           anyxml anti-virus-status-detail;
         }
         case multichassis-tag {
           anyxml multi-routing-engine-results;
         }
       }
     }
   }
   rpc get-anti-virus-performance {
     description "Show anti-virus performance";
     output {
       choice output_c {
         case output-tag {
           leaf output {
             type string;
           }
         }
         case actual-tag {
           anyxml anti-virus-performance;
         }
         case multichassis-tag {
           anyxml multi-routing-engine-results;
         }
       }
     }
   }
   rpc get-web-filtering {
     description "Show web-filtering information";
     output {
       choice output_c {
         case output-tag {
           leaf output {
             type string;
           }
         }
         case multichassis-tag {
           anyxml multi-routing-engine-results;
         }
       }
     }
   }
   rpc get-web-filtering-statistics {
     description "Show web-filtering statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml web-filtering-statistics;
         }
         case multichassis-tag {
           anyxml multi-routing-engine-results;
         }
       }
     }
   }
   rpc get-web-filtering-status {
     description "Show web-filtering status";
     output {
       choice output_c {
         case output-tag {
           leaf output {
             type string;
           }
         }
         case actual-tag {
           anyxml web-filtering-status;
         }
         case multichassis-tag {
           anyxml multi-routing-engine-results;
         }
       }
     }
   }
   rpc get-web-filtering-category {
     description "Show category information";
     output {
       choice output_c {
         case output-tag {
           leaf output {
             type string;
           }
         }
         case multichassis-tag {
           anyxml multi-routing-engine-results;
         }
       }
     }
   }
   rpc get-category-status {
     description "Show category package download/install status";
     output {
       choice output_c {
         case output-tag {
           leaf output {
             type string;
           }
         }
         case actual-tag {
           anyxml category-status;
         }
         case multichassis-tag {
           anyxml multi-routing-engine-results;
         }
       }
     }
   }
   rpc get-category-category-list {
     description "Show EWF predefined category";
     input {
       uses command-forwarding;
       leaf start {
         description "Paging start";
         type union {
           type uint32;
           type string {
             pattern "<.*>|$.*";
           }
         }
       }
       leaf count {
         description "Item count";
         type union {
           type uint32;
           type string {
             pattern "<.*>|$.*";
           }
         }
       }
     }
     output {
       choice output_c {
         case output-tag {
           leaf output {
             type string;
           }
         }
         case actual-tag {
           anyxml category-category-list;
         }
         case multichassis-tag {
           anyxml multi-routing-engine-results;
         }
       }
     }
   }
   rpc get-category-base-filter {
     description "Show EWF predefined base-filter";
     input {
       uses command-forwarding;
       leaf base-filter-name {
         description "Base-filter name";
         type string;
       }
       leaf start {
         description "Paging start";
         type union {
           type uint32;
           type string {
             pattern "<.*>|$.*";
           }
         }
       }
       leaf count {
         description "Item count";
         type union {
           type uint32;
           type string {
             pattern "<.*>|$.*";
           }
         }
       }
     }
     output {
       choice output_c {
         case output-tag {
           leaf output {
             type string;
           }
         }
         case actual-tag {
           anyxml category-base-filter;
         }
         case multichassis-tag {
           anyxml multi-routing-engine-results;
         }
       }
     }
   }
   rpc get-content-filtering {
     description "Show content-filtering information";
     output {
       choice output_c {
         case output-tag {
           leaf output {
             type string;
           }
         }
         case multichassis-tag {
           anyxml multi-routing-engine-results;
         }
       }
     }
   }
   rpc get-content-filtering-statistics {
     description "Show content-filtering statistics";
     input {
       uses command-forwarding;
       leaf utm-policy {
         description "Show statistics associated to utm-policy";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml show-content-filtering-statistics;
         }
         case multichassis-tag {
           anyxml multi-routing-engine-results;
         }
       }
     }
   }
   rpc get-content-filtering-dpi-status {
     description "Show content-filtering status";
     output {
       choice output_c {
         case output-tag {
           leaf output {
             type string;
           }
         }
         case actual-tag {
           anyxml content-filtering-dpi-status;
         }
         case multichassis-tag {
           anyxml multi-routing-engine-results;
         }
       }
     }
   }
   rpc get-anti-spam {
     description "Show anti-spam information";
     output {
       choice output_c {
         case output-tag {
           leaf output {
             type string;
           }
         }
         case multichassis-tag {
           anyxml multi-routing-engine-results;
         }
       }
     }
   }
   rpc get-anti-spam-statistics {
     description "Show anti-spam statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml anti-spam-statistics;
         }
         case multichassis-tag {
           anyxml multi-routing-engine-results;
         }
       }
     }
   }
   rpc get-anti-spam-status {
     description "Show anti-spam status";
     output {
       choice output_c {
         case output-tag {
           leaf output {
             type string;
           }
         }
         case actual-tag {
           anyxml anti-spam-status;
         }
         case multichassis-tag {
           anyxml multi-routing-engine-results;
         }
       }
     }
   }
   rpc get-security-dynamic-address {
     description "Security dynamic address name";
     input {
       uses command-forwarding;
       leaf category-name {
         description "Source category";
         type enumeration {
           enum "IPFilter" {
             description "IPFilter";
           }
           enum "GeoIP" {
             description "GeoIP";
           }
           enum "CC" {
             description "Command and control";
           }
           enum "JWAS" {
             description "JWAS";
           }
           enum "Blacklist" {
             description "Blacklist";
           }
           enum "Whitelist" {
             description "Whitelist";
           }
           enum "Infected-Hosts" {
             description "Infected-Hosts";
           }
           enum "SecProfiling" {
             description "SecProfiling";
           }
         }
       }
       leaf feed-name {
         description "Source feed name";
         type string {
           length "1 .. 240";
         }
       }
       leaf address-name {
         description "Dynamic address name";
         type string {
           length "1 .. 240";
         }
       }
       leaf ip-start {
         description "Numerically minimal IP address within the range";
         type jt:ipaddr;
       }
       leaf ip-end {
         description "Numerically maximal IP address within the range";
         type jt:ipaddr;
       }
       leaf family {
         description "Protocol-family";
         type enumeration {
           enum "inet" {
             description "IPv4 address";
           }
           enum "inet6" {
             description "IPv6 address";
           }
         }
       }
       leaf instance {
         description "Dynamic address instance";
         type enumeration {
           enum "default" {
             description "Default instance";
           }
           enum "geoip" {
             description "GeoIP instance";
           }
           enum "advanced-anti-malware" {
             description "Instance for anti-malware solution";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml security-dynamic-address;
         }
         case multichassis-tag {
           anyxml multi-routing-engine-results;
         }
       }
     }
   }
   rpc get-security-dynamic-address-summary {
     description "Summary about dynamic address";
     input {
       uses command-forwarding;
       leaf instance {
         description "Dynamic address instance";
         type enumeration {
           enum "default" {
             description "Default instance";
           }
           enum "geoip" {
             description "GeoIP instance";
           }
           enum "advanced-anti-malware" {
             description "Instance for anti-malware solution";
           }
         }
       }
       leaf address-name {
         description "Show summary by dynamic address name";
         type string {
           length "1 .. 240";
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml security-dynamic-address-summary;
         }
         case multichassis-tag {
           anyxml multi-routing-engine-results;
         }
       }
     }
   }
   rpc get-ssh-key-information {
     description "Show SSH identity brief information";
     input {
       leaf identity-name {
         description "Show brief information of specified identity";
         type string {
         }
       }
     }
     output {
       choice output_c {
         case output-tag {
           leaf output {
             type string;
           }
         }
         case actual-tag {
           anyxml identity-information;
         }
         case multichassis-tag {
           anyxml multi-routing-engine-results;
         }
       }
     }
   }
   rpc get-ssh-key-public-information {
     description "Show SSH identity public key";
     input {
       leaf identity-name {
         description "Show public key of specified identity";
         type string {
         }
         mandatory true;
       }
     }
     output {
       choice output_c {
         case output-tag {
           leaf output {
             type string;
           }
         }
         case actual-tag {
           anyxml identity-public-information;
         }
         case multichassis-tag {
           anyxml multi-routing-engine-results;
         }
       }
     }
   }
   rpc get-ds-lite-softwire-sc-infomation {
     description "Show softwire information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml ds-lite-softwire-sc-information;
         }
         case multichassis-tag {
           anyxml multi-routing-engine-results;
         }
       }
     }
   }
   rpc get-ds-lite-softwire-one-sc-information {
     description "Show Softwire Concentrator object";
     input {
       uses command-forwarding;
       leaf softwire-name-str {
         description "Softwire Name";
         type string;
         mandatory true;
       }
       leaf start-id {
         description "Show softwire initiator info from start identifier";
         type union {
           type string {
             pattern "<.*>|$.*";
           }
           type uint32 {
             range "1 .. 100000";
           }
         }
       }
       leaf count {
         description "Number of softwire initiator entries";
         type union {
           type string {
             pattern "<.*>|$.*";
           }
           type uint32 {
             range "1 .. 100000";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml ds-lite-softwire-one-sc-information;
         }
         case multichassis-tag {
           anyxml multi-routing-engine-results;
         }
       }
     }
   }
   rpc get-mape-domain-information {
     description "Show MAP-E information";
     output {
       choice output_c {
         case output-tag {
           leaf output {
             type string;
           }
         }
         case actual-tag {
           anyxml mape-domain-information;
         }
         case multichassis-tag {
           anyxml multi-routing-engine-results;
         }
       }
     }
   }
   rpc get-mape-confidentiality-status {
     description "Show confidentiality status";
     output {
       choice output_c {
         case output-tag {
           leaf output {
             type string;
           }
         }
         case actual-tag {
           anyxml mape-confidentiality-status;
         }
         case multichassis-tag {
           anyxml multi-routing-engine-results;
         }
       }
     }
   }
   rpc get-mape-one-domain-information {
     description "Show MAP-E domain object";
     input {
       leaf mape-domain-name {
         description "Specify name of the MAP-E domain";
         type string;
         mandatory true;
       }
       leaf rule {
         description "MAP-E rule name";
         type string;
       }
       leaf statistics {
         description "MAP-E statistics";
         type empty;
       }
     }
     output {
       choice output_c {
         case output-tag {
           leaf output {
             type string;
           }
         }
         case actual-tag {
           anyxml mape-one-domain-information;
         }
         case multichassis-tag {
           anyxml multi-routing-engine-results;
         }
       }
     }
   }
   rpc get-firewall-dynamic-policies {
     description "Show security firewall dynamic policies";
     input {
       uses command-forwarding;
       leaf from-zone {
         description "Show the policy information matching the given source zone";
         type string;
       }
       leaf to-zone {
         description "Show the policy information matching the given destination zone";
         type string;
       }
       leaf detail {
         description "Show the detailed dynamic policy information";
         type empty;
       }
       leaf scope-id {
         description "Show the policy information matching the given scope policy id [4...MAX_POLICIES]";
         type union {
           type string {
             pattern "<.*>|$.*";
           }
           type uint32 {
             range "4 .. 4294967295";
           }
         }
       }
     }
     output {
       choice output_c {
         case output-tag {
           leaf output {
             type string;
           }
         }
         case actual-tag {
           anyxml security-dynamic-policies;
         }
         case multichassis-tag {
           anyxml multi-routing-engine-results;
         }
       }
     }
   }
   rpc get-swrss-io-information {
     description "Show swrss io status";
     output {
       choice output_c {
         case output-tag {
           leaf output {
             type string;
           }
         }
         case actual-tag {
           anyxml flow-swrss-io;
         }
         case multichassis-tag {
           anyxml multi-routing-engine-results;
         }
       }
     }
   }
   rpc get-pmi-statistics-all {
     description "Show pmi statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml flow-pmi-statistics;
         }
         case multichassis-tag {
           anyxml multi-routing-engine-results;
         }
       }
     }
   }
   rpc get-tunnel-inspection-statistics-all {
     description "Show tunnel-inspection statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml flow-tunnel-inspection-statistics;
         }
         case multichassis-tag {
           anyxml multi-routing-engine-results;
         }
       }
     }
   }
   rpc get-flow-statistics-all {
     description "Show flow statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml flow-statistics-all;
         }
         case multichassis-tag {
           anyxml multi-routing-engine-results;
         }
       }
     }
   }
   rpc get-flow-status-all {
     description "Show flow status";
     input {
       uses command-forwarding;
       choice lsys {
         case logical-system {
         }
         case root-logical-system {
           leaf root-logical-system {
             description "Root logical-system (default)";
             type empty;
           }
         }
         case tenant {
         }
       }
     }
     output {
       choice output_c {
         case output-tag {
           leaf output {
             type string;
           }
         }
         case actual-tag {
           anyxml flow-status-all;
         }
         case multichassis-tag {
           anyxml multi-routing-engine-results;
         }
       }
     }
   }
   rpc get-flow-gate-information {
     description "Show gate information";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "brief";
         type enumeration {
           enum "summary" {
             description "Show output summary";
           }
           enum "brief" {
             description "Show brief output (default)";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml flow-gate-information;
         }
         case multichassis-tag {
           anyxml multi-routing-engine-results;
         }
       }
     }
   }
   rpc get-flow-cp-session {
     description "Show CP sessions";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       leaf level {
         default "terse";
         type enumeration {
           enum "summary" {
             description "Show output summary";
           }
           enum "terse" {
             description "Show terse output (default)";
           }
         }
       }
       leaf flag-old {
         description "Obsoleted json-unfriendly format for old script compatibility";
         type enumeration {
           enum "old" {
             description "Show summary in old json-unfriendly format";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf conn-tag {
         description "Session connection tag";
         type union {
           type string {
             pattern "<.*>|$.*";
           }
           type uint32 {
             range "0 .. 4294967295";
           }
         }
       }
     }
     output {
       choice output_c {
         case output-tag {
           leaf output {
             type string;
           }
         }
         case actual-tag {
           anyxml flow-cp-session;
         }
         case multichassis-tag {
           anyxml multi-routing-engine-results;
         }
       }
     }
   }
   rpc get-advanced-connection-tracking-entries {
     description "Advanced-connection-tracking table";
     input {
       uses command-forwarding;
       leaf family {
         description "Protocol family";
         type enumeration {
           enum "inet" {
             description "Show IPv4";
           }
           enum "inet6" {
             description "Show IPv6/IPv6-NATPT";
           }
         }
       }
       leaf destination-prefix {
         description "Destination IP prefix or address";
         type jt:ipprefix;
       }
       leaf source-prefix {
         description "Source IP prefix or address";
         type jt:ipprefix;
       }
       leaf destination-port {
         description "Destination port";
         type union {
           type string {
             pattern "<.*>|$.*";
           }
           type uint32 {
             range "0 .. 65535";
           }
         }
       }
       leaf protocol {
         description "IP protocol number";
         type string;
       }
       leaf zone-name {
         description "Zone name";
         type string;
       }
       leaf type-of-entry {
         description "Advanced-connection-tracking entry type";
         type enumeration {
           enum "any-host" {
             description "Advanced-connection-tracking table any-host entry";
           }
           enum "target-host" {
             description "Advanced-connection-tracking table target-host entry";
           }
           enum "target-host-port" {
             description "Advanced-connection-tracking table target-host-port entry";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf level {
         default "terse";
         type enumeration {
           enum "summary" {
             description "Show output summary";
           }
           enum "terse" {
             description "Show terse output (default)";
           }
         }
       }
     }
     output {
       choice output_c {
         case output-tag {
           leaf output {
             type string;
           }
         }
         case actual-tag {
           anyxml advanced-connection-tracking-table;
         }
         case multichassis-tag {
           anyxml multi-routing-engine-results;
         }
       }
     }
   }
   rpc get-flow-session-information {
     description "Show session table";
     input {
       uses command-forwarding;
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf level {
         default "brief";
         type enumeration {
           enum "summary" {
             description "Show output summary";
           }
           enum "brief" {
             description "Show brief output (default)";
           }
           enum "extensive" {
             description "Show detailed output";
           }
           enum "pretty" {
             description "Show output pretty";
           }
           enum "plugins" {
             description "Show session plugins";
           }
         }
       }
       leaf flag-old {
         description "Obsoleted json-unfriendly format for old script compatibility";
         type enumeration {
           enum "old" {
             description "Show summary in old json-unfriendly format";
           }
         }
       }
       leaf enc {
         type enumeration {
           enum "encrypted" {
             description "Show encrypted traffic";
           }
         }
       }
       leaf add-on {
         type enumeration {
           enum "idp" {
             description "IDP sessions";
           }
           enum "ssl" {
             description "SSL sessions";
           }
           enum "tunnel" {
             description "Tunnel sessions";
           }
           enum "nat" {
             description "Sessions with network address translation";
           }
           enum "services-offload" {
             description "Services-offload sessions";
           }
           enum "resource-manager" {
             description "Sessions with resource manager";
           }
           enum "application-firewall" {
             description "Show application-firewall sessions";
           }
           enum "application-traffic-control" {
             description "Show application-traffic-control sessions";
           }
           enum "security-intelligence" {
             description "Show security-intelligence sessions";
           }
           enum "advanced-anti-malware" {
             description "Show advanced-anti-malware sessions";
           }
           enum "anti-virus" {
             description "Show anti-virus sessions";
           }
         }
       }
       leaf application {
         description "Application protocol name";
         type enumeration {
           enum "dns" {
             description "Domain Name Service";
           }
           enum "ftp" {
             description "File Transfer Protocol";
           }
           enum "ignore" {
             description "Ignore application type";
           }
           enum "mgcp-ca" {
             description "MGCP-CA";
           }
           enum "mgcp-ua" {
             description "MGCP-UA";
           }
           enum "ms-rpc" {
             description "Microsoft RPC";
           }
           enum "pptp" {
             description "Point-to-Point Tunneling Protocol";
           }
           enum "sun-rpc" {
             description "Sun Microsystems RPC";
           }
           enum "q931" {
             description "Q.931";
           }
           enum "ras" {
             description "RAS";
           }
           enum "realaudio" {
             description "RealAudio";
           }
           enum "rsh" {
             description "Remote Shell";
           }
           enum "rtsp" {
             description "Real Time Streaming Protocol";
           }
           enum "sccp" {
             description "Skinny Client Control Protocol";
           }
           enum "sip" {
             description "Session Initiation Protocol";
           }
           enum "sqlnet-v2" {
             description "Oracle SQL*Net Version 2";
           }
           enum "talk" {
             description "Talk program";
           }
           enum "tftp" {
             description "Trivial File Transfer Protocol";
           }
           enum "http" {
             description "Hyper Text transfer protocol";
           }
           enum "https" {
             description "Secure HyperText Transfer Protocol";
           }
           enum "smtp" {
             description "Simple Mail Transfer Protocol";
           }
           enum "imap" {
             description "Internet Message Access Protocol";
           }
           enum "ssh" {
             description "Secure Shell";
           }
           enum "telnet" {
             description "Telnet Terminal Emulation Protocol";
           }
         }
       }
       leaf family {
         description "Protocol family";
         type enumeration {
           enum "inet" {
             description "Show IPv4";
           }
           enum "inet6" {
             description "Show IPv6/IPv6-NATPT";
           }
         }
       }
       leaf policy-id {
         description "Policy id value";
         type union {
           type string {
             pattern "<.*>|$.*";
           }
           type uint32 {
             range "1 .. 4294967295";
           }
         }
       }
       leaf zone {
         description "Zone name";
         type string;
       }
       leaf interface {
         description "Name of incoming or outgoing interface";
         type string;
       }
       leaf application-firewall-rule-set {
         description "Show application-firewall session by rule-set";
         type string;
       }
       leaf application-traffic-control-rule-set {
         description "Show application-traffic-control session by rule-set";
         type string;
       }
       leaf dynamic-application {
         description "Dynamic application name";
         type string;
       }
       leaf url-category {
         description "Show session by url-category";
         type string;
       }
       leaf dynamic-application-group {
         description "Dynamic application group name";
         type string;
       }
       leaf start-identifier {
         description "Show sessions from this start identifier";
         type union {
           type string {
             pattern "<.*>|$.*";
           }
           type uint64 {
             range "1 .. 18446744073709551615";
           }
         }
       }
       leaf count {
         description "Number of entries to show";
         type union {
           type string {
             pattern "<.*>|$.*";
           }
           type uint32 {
             range "1 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf conn-tag {
         description "Session connection tag";
         type union {
           type string {
             pattern "<.*>|$.*";
           }
           type uint32 {
             range "0 .. 4294967295";
           }
         }
       }
       leaf vrf-group {
         description "Session L3VPN VRF Group";
         type string;
       }
       leaf session-state {
         description "Session state";
         type enumeration {
           enum "warm" {
             description "L3 HA warm session ";
           }
           enum "backup" {
             description "L2 HA backup session";
           }
         }
       }
       leaf tunnel-inspection-type {
         description "Tunnel inspection type";
         type enumeration {
           enum "vxlan" {
             description "Show vxlan tunnel inspection";
           }
           enum "gre" {
             description "Show gre tunnel inspection";
           }
           enum "ipip" {
             description "Show ipip tunnel inspection";
           }
         }
       }
       leaf vxlan-vni {
         description "VXLAN VNI";
         type union {
           type string {
             pattern "<.*>|$.*";
           }
           type uint32 {
             range "0 .. 4294967295";
           }
         }
       }
       leaf ha-link {
         description "Show HA link session";
         type empty;
       }
       leaf plugin-name {
         description "Plugin name";
         type enumeration {
           enum "junos-idp" {
             description "Junos-idp";
           }
           enum "junos-idp-stream" {
             description "Junos-idp-stream";
           }
           enum "junos-appid-packet" {
             description "Junos-appid-packet";
           }
           enum "junos-appid-stream" {
             description "Junos-aapid-stream";
           }
           enum "junos-appqos" {
             description "Junos-appqos";
           }
           enum "junos-appfw" {
             description "Junos-appfw";
           }
           enum "junos-appfw-stream" {
             description "Junos-appfw-stream";
           }
           enum "junos-secintel" {
             description "Junos-secintel";
           }
           enum "junos-secintel-stream" {
             description "Junos-secintel-stream";
           }
           enum "junos-aamw" {
             description "Junos-aamw";
           }
           enum "junos-aamw-stream" {
             description "Junos-aamw-stream";
           }
           enum "junos-alg" {
             description "Junos-alg";
           }
           enum "junos-gprs" {
             description "Junos-gprs";
           }
           enum "junos-utm-uf-pkt" {
             description "Junos-utm-uf-pkt";
           }
           enum "junos-utm-uf-stream" {
             description "Junos-utm-uf-stream";
           }
           enum "junos-utm" {
             description "Junos-utm";
           }
           enum "junos-utm-udp" {
             description "Junos-utm-udp";
           }
           enum "junos-icap-redirect" {
             description "Junos-icap-redirect";
           }
           enum "junos-uac" {
             description "Junos-uac";
           }
           enum "junos-rtm" {
             description "Junos-rtm";
           }
           enum "junos-captive-portal" {
             description "Junos-captive-portal";
           }
           enum "junos-tcp-svr-emul" {
             description "Junos-tcp-svr-emul";
           }
           enum "junos-tcp-clt-emul" {
             description "Junos-tcp-clt-emul";
           }
           enum "junos-hcm" {
             description "Junos-hcm";
           }
           enum "junos-hcm-pkt" {
             description "Junos-hcm-pkt";
           }
           enum "junos-slb-main" {
             description "Junos-slb-main";
           }
           enum "junos-slb-strm" {
             description "Junos-slb-strm";
           }
           enum "junos-slb-xlate" {
             description "Junos-slb-xlate";
           }
           enum "junos-screen-adapter" {
             description "Junos-screen-adapter";
           }
           enum "junos-fwauth-adapter" {
             description "Junos-fwauth-adapter";
           }
           enum "junos-fwauth-stream-adapter" {
             description "Junos-fwauth-stream-adapter";
           }
           enum "junos-syn-term" {
             description "Junos-syn-term";
           }
           enum "junos-syn-init" {
             description "Junos-syn-init";
           }
           enum "junos-test" {
             description "Junos-test";
           }
           enum "junos-ssl-term" {
             description "Junos-ssl-term";
           }
           enum "junos-ssl-init" {
             description "Junos-ssl-init";
           }
           enum "junos-ssl-proxy" {
             description "Junos-ssl-proxy";
           }
           enum "jsf-ssl-test" {
             description "Jsf-ssl-test";
           }
           enum "junos-jwx-policy" {
             description "Junos-jwx-policy";
           }
           enum "junos-jwx-cifs" {
             description "Junos-jwx-cifs";
           }
           enum "junos-jwx-zlib" {
             description "Junos-jwx-zlib";
           }
           enum "junos-cpcd" {
             description "Junos-cpcd";
           }
           enum "junos-rpm" {
             description "Junos-rpm";
           }
           enum "junos-subsc" {
             description "Junos-subsc";
           }
           enum "junos-mobile-subsc" {
             description "Junos-mobile-subsc";
           }
           enum "junos-pcef" {
             description "Junos-pcef";
           }
           enum "junos-tcp-utils" {
             description "Junos-tcp-utils";
           }
           enum "junos-userfw" {
             description "Junos-userfw";
           }
           enum "junos-jcpp" {
             description "Junos-jcpp";
           }
           enum "junos-rtcom-stream" {
             description "Junos-rtcom-stream";
           }
           enum "junos-rtcom" {
             description "Junos-rtcom";
           }
           enum "junos-log" {
             description "Junos-log";
           }
           enum "junos-jdpi" {
             description "Junos-jdpi";
           }
           enum "junos-dpi-stream" {
             description "Junos-dpi-stream";
           }
           enum "junos-lrf" {
             description "Junos-lrf";
           }
           enum "junos-ipsec" {
             description "Junos-ipsec";
           }
           enum "junos-apbr-main" {
             description "Junos-apbr-main";
           }
           enum "junos-url-filter" {
             description "Junos-url-filter";
           }
           enum "junos-remote-access-gw" {
             description "Junos-remote-access-gw";
           }
           enum "junos-dynapp" {
             description "Junos-dynapp";
           }
           enum "junos-dynapp-stream" {
             description "Junos-dynapp-stream";
           }
           enum "junos-telemetry" {
             description "Junos-telemetry";
           }
           enum "junos-appqoe" {
             description "Junos-appqoe";
           }
           enum "junos-appqoe-stream" {
             description "Junos-appqoe-stream";
           }
           enum "junos-amr" {
             description "Junos-amr";
           }
           enum "junos-cos" {
             description "Junos-cos";
           }
           enum "junos-tcplog" {
             description "Junos-tcplog";
           }
           enum "junos-stateful-ha" {
             description "Junos-stateful-ha";
           }
           enum "junos-web-proxy" {
             description "Junos-web-proxy";
           }
           enum "junos-web-proxy-pkt" {
             description "Junos-web-proxy-pkt";
           }
           enum "junos-web-proxy-sentinel" {
             description "Junos-web-proxy-sentinel";
           }
           enum "junos-emsdp-main" {
             description "Junos-emsdp-main";
           }
           enum "junos-health-check" {
             description "Junos-health-check";
           }
           enum "junos-ha-peer-infra" {
             description "Junos-ha-peer-infra";
           }
           enum "junos-softwire-head" {
             description "Junos-softwire-head";
           }
           enum "junos-softwire-tail" {
             description "Junos-softwire-tail";
           }
           enum "junos-csrx" {
             description "Junos-csrx";
           }
           enum "junos-srx-inline-ka-rt" {
             description "Junos-srx-inline-ka-rt";
           }
           enum "junos-utm-cf-stream" {
             description "Junos-utm-cf-stream";
           }
           enum "junos-utm-cf-pkt" {
             description "Junos-utm-cf-pkt";
           }
         }
       }
       leaf plugin-status {
         description "Plugin status";
         type enumeration {
           enum "interested" {
             description "Session's plugin is interested";
           }
           enum "ignore" {
             description "Session's plugin is ignored";
           }
         }
       }
       leaf duration-more-than {
         description "Session's duration time is more";
         type union {
           type string {
             pattern "<.*>|$.*";
           }
           type uint32 {
             range "1 .. 100000";
           }
         }
       }
       leaf duration-less-than {
         description "Session's duration time is less";
         type union {
           type string {
             pattern "<.*>|$.*";
           }
           type uint32 {
             range "1 .. 100000";
           }
         }
       }
       leaf timeout-more-than {
         description "Session's timeout value is more";
         type union {
           type string {
             pattern "<.*>|$.*";
           }
           type uint32 {
             range "1 .. 100000";
           }
         }
       }
       leaf timeout-less-than {
         description "Session's timeout value is less";
         type union {
           type string {
             pattern "<.*>|$.*";
           }
           type uint32 {
             range "1 .. 100000";
           }
         }
       }
       leaf curr-more-than {
         description "Session's current-timeout value is more";
         type union {
           type string {
             pattern "<.*>|$.*";
           }
           type uint32 {
             range "1 .. 100000";
           }
         }
       }
       leaf curr-less-than {
         description "Session's current-timeout value is less";
         type union {
           type string {
             pattern "<.*>|$.*";
           }
           type uint32 {
             range "1 .. 100000";
           }
         }
       }
       leaf packets-more-than {
         description "Session's packets-count is more";
         type union {
           type string {
             pattern "<.*>|$.*";
           }
           type uint32 {
             range "1 .. 4294967295";
           }
         }
       }
       leaf packets-less-than {
         description "Session's packets-count is less";
         type union {
           type string {
             pattern "<.*>|$.*";
           }
           type uint32 {
             range "1 .. 4294967295";
           }
         }
       }
       leaf bytes-more-than {
         description "Session's bytes-count is more";
         type union {
           type string {
             pattern "<.*>|$.*";
           }
           type uint32 {
             range "1 .. 4294967295";
           }
         }
       }
       leaf bytes-less-than {
         description "Session's bytes-count is less";
         type union {
           type string {
             pattern "<.*>|$.*";
           }
           type uint32 {
             range "1 .. 4294967295";
           }
         }
       }
       leaf source-tenant {
         description "Vector routing source tenant";
         type string;
       }
       leaf destination-service {
         description "Vector routing destination service";
         type string;
       }
     }
     output {
       choice output_c {
         case output-tag {
           leaf output {
             type string;
           }
         }
         case actual-tag {
           anyxml security-flow-information;
         }
         case multichassis-tag {
           anyxml multi-routing-engine-results;
         }
       }
     }
   }
   rpc get-flow-session-by-identifier {
     description "Show session with specified session identifier";
     input {
       uses command-forwarding;
       leaf session-identifier {
         description "Session identifier";
         type union {
           type string {
             pattern "<.*>|$.*";
           }
           type uint64 {
             range "1 .. 18446744073709551615";
           }
         }
         mandatory true;
       }
       leaf level {
         type enumeration {
           enum "pretty" {
             description "Show output pretty";
           }
           enum "plugins" {
             description "Show session plugins";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml flow-session-information;
         }
         case multichassis-tag {
           anyxml multi-routing-engine-results;
         }
       }
     }
   }
   rpc get-flow-session-summary-idp {
     description "Show IDP session summary";
     status deprecated;
     output {
       choice output_c {
         case output-tag {
           leaf output {
             type string;
           }
         }
         case actual-tag {
           anyxml idp-session-summary-information;
         }
         case multichassis-tag {
           anyxml multi-routing-engine-results;
         }
       }
     }
   }
   rpc get-flow-ipaction-information {
     description "Show ip-action table";
     input {
       leaf source-prefix {
         description "Source IP prefix or address";
         type jt:ipprefix;
       }
       leaf destination-prefix {
         description "Destination IP prefix or address";
         type jt:ipprefix;
       }
       leaf source-port {
         description "Source port";
         type union {
           type string {
             pattern "<.*>|$.*";
           }
           type uint32 {
             range "1 .. 65535";
           }
         }
       }
       leaf destination-port {
         description "Destination port";
         type union {
           type string {
             pattern "<.*>|$.*";
           }
           type uint32 {
             range "1 .. 65535";
           }
         }
       }
       leaf protocol {
         description "IP protocol number";
         type string;
       }
       leaf family {
         description "Protocol family";
         type enumeration {
           enum "inet" {
             description "Show IPv4";
           }
           enum "inet6" {
             description "Show IPv6/IPv6-NATPT";
           }
         }
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
       leaf level {
         default "brief";
         type enumeration {
           enum "summary" {
             description "Show output summary";
           }
           enum "brief" {
             description "Show brief output (default)";
           }
         }
       }
     }
     output {
       choice output_c {
         case output-tag {
           leaf output {
             type string;
           }
         }
         case actual-tag {
           anyxml flow-ipaction-information;
         }
         case multichassis-tag {
           anyxml multi-routing-engine-results;
         }
       }
     }
   }
   rpc get-flow-ipaction-information-all {
     description "Show all ip-action entries";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       choice output_c {
         case output-tag {
           leaf output {
             type string;
           }
         }
         case actual-tag {
           anyxml flow-ipaction-information;
         }
         case multichassis-tag {
           anyxml multi-routing-engine-results;
         }
       }
     }
   }
   rpc get-forward-options-information {
     description "Show forward-options status";
     output {
       choice output_c {
         case output-tag {
           leaf output {
             type string;
           }
         }
         case actual-tag {
           anyxml forward-options-information;
         }
         case multichassis-tag {
           anyxml multi-routing-engine-results;
         }
       }
     }
   }
   rpc get-secure-wire-information {
     description "Show secure wire information";
     input {
       uses command-forwarding;
       choice lsys {
         case logical-system {
         }
         case root-logical-system {
           leaf root-logical-system {
             description "Root logical-system (default)";
             type empty;
           }
         }
       }
       leaf secure-wire-name {
         description "Display specified secure wire";
         type string;
       }
     }
     output {
       choice output_c {
         case output-tag {
           leaf output {
             type string;
           }
         }
         case actual-tag {
           anyxml secure-wire-information;
         }
         case multichassis-tag {
           anyxml multi-routing-engine-results;
         }
       }
     }
   }
   rpc get-flow-resource-manager-settings {
     description "Show resource manager settings";
     output {
       choice output_c {
         case output-tag {
           leaf output {
             type string;
           }
         }
         case actual-tag {
           anyxml flow-resource-manager-settings;
         }
         case multichassis-tag {
           anyxml multi-routing-engine-results;
         }
       }
     }
   }
   rpc get-resource-manager-status-details {
     description "Show resource manager status";
     output {
       choice output_c {
         case output-tag {
           leaf output {
             type string;
           }
         }
         case actual-tag {
           anyxml resource-manager-status-details;
         }
         case multichassis-tag {
           anyxml multi-routing-engine-results;
         }
       }
     }
   }
   rpc get-dpts-status-all {
     description "Show dataplane sleep status";
     output {
       choice output_c {
         case output-tag {
           leaf output {
             type string;
           }
         }
         case actual-tag {
           anyxml flow-vsrx-dpts-status;
         }
         case multichassis-tag {
           anyxml multi-routing-engine-results;
         }
       }
     }
   }
   rpc get-mirror-filter {
     description "Show  mirror-filter with specified filter-name";
     input {
       uses command-forwarding;
       choice filter {
         case name {
           leaf get-mirror-filter-by-name {
             description "Mirror filter name";
             type string;
             mandatory true;
           }
         }
         case all {
           leaf get-mirror-filter-all {
             description "List all mirror filters Counter";
             type empty;
           }
         }
       }
     }
     output {
       choice output_c {
         case output-tag {
           leaf output {
             type string;
           }
         }
         case actual-tag {
           anyxml show-mirror-filter-entry;
         }
         case multichassis-tag {
           anyxml multi-routing-engine-results;
         }
       }
     }
   }
   rpc get-packet-drop-records-all {
     description "Show packet-drop records";
     output {
       choice output_c {
         case output-tag {
           leaf output {
             type string;
           }
         }
         case actual-tag {
           anyxml packet-drop-records;
         }
         case multichassis-tag {
           anyxml multi-routing-engine-results;
         }
       }
     }
   }
   rpc get-firewall-authentication-jims {
     description "Show JIMS information";
     input {
       uses command-forwarding;
       choice filter {
         case statistics {
           leaf get-firewall-authentication-jims-statistics {
             description "Show firewall authentication JIMS statistics";
             type empty;
           }
         }
       }
     }
     output {
       choice output_c {
         case output-tag {
           leaf output {
             type string;
           }
         }
         case actual-tag {
           anyxml firewall-authentication-jims;
         }
         case multichassis-tag {
           anyxml multi-routing-engine-results;
         }
       }
     }
   }
   rpc get-firewall-authentication-users {
     description "Show current firewall authentication users";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case identifier {
           leaf get-firewall-authentication-users-specific {
             description "Locate authentication entry by id";
             type union {
               type uint32;
               type string {
                 pattern "<.*>|$.*";
               }
             }
           }
         }
         case auth-type {
           leaf get-firewall-authentication-users {
             description "Show authentication entry matching the given auth-type";
             type enumeration {
               enum "user-firewall" {
                 description "User firewall authentication";
               }
               enum "pass-through" {
                 description "Pass-through authentication";
               }
               enum "web-authentication" {
                 description "Web firewall authentication";
               }
             }
           }
         }
         case address {
           leaf get-firewall-authentication-users-specific {
             description "Locate authentication entry by ip address";
             type jt:ipprefix;
           }
         }
         case from-zone {
           leaf from-zone {
             description "Show authentication entry matching the given source zone, null for web-auth and userfw-auth";
             type string;
           }
         }
         case to-zone {
           leaf to-zone {
             description "Show authentication entry matching the given destination zone, null for web-auth and userfw-auth";
             type string;
           }
         }
       }
     }
     output {
       choice output_c {
         case output-tag {
           leaf output {
             type string;
           }
         }
         case actual-tag {
           anyxml firewall-authentication-users;
         }
         case multichassis-tag {
           anyxml multi-routing-engine-results;
         }
       }
     }
   }
   rpc get-firewall-authentication-history {
     description "Show firewall authentication history";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case identifier {
           leaf get-firewall-authentication-history-specific {
             description "Locate authentication history by id";
             type union {
               type uint32;
               type string {
                 pattern "<.*>|$.*";
               }
             }
           }
         }
         case address {
           leaf get-firewall-authentication-history-specific {
             description "Locate authentication history by ip address";
             type jt:ipprefix;
           }
         }
         case from-zone {
           leaf from-zone {
             description "Show authentication history matching the given source zone, null for web-auth and userfw-auth";
             type string;
           }
         }
         case to-zone {
           leaf to-zone {
             description "Show authentication history matching the given destination zone, null for web-auth and userfw-auth";
             type string;
           }
         }
       }
     }
     output {
       choice output_c {
         case output-tag {
           leaf output {
             type string;
           }
         }
         case actual-tag {
           anyxml firewall-authentication-history;
         }
         case multichassis-tag {
           anyxml multi-routing-engine-results;
         }
       }
     }
   }
   rpc get-security-screen-ids-data {
     description "Show screen data";
     output {
       choice output_c {
         case output-tag {
           leaf output {
             type string;
           }
         }
         case actual-tag {
           anyxml show-ids-data;
         }
         case multichassis-tag {
           anyxml multi-routing-engine-results;
         }
       }
     }
   }
   rpc get-security-screen-ids-whitelist {
     description "Show white list data";
     input {
       uses command-forwarding;
       leaf wlist-name {
         description "White list name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml show-ids-whitelist;
         }
         case multichassis-tag {
           anyxml multi-routing-engine-results;
         }
       }
     }
   }
   rpc get-security-screen-ids-status {
     description "Show status of screen object";
     input {
       uses command-forwarding;
       leaf screen-name {
         description "Screen name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml show-ids-status;
         }
         case multichassis-tag {
           anyxml multi-routing-engine-results;
         }
       }
     }
   }
   rpc get-ids-statistics {
     description "Show screen attack statistics information";
     input {
       uses command-forwarding;
       choice filter {
         case zone {
           leaf zone {
             description "IDS statistics zone";
             type string;
           }
         }
         case interface {
           leaf interface {
             description "IDS statistics interface";
             type string;
           }
         }
       }
       leaf ip {
         description "IDS statistics ip";
         type enumeration {
           enum "tunnel" {
             description "IDS statistics ip tunnel";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml ids-statistics;
         }
         case multichassis-tag {
           anyxml multi-routing-engine-results;
         }
       }
     }
   }
   rpc get-destination-nat-pool-information {
     description "Show destination NAT address-pool information";
     input {
       uses command-forwarding;
       choice pool-choice {
         case pool-name {
           leaf pool-name {
             description "Destination address pool name";
             type string {
               length "1 .. 64";
             }
             mandatory true;
           }
         }
         case all {
           leaf all {
             description "Display all destination NAT address-pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-pool-information;
         }
         case multichassis-tag {
           anyxml multi-routing-engine-results;
         }
       }
     }
   }
   rpc get-destination-nat-rule-sets-information {
     description "Show destination NAT rule-set information";
     input {
       uses command-forwarding;
       choice rule-choice {
         case rule-name {
           leaf rule-name {
             description "Destination NAT rule name";
             type string {
               length "1 .. 64";
             }
             mandatory true;
           }
         }
         case all {
           leaf all {
             description "Display all destination NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-rule-sets;
         }
         case multichassis-tag {
           anyxml multi-routing-engine-results;
         }
       }
     }
   }
   rpc get-destination-nat-rule-application-information {
     description "Show destination NAT rule application information";
     input {
       uses command-forwarding;
       choice rule-choice {
         case rule-name {
           leaf rule-name {
             description "Destination NAT rule name";
             type string {
               length "1 .. 64";
             }
             mandatory true;
           }
         }
         case all {
           leaf all {
             description "Display all destination NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-rule-application-information;
         }
         case multichassis-tag {
           anyxml multi-routing-engine-results;
         }
       }
     }
   }
   rpc retrieve-destination-nat-summary-information {
     description "Show destination NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-summary-information;
         }
         case multichassis-tag {
           anyxml multi-routing-engine-results;
         }
       }
     }
   }
   rpc retrieve-source-nat-pool-information {
     description "Show source NAT information of this pool";
     input {
       uses command-forwarding;
       choice pool-choice {
         case pool-name {
           leaf pool-name {
             description "Source address pool name";
             type string;
             mandatory true;
           }
         }
         case all {
           leaf all {
             description "Display all source NAT pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-pool-information;
         }
         case multichassis-tag {
           anyxml multi-routing-engine-results;
         }
       }
     }
   }
   rpc get-persist-nat-all {
     description "Show all persistent NAT information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf family {
         description "Protocol family";
         type enumeration {
           enum "inet" {
             description "Show IPv4";
           }
           enum "inet6" {
             description "Show IPv6/IPv6-NATV6V4";
           }
         }
       }
     }
     output {
       choice output_c {
         case output-tag {
           leaf output {
             type string;
           }
         }
         case actual-tag {
           anyxml persist-nat-all;
         }
         case multichassis-tag {
           anyxml multi-routing-engine-results;
         }
       }
     }
   }
   rpc get-persist-nat-sum {
     description "Show persistent NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml persist-nat-sum;
         }
         case multichassis-tag {
           anyxml multi-routing-engine-results;
         }
       }
     }
   }
   rpc retrieve-persist-nat-pool-information {
     description "Show persistent NAT information of this pool";
     input {
       uses command-forwarding;
       leaf pool-name {
         description "Source NAT pool name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml persist-nat-pool-information;
         }
         case multichassis-tag {
           anyxml multi-routing-engine-results;
         }
       }
     }
   }
   rpc get-persist-nat-interface-information {
     description "Show persistent NAT information of this interface";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-summary;
         }
         case multichassis-tag {
           anyxml multi-routing-engine-results;
         }
       }
     }
   }
   rpc retrieve-persist-nat-ip-port-information {
     description "Show persistent NAT information of internal IP and port";
     input {
       uses command-forwarding;
       leaf ip {
         description "Internal IP address";
         type jt:ipaddr;
         mandatory true;
       }
       leaf internal-port {
         description "Internal port";
         type union {
           type uint16;
           type string {
             pattern "<.*>|$.*";
           }
         }
       }
       leaf internal-protocol {
         description "Internal protocol";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml persist-nat-ip-port-information;
         }
         case multichassis-tag {
           anyxml multi-routing-engine-results;
         }
       }
     }
   }
   rpc get-src-nat-port-block {
     description "Show port block allocation information";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-port-block;
         }
         case multichassis-tag {
           anyxml multi-routing-engine-results;
         }
       }
     }
   }
   rpc get-deterministic-nat {
     description "Show deterministic port block allocation information";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-deterministic;
         }
         case multichassis-tag {
           anyxml multi-routing-engine-results;
         }
       }
     }
   }
   rpc get-det-nat-host-sddr-range {
     description "Show deterministic host address range without overlap";
     input {
       uses command-forwarding;
       leaf pool {
         description "Source NAT pool name";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-det-host-sddr-range;
         }
         case multichassis-tag {
           anyxml multi-routing-engine-results;
         }
       }
     }
   }
   rpc retrieve-source-nat-paired-address-information {
     description "Show paired address information";
     input {
       uses command-forwarding;
       leaf pool-name {
         description "Address pool name";
         type string;
       }
       choice ip-choice {
         case internal-ip {
           leaf internal-ip {
             description "Internal IP address";
             type jt:ipaddr;
           }
         }
         case xlated-ip {
           leaf xlated-ip {
             description "Xlated IP address";
             type jt:ipaddr;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-paired-address-information;
         }
         case multichassis-tag {
           anyxml multi-routing-engine-results;
         }
       }
     }
   }
   rpc get-source-nat-rule-sets-information {
     description "Show source NAT rule-set information";
     input {
       uses command-forwarding;
       choice rule-choice {
         case rule-name {
           leaf rule-name {
             description "Source NAT rule name";
             type string {
               length "1 .. 64";
             }
             mandatory true;
           }
         }
         case all {
           leaf all {
             description "Display all source NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-rule-sets-information;
         }
         case multichassis-tag {
           anyxml multi-routing-engine-results;
         }
       }
     }
   }
   rpc get-source-nat-rule-application-information {
     description "Show source NAT rule application information";
     input {
       uses command-forwarding;
       choice rule-choice {
         case rule-name {
           leaf rule-name {
             description "Source NAT rule name";
             type string {
               length "1 .. 64";
             }
             mandatory true;
           }
         }
         case all {
           leaf all {
             description "Display all source NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-rule-application-information;
         }
         case multichassis-tag {
           anyxml multi-routing-engine-results;
         }
       }
     }
   }
   rpc retrieve-source-nat-summary {
     description "Show source NAT summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-summary;
         }
         case multichassis-tag {
           anyxml multi-routing-engine-results;
         }
       }
     }
   }
   rpc get-source-nat-pool-distribution {
     description "Show source NAT pool-distribution";
     output {
       choice output_c {
         case output-tag {
           leaf output {
             type string;
           }
         }
         case actual-tag {
           anyxml source-nat-pool-distribution;
         }
         case multichassis-tag {
           anyxml multi-routing-engine-results;
         }
       }
     }
   }
   rpc get-static-nat-rule-information {
     description "Show static NAT rule information";
     input {
       uses command-forwarding;
       choice rule-choice {
         case rule-name {
           leaf rule-name {
             description "Static NAT rule name";
             type string {
               length "1 .. 64";
             }
             mandatory true;
           }
         }
         case all {
           leaf all {
             description "Display all static NAT rule information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml static-nat-rule-information;
         }
         case multichassis-tag {
           anyxml multi-routing-engine-results;
         }
       }
     }
   }
   rpc get-interface-nat-ports-information {
     description "Show interface nat ports information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml interface-nat-ports-information;
         }
         case multichassis-tag {
           anyxml multi-routing-engine-results;
         }
       }
     }
   }
   rpc retrieve-source-nat-pool-resource-usage {
     description "Show source pool resource usage information";
     input {
       uses command-forwarding;
       choice pool-choice {
         case pool-name {
           leaf pool-name {
             description "Source address pool name";
             type string;
             mandatory true;
           }
         }
         case all {
           leaf all {
             description "Display all source NAT pool resource usage";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-pool-resource-usage;
         }
         case multichassis-tag {
           anyxml multi-routing-engine-results;
         }
       }
     }
   }
   rpc get-firewall-policies {
     description "Show security firewall policies";
     input {
       uses command-forwarding;
       leaf from-zone {
         description "Show the policy information matching the given source zone";
         type string;
       }
       leaf to-zone {
         description "Show the policy information matching the given destination zone";
         type string;
       }
       leaf policy-set {
         description "Show the policy information matching the given policy-set";
         type string;
       }
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml security-policies;
         }
         case multichassis-tag {
           anyxml multi-routing-engine-results;
         }
       }
     }
   }
   rpc get-security-policies-hit-count {
     description "Show the hit count of policies";
     input {
       uses command-forwarding;
       leaf from-zone {
         description "Show the policy hit-count matching the given source zone";
         type string;
       }
       leaf to-zone {
         description "Show the policy hit-count matching the given destination zone";
         type string;
       }
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
       leaf detail {
         description "Show the detailed information";
         type empty;
       }
       leaf policy-name {
         description "Show the policy information matching the given policy name";
         type string;
       }
       leaf dynamic-applications {
         description "Show hit-count for each dynamic-application of this policy";
         type empty;
       }
       leaf url-categories {
         description "Show hit-count for each url-category of this policy";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml policy-hit-count;
         }
         case multichassis-tag {
           anyxml multi-routing-engine-results;
         }
       }
     }
   }
   rpc get-global-firewall-policies {
     description "Show the policy information of global policies";
     input {
       uses command-forwarding;
       leaf policy-name {
         description "Show the policy information matching the given policy name";
         type string;
       }
       leaf detail {
         description "Show the detailed information";
         type empty;
       }
       leaf zone-context {
         description "Show the count of policies in each context (from-zone and to-zone)";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       leaf application-firewall {
         description "Show the information of application-firewall";
         type empty;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml security-global-policies;
         }
         case multichassis-tag {
           anyxml multi-routing-engine-results;
         }
       }
     }
   }
   rpc unknown-source-identity-of-policies {
     description "Show the unknown-source-identity of policy";
     output {
       choice output_c {
         case output-tag {
           leaf output {
             type string;
           }
         }
         case actual-tag {
           anyxml unknown-source-identity;
         }
         case multichassis-tag {
           anyxml multi-routing-engine-results;
         }
       }
     }
   }
   rpc get-firewall-policies-information {
     description "Show the policy information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml policy-internal-information;
         }
         case multichassis-tag {
           anyxml multi-routing-engine-results;
         }
       }
     }
   }
   rpc get-policy-checksum-information {
     description "Show policy information checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       choice output_c {
         case output-tag {
           leaf output {
             type string;
           }
         }
         case actual-tag {
           anyxml policy-context-checksum-info;
         }
         case multichassis-tag {
           anyxml multi-routing-engine-results;
         }
       }
     }
   }
   rpc match-firewall-policies {
     description "Show security match policies";
     input {
       uses command-forwarding;
       choice lsys {
         case logical-system {
         }
         case root-logical-system {
           leaf root-logical-system {
             description "Root logical-system (default)";
             type empty;
           }
         }
         case tenant {
         }
       }
       leaf from-zone {
         description "Match policy for the given source zone(optional for global policies)";
         type string;
         mandatory true;
       }
       leaf to-zone {
         description "Match policy for the given destination zone (optional for global policies)";
         type string;
         mandatory true;
       }
       leaf policy-set {
         description "Match policy for the given policy-set";
         type string;
       }
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf url-category {
         description "Match policy for the given url category";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf source-end-user-profile {
         description "Match policy for the given source-end-user-profile (optional)";
         type string;
       }
       leaf source-vrf {
         description "Match policy for the given source vrf (optional)";
         type string;
       }
       leaf destination-vrf {
         description "Match policy for the given destination vrf (optional)";
         type string;
       }
     }
     output {
       choice output_c {
         case output-tag {
           leaf output {
             type string;
           }
         }
         case actual-tag {
           anyxml security-policy-match;
         }
         case multichassis-tag {
           anyxml multi-routing-engine-results;
         }
       }
     }
   }
   rpc match-global-policies {
     description "Match global policy";
     input {
       uses command-forwarding;
       choice lsys {
         case logical-system {
         }
         case root-logical-system {
           leaf root-logical-system {
             description "Root logical-system (default)";
             type empty;
           }
         }
         case tenant {
         }
       }
       leaf source-ip {
         description "Match policy for the given source IP";
         type string;
         mandatory true;
       }
       leaf destination-ip {
         description "Match policy for the given destination IP";
         type string;
         mandatory true;
       }
       leaf source-port {
         description "Match policy for the given source port";
         type union {
           type string {
             pattern "<.*>|$.*";
           }
           type uint32 {
             range "1 .. 65535";
           }
         }
         mandatory true;
       }
       leaf destination-port {
         description "Match policy for the given destination port";
         type union {
           type string {
             pattern "<.*>|$.*";
           }
           type uint32 {
             range "1 .. 65535";
           }
         }
         mandatory true;
       }
       leaf protocol {
         description "Match policy for the given protocol";
         type string;
         mandatory true;
       }
       leaf dynamic-application {
         description "Match policy for the given dynamic application";
         type string;
       }
       leaf url-category {
         description "Match policy for the given url category";
         type string;
       }
       leaf result-count {
         description "Expected results count (optional)";
         type union {
           type string {
             pattern "<.*>|$.*";
           }
           type uint32 {
             range "1 .. 16";
           }
         }
       }
       leaf source-identity {
         description "Match policy for the given roles (optional)";
         type string {
         }
       }
       leaf source-end-user-profile {
         description "Match policy for the given source-end-user-profile (optional)";
         type string;
       }
       leaf from-zone {
         description "Match policy for the given source zone(optional for global policies)";
         type string;
       }
       leaf to-zone {
         description "Match policy for the given destination zone (optional for global policies)";
         type string;
       }
       leaf source-vrf {
         description "Match policy for the given source vrf (optional)";
         type string;
       }
       leaf destination-vrf {
         description "Match policy for the given destination vrf (optional)";
         type string;
       }
     }
     output {
       choice output_c {
         case output-tag {
           leaf output {
             type string;
           }
         }
         case actual-tag {
           anyxml global-policy-match;
         }
         case multichassis-tag {
           anyxml multi-routing-engine-results;
         }
       }
     }
   }
   rpc get-firewall-policy-dns-cache {
     description "Show DNS cache of firewall policy";
     input {
       leaf dns-name {
         description "Show DNS cache matching the given DNS name";
         type string;
       }
     }
     output {
       choice output_c {
         case output-tag {
           leaf output {
             type string;
           }
         }
         case actual-tag {
           anyxml security-dns-cache;
         }
         case multichassis-tag {
           anyxml multi-routing-engine-results;
         }
       }
     }
   }
   rpc shadow-firewall-policies {
     description "Show security shadow policies";
     input {
       uses command-forwarding;
       choice lsys {
         case logical-system {
         }
         case root-logical-system {
           leaf root-logical-system {
             description "Root logical-system (default)";
             type empty;
           }
         }
         case tenant {
         }
       }
       leaf from-zone {
         description "Show shadow policy information for the given source zone";
         type string;
         mandatory true;
       }
       leaf to-zone {
         description "Show shadow policy information for the given destination zone";
         type string;
         mandatory true;
       }
       leaf policy {
         description "Show shadow policy information for the given policy";
         type string;
       }
       leaf reverse {
         description "Show the policies which shadows the given policy";
         type empty;
       }
     }
     output {
       choice output_c {
         case output-tag {
           leaf output {
             type string;
           }
         }
         case actual-tag {
           anyxml security-policy-shadow;
         }
         case multichassis-tag {
           anyxml multi-routing-engine-results;
         }
       }
     }
   }
   rpc shadow-global-policies {
     description "Shadow policy information for global policy";
     input {
       uses command-forwarding;
       choice lsys {
         case logical-system {
         }
         case root-logical-system {
           leaf root-logical-system {
             description "Root logical-system (default)";
             type empty;
           }
         }
         case tenant {
         }
       }
       leaf policy {
         description "Show shadow policy information for the given policy";
         type string;
       }
       leaf reverse {
         description "Show the policies which shadows the given policy";
         type empty;
       }
     }
     output {
       choice output_c {
         case output-tag {
           leaf output {
             type string;
           }
         }
         case actual-tag {
           anyxml global-policy-shadow;
         }
         case multichassis-tag {
           anyxml multi-routing-engine-results;
         }
       }
     }
   }
   rpc get-policy-report {
     description "Show security policy report";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf from-zone {
         description "Show policy report for the given source zone";
         type string;
       }
       leaf to-zone {
         description "Show policy reportfor the given destination zone";
         type string;
       }
       leaf report-type {
         description "Policy report";
         type enumeration {
           enum "shadowing" {
             description "Shadow report";
           }
           enum "redundant" {
             description "Redundant report";
           }
           enum "generalization" {
             description "Generalization report";
           }
           enum "consolidation" {
             description "Consolidation report";
           }
           enum "unused" {
             description "Unused report";
           }
           enum "expired" {
             description "Expired report";
           }
           enum "scheduler" {
             description "Scheduler report";
           }
           enum "no-comments" {
             description "No-comments report";
           }
           enum "no-logging" {
             description "No-logging report";
           }
           enum "most-hit" {
             description "Most-hit report";
           }
           enum "least-hit" {
             description "Least-hit report";
           }
           enum "30d-not-hit" {
             description "Not-hit-30-days report";
           }
           enum "60d-not-hit" {
             description "Not-hit-60-days report";
           }
           enum "90d-not-hit" {
             description "Not-hit-90-days report";
           }
           enum "1-year-not-hit" {
             description "Not-hit-1-year report";
           }
         }
       }
     }
     output {
       choice output_c {
         case output-tag {
           leaf output {
             type string;
           }
         }
         case actual-tag {
           anyxml security-policy-report;
         }
         case multichassis-tag {
           anyxml multi-routing-engine-results;
         }
       }
     }
   }
   rpc get-global-policies-repot {
     description "Show security policy report for global policy";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf report-type {
         description "Policy report";
         type enumeration {
           enum "shadowing" {
             description "Shadow report";
           }
           enum "redundant" {
             description "Redundant report";
           }
           enum "generalization" {
             description "Generalization report";
           }
           enum "consolidation" {
             description "Consolidation report";
           }
           enum "unused" {
             description "Unused report";
           }
           enum "expired" {
             description "Expired report";
           }
           enum "scheduler" {
             description "Scheduler report";
           }
           enum "no-comments" {
             description "No-comments report";
           }
           enum "no-logging" {
             description "No-logging report";
           }
           enum "most-hit" {
             description "Most-hit report";
           }
           enum "least-hit" {
             description "Least-hit report";
           }
           enum "30d-not-hit" {
             description "Not-hit-30-days report";
           }
           enum "60d-not-hit" {
             description "Not-hit-60-days report";
           }
           enum "90d-not-hit" {
             description "Not-hit-90-days report";
           }
           enum "1-year-not-hit" {
             description "Not-hit-1-year report";
           }
         }
       }
     }
     output {
       choice output_c {
         case output-tag {
           leaf output {
             type string;
           }
         }
         case actual-tag {
           anyxml global-policy-report;
         }
         case multichassis-tag {
           anyxml multi-routing-engine-results;
         }
       }
     }
   }
   rpc get-sla-policies {
     description "Show advance policy based routing information";
     input {
       uses command-forwarding;
       leaf from-zone {
         description "Show the policy information matching the given source zone";
         type string;
       }
       leaf policy-name {
         description "Show the policy information matching the given policy name";
         type string;
       }
       leaf detail {
         description "Show the detailed information";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml sla-policies;
         }
         case multichassis-tag {
           anyxml multi-routing-engine-results;
         }
       }
     }
   }
   rpc get-sla-policies-hit-count {
     description "Show the hit count of policies";
     input {
       uses command-forwarding;
       leaf from-zone {
         description "Show the policy hit-count matching the given source zone";
         type string;
       }
       leaf order {
         description "Policy order";
         type enumeration {
           enum "ascending" {
             description "Ascending order";
           }
           enum "descending" {
             description "Descending order";
           }
         }
       }
       leaf less-than {
         description "Maximum hit-count";
         type union {
           type string {
             pattern "<.*>|$.*";
           }
           type uint32 {
             range "0 .. 4294967295";
           }
         }
       }
       leaf greater-than {
         description "Minimum hit-count";
         type union {
           type string {
             pattern "<.*>|$.*";
           }
           type uint32 {
             range "0 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml sla-hit-count;
         }
         case multichassis-tag {
           anyxml multi-routing-engine-results;
         }
       }
     }
   }
   rpc get-apbr-statistics {
     description "Show advance-policy-based-routing statistics";
     output {
       choice output_c {
         case output-tag {
           leaf output {
             type string;
           }
         }
         case actual-tag {
           anyxml apbr-statistics;
         }
         case multichassis-tag {
           anyxml multi-routing-engine-results;
         }
       }
     }
   }
   rpc get-apbr-profile {
     description "Show advance-policy-based-routing profile";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml apbr-profile;
         }
         case multichassis-tag {
           anyxml multi-routing-engine-results;
         }
       }
     }
   }
   rpc get-apbr-status {
     description "Show advance-policy-based-routing status";
     output {
       choice output_c {
         case output-tag {
           leaf output {
             type string;
           }
         }
         case actual-tag {
           anyxml apbr-status;
         }
         case multichassis-tag {
           anyxml multi-routing-engine-results;
         }
       }
     }
   }
   rpc get-apbr-sla-status {
     description "Show advance-policy-based-routing sla status";
     output {
       choice output_c {
         case output-tag {
           leaf output {
             type string;
           }
         }
         case actual-tag {
           anyxml apbr-sla-status;
         }
         case multichassis-tag {
           anyxml multi-routing-engine-results;
         }
       }
     }
   }
   rpc get-apbr-sla-version {
     description "Show advance-policy-based-routing sla version";
     output {
       choice output_c {
         case output-tag {
           leaf output {
             type string;
           }
         }
         case actual-tag {
           anyxml apbr-sla-version;
         }
         case multichassis-tag {
           anyxml multi-routing-engine-results;
         }
       }
     }
   }
   rpc get-apbr-sla-statistics {
     description "Show advance-policy-based-routing sla statistics";
     output {
       choice output_c {
         case output-tag {
           leaf output {
             type string;
           }
         }
         case actual-tag {
           anyxml apbr-sla-statistics;
         }
         case multichassis-tag {
           anyxml multi-routing-engine-results;
         }
       }
     }
   }
   rpc get-apbr-sla-active-statistics {
     description "Choose for a Probe Params";
     input {
       uses command-forwarding;
       leaf active-probe-params-name {
         description "Active Probe Params Name";
         type string;
         mandatory true;
       }
     }
     output {
       choice output_c {
         case output-tag {
           leaf output {
             type string;
           }
         }
         case actual-tag {
           anyxml apbr-sla-active-statistics;
         }
         case multichassis-tag {
           anyxml multi-routing-engine-results;
         }
       }
     }
   }
   rpc get-apbr-sla-information {
     description "Show advance-policy-based-routing sla profile data";
     input {
       uses command-forwarding;
       leaf profile-name {
         description "Profile name";
         type string;
         mandatory true;
       }
       leaf application {
         description "Application name";
         type string;
       }
       leaf dscp {
         description "DSCP value";
         type union {
           type string {
             pattern "<.*>|$.*";
           }
           type uint32 {
             range "0 .. 63";
           }
         }
       }
       leaf next-hop {
         description "Forwarding Next-Hop ID";
         type union {
           type int32;
           type string {
             pattern "<.*>|$.*";
           }
         }
       }
       leaf server-ip {
         description "SaaS server IP";
         type jt:ipaddr;
       }
       leaf get-apbr-sla-options {
         description "Options";
         type enumeration {
           enum "status" {
             description "Current running Status";
           }
         }
       }
     }
     output {
       choice output_c {
         case output-tag {
           leaf output {
             type string;
           }
         }
         case multichassis-tag {
           anyxml multi-routing-engine-results;
         }
       }
     }
   }
   rpc get-multipath-rule-status {
     description "Show multipath rule details";
     input {
       uses command-forwarding;
       leaf rule-name {
         description "Multipath rule name";
         type string;
         mandatory true;
       }
       choice filter {
         case application {
           leaf application {
             description "Application name";
             type string;
           }
         }
         case cos-q {
           leaf cos-q {
             description "Cos-Q number from 0-7";
             type union {
               type string {
                 pattern "<.*>|$.*";
               }
               type uint32 {
                 range "0 .. 7";
               }
             }
           }
         }
         case ifl-name {
           leaf ifl-name {
             description "Specify ifl name";
             type string;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml multipath-rule-status;
         }
         case multichassis-tag {
           anyxml multi-routing-engine-results;
         }
       }
     }
   }
   rpc get-multipath-policy-information {
     description "Show advance-policy-based-routing multipath policy statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf multipath-name {
         description "Multipath name";
         type string;
       }
       choice filter {
         case application {
           leaf application {
             description "Application name";
             type string;
           }
         }
       }
     }
     output {
       choice output_c {
         case output-tag {
           leaf output {
             type string;
           }
         }
         case actual-tag {
           anyxml multipath-policy-information;
         }
         case multichassis-tag {
           anyxml multi-routing-engine-results;
         }
       }
     }
   }
   rpc get-ragw-statistics {
     description "Show TCP encapsulation statistics";
     output {
       choice output_c {
         case output-tag {
           leaf output {
             type string;
           }
         }
         case actual-tag {
           anyxml ragw-statistics;
         }
         case multichassis-tag {
           anyxml multi-routing-engine-results;
         }
       }
     }
   }
   rpc get-ragw-connection {
     description "Show TCP encap session details";
     input {
       uses command-forwarding;
       leaf level {
         default "brief";
         type enumeration {
           enum "brief" {
             description "Display brief output";
           }
           enum "detail" {
             description "Display detailed output";
           }
         }
       }
       leaf get-sess-id-connection-details {
         description "Session id";
         type union {
           type string {
             pattern "<.*>|$.*";
           }
           type uint32 {
             range "1 .. 4294967295";
           }
         }
       }
     }
     output {
       choice output_c {
         case output-tag {
           leaf output {
             type string;
           }
         }
         case actual-tag {
           anyxml ragw-connection;
         }
         case multichassis-tag {
           anyxml multi-routing-engine-results;
         }
       }
     }
   }
   rpc get-resmgr-group-active {
     description "Show active resource manager group service information";
     input {
       uses command-forwarding;
       leaf group-number {
         description "Show active resource manager group";
         type union {
           type uint32;
           type string {
             pattern "<.*>|$.*";
           }
         }
       }
     }
     output {
       choice output_c {
         case output-tag {
           leaf output {
             type string;
           }
         }
         case actual-tag {
           anyxml resmgr-group-active;
         }
         case multichassis-tag {
           anyxml multi-routing-engine-results;
         }
       }
     }
   }
   rpc get-resmgr-resource-active {
     description "Show active resource manager resource service information";
     input {
       uses command-forwarding;
       leaf resource-number {
         description "Show active resource manager resource";
         type union {
           type uint32;
           type string {
             pattern "<.*>|$.*";
           }
         }
       }
     }
     output {
       choice output_c {
         case output-tag {
           leaf output {
             type string;
           }
         }
         case actual-tag {
           anyxml resmgr-resource-active;
         }
         case multichassis-tag {
           anyxml multi-routing-engine-results;
         }
       }
     }
   }
   rpc get-resmgr-settings {
     description "Show resource manager settings information";
     output {
       choice output_c {
         case output-tag {
           leaf output {
             type string;
           }
         }
         case actual-tag {
           anyxml resmgr-settings;
         }
         case multichassis-tag {
           anyxml multi-routing-engine-results;
         }
       }
     }
   }
   rpc get-resource-manager-summary {
     description "Show resource manager summary information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml resource-manager-summary-information;
         }
         case multichassis-tag {
           anyxml multi-routing-engine-results;
         }
       }
     }
   }
   rpc get-security-report-threats-summary {
     description "Show threat indicator summary";
     output {
       choice output_c {
         case output-tag {
           leaf output {
             type string;
           }
         }
         case actual-tag {
           anyxml security-report-threats-summary;
         }
         case multichassis-tag {
           anyxml multi-routing-engine-results;
         }
       }
     }
   }
   rpc get-security-report-threats-statistics {
     description "Show the threat statistics";
     output {
       choice output_c {
         case output-tag {
           leaf output {
             type string;
           }
         }
         case actual-tag {
           anyxml security-report-threats-statistics;
         }
         case multichassis-tag {
           anyxml multi-routing-engine-results;
         }
       }
     }
   }
   rpc get-security-report-threats-recent-activity {
     description "Show the most recent threat activities";
     output {
       choice output_c {
         case output-tag {
           leaf output {
             type string;
           }
         }
         case actual-tag {
           anyxml security-report-threats-recent-activity;
         }
         case multichassis-tag {
           anyxml multi-routing-engine-results;
         }
       }
     }
   }
   rpc get-security-report-traffic-statistics {
     description "Show the traffic statistics";
     output {
       choice output_c {
         case output-tag {
           leaf output {
             type string;
           }
         }
         case actual-tag {
           anyxml security-report-traffic-statistics;
         }
         case multichassis-tag {
           anyxml multi-routing-engine-results;
         }
       }
     }
   }
   rpc get-performance-summary-information {
     description "Show security SPU monitoring information";
     output {
       choice output_c {
         case output-tag {
           leaf output {
             type string;
           }
         }
         case actual-tag {
           anyxml performance-summary-information;
         }
         case multichassis-tag {
           anyxml multi-routing-engine-results;
         }
       }
     }
   }
   rpc get-spu-monitoring-information {
     description "Show the FPC slot security monitoring information";
     input {
       uses command-forwarding;
       leaf fpc-slot {
         description "FPC slot number";
         type union {
           type string {
             pattern "<.*>|$.*";
           }
           type uint32;
         }
         mandatory true;
       }
     }
     output {
       choice output_c {
         case output-tag {
           leaf output {
             type string;
           }
         }
         case actual-tag {
           anyxml spu-monitroing-information;
         }
         case multichassis-tag {
           anyxml multi-routing-engine-results;
         }
       }
     }
   }
   rpc get-spu-monitoring-re-ipc-debug {
     description "Show the debug info about IPC between RTLGOD on HA nodes.";
     output {
       choice output_c {
         case output-tag {
           leaf output {
             type string;
           }
         }
         case actual-tag {
           anyxml spu-monitroing-re-ipc-debug;
         }
         case multichassis-tag {
           anyxml multi-routing-engine-results;
         }
       }
     }
   }
   rpc get-performance-spu-information {
     description "Show security performance SPU information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       choice output_c {
         case output-tag {
           leaf output {
             type string;
           }
         }
         case actual-tag {
           anyxml performance-spu-information;
         }
         case multichassis-tag {
           anyxml multi-routing-engine-results;
         }
       }
     }
   }
   rpc get-performance-spu-extensive-information {
     description "Show security performance SPU extensive information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       choice output_c {
         case output-tag {
           leaf output {
             type string;
           }
         }
         case actual-tag {
           anyxml performance-spu-extensive-information;
         }
         case multichassis-tag {
           anyxml multi-routing-engine-results;
         }
       }
     }
   }
   rpc get-performance-spu-summary-information {
     description "Show security performance SPU summary information";
     input {
       uses command-forwarding;
       leaf fpc {
         description "FPC slot number";
         type union {
           type string {
             pattern "<.*>|$.*";
           }
           type uint32;
         }
         mandatory true;
       }
       leaf pic {
         description "PIC slot number";
         type union {
           type string {
             pattern "<.*>|$.*";
           }
           type uint32;
         }
         mandatory true;
       }
       leaf thread {
         description "SPU thread number";
         type union {
           type string {
             pattern "<.*>|$.*";
           }
           type uint32 {
             range "0 .. 31";
           }
         }
       }
     }
     output {
       choice output_c {
         case output-tag {
           leaf output {
             type string;
           }
         }
         case actual-tag {
           anyxml performance-spu-summary-information;
         }
         case multichassis-tag {
           anyxml multi-routing-engine-results;
         }
       }
     }
   }
   rpc get-performance-session-information {
     description "Show security performance session information";
     input {
       uses command-forwarding;
       leaf fpc {
         description "FPC slot number";
         type union {
           type string {
             pattern "<.*>|$.*";
           }
           type uint32;
         }
       }
       leaf pic {
         description "PIC slot number";
         type union {
           type string {
             pattern "<.*>|$.*";
           }
           type uint32;
         }
       }
     }
     output {
       choice output_c {
         case output-tag {
           leaf output {
             type string;
           }
         }
         case actual-tag {
           anyxml performance-session-information;
         }
         case multichassis-tag {
           anyxml multi-routing-engine-results;
         }
       }
     }
   }
   rpc get-userfw-local-auth-table-all {
     description "Show the entire local user authentication table";
     input {
       uses command-forwarding;
       leaf level {
         default "brief";
         type enumeration {
           enum "brief" {
             description "Show brief output (default)";
           }
           enum "extensive" {
             description "Show extensive output";
           }
         }
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-ip {
     description "Show local user authentication information for the specified ip-address";
     input {
       uses command-forwarding;
       leaf ip-address {
         description "IP address";
         type jt:ipaddr;
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-user {
     description "Show local user authentication information for the specified user";
     input {
       uses command-forwarding;
       leaf user-name {
         description "User name";
         type string {
           length "1 .. 64";
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-role {
     description "Show local user authentication information for the specified role";
     input {
       uses command-forwarding;
       leaf role-name {
         description "Role name";
         type string {
           length "1 .. 63";
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-local-auth-table-start {
     description "Show local user authentication table information from a given position";
     input {
       uses command-forwarding;
       leaf start {
         type union {
           type string {
             pattern "<.*>|$.*";
           }
           type uint32 {
             range "1 .. 65535";
           }
         }
         mandatory true;
       }
       leaf count {
         description "Number of local user authentication table entries to show";
         type union {
           type string {
             pattern "<.*>|$.*";
           }
           type uint32 {
             range "1 .. 65535";
           }
         }
         mandatory true;
       }
     }
     output {
       choice output_c {
         case output-tag {
           leaf output {
             type string;
           }
         }
         case actual-tag {
           anyxml user-identification;
         }
         case multichassis-tag {
           anyxml multi-routing-engine-results;
         }
       }
     }
   }
   rpc get-userfw-device-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-ad-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-jims-device-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-role-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-ad-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-jims-role-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-user-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-ad-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-jims-user-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-userfw-source-identity-info {
     description "Show all information";
     input {
       uses command-forwarding;
       leaf all {
         type empty;
       }
     }
     output {
       choice output_c {
         case output-tag {
           leaf output {
             type string;
           }
         }
         case actual-tag {
           anyxml user-identification;
         }
         case multichassis-tag {
           anyxml multi-routing-engine-results;
         }
       }
     }
   }
   rpc get-userfw-source-identity-info-start {
     description "Show information from a given position";
     input {
       uses command-forwarding;
       leaf start {
         type union {
           type uint32;
           type string {
             pattern "<.*>|$.*";
           }
         }
         mandatory true;
       }
       leaf count {
         description "Number of entries to show";
         type union {
           type string {
             pattern "<.*>|$.*";
           }
           type uint32 {
             range "1 .. 65535";
           }
         }
         mandatory true;
       }
       leaf prefix {
         description "Prefix";
         type string {
           length "1 .. 64";
         }
       }
       leaf match-string {
         description "Match string in regular expression";
         type string {
           length "1 .. 64";
         }
       }
     }
     output {
       choice output_c {
         case output-tag {
           leaf output {
             type string;
           }
         }
         case actual-tag {
           anyxml user-identification;
         }
         case multichassis-tag {
           anyxml multi-routing-engine-results;
         }
       }
     }
   }
   rpc get-zones-information {
     description "Show security zone information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       choice filter {
         case name {
           leaf get-zones-named-information {
             description "Show information for a specified zone";
             type string;
           }
         }
         case type {
           leaf type {
             description "Show information for zones of a specified type";
             type enumeration {
               enum "functional" {
                 description "Show information for functional zones";
               }
               enum "security" {
                 description "Show information for security zones";
               }
             }
           }
         }
       }
       leaf level {
         default "detail";
         type enumeration {
           enum "terse" {
             description "Display terse output";
           }
           enum "detail" {
             description "Display detailed output (default)";
           }
         }
       }
     }
     output {
       choice output_c {
         case output-tag {
           leaf output {
             type string;
           }
         }
         case actual-tag {
           anyxml zones-information;
         }
         case multichassis-tag {
           anyxml multi-routing-engine-results;
         }
       }
     }
   }
   rpc get-vrf-groups-information {
     description "Show security vrf-group information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-vrf-groups-named-information {
         description "Show information for a specified vrf-group";
         type string;
       }
       leaf level {
         default "detail";
         type enumeration {
           enum "terse" {
             description "Display terse output";
           }
           enum "detail" {
             description "Display detailed output (default)";
           }
         }
       }
     }
     output {
       choice output_c {
         case output-tag {
           leaf output {
             type string;
           }
         }
         case actual-tag {
           anyxml vrf-group-information;
         }
         case multichassis-tag {
           anyxml multi-routing-engine-results;
         }
       }
     }
   }
   rpc get-tunnel-inspections-profile-information {
     description "Show security tunnel-inspection profile information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-tunnel-inspections-profile-named-information {
         description "Show information for a specified tunnel-inspection profile";
         type string;
       }
     }
     output {
       choice output_c {
         case output-tag {
           leaf output {
             type string;
           }
         }
         case actual-tag {
           anyxml tunnel-inspection-profile-information;
         }
         case multichassis-tag {
           anyxml multi-routing-engine-results;
         }
       }
     }
   }
   rpc get-tunnel-inspections-vni-information {
     description "Show security tunnel-inspection vni information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf get-tunnel-inspections-vni-named-information {
         description "Show information for a specified tunnel-inspection vni";
         type string;
       }
     }
     output {
       choice output_c {
         case output-tag {
           leaf output {
             type string;
           }
         }
         case actual-tag {
           anyxml tunnel-inspection-vni-information;
         }
         case multichassis-tag {
           anyxml multi-routing-engine-results;
         }
       }
     }
   }
   rpc get-remote-access-default-config {
     description "Show default-config values";
     output {
       choice output_c {
         case output-tag {
           leaf output {
             type string;
           }
         }
         case actual-tag {
           anyxml remote-access-default-config;
         }
         case multichassis-tag {
           anyxml multi-routing-engine-results;
         }
       }
     }
   }
   rpc get-security-gtp-tunnels {
     description "Show security gtp tunnels";
     input {
       uses command-forwarding;
       leaf level {
         default "brief";
         type enumeration {
           enum "summary" {
             description "Show the summary of GTP tunnels";
           }
           enum "brief" {
             description "Show a brief of each GTP tunnel (default)";
           }
           enum "detail" {
             description "Show a detail of each GTP tunnel";
           }
         }
       }
     }
     output {
       choice output_c {
         case output-tag {
           leaf output {
             type string;
           }
         }
         case actual-tag {
           anyxml gtp-show-tunnel;
         }
         case multichassis-tag {
           anyxml multi-routing-engine-results;
         }
       }
     }
   }
   rpc get-security-gtp-counters {
     description "Show security gtp counters";
     input {
       uses command-forwarding;
       choice counter-type {
         case path-rate-limit {
           leaf path-rate-limit {
             description "Show path-rate-limit counters";
             type empty;
           }
         }
         case rate-limit {
           leaf rate-limit {
             description "Show rate-limit counters";
             type empty;
           }
         }
         case error {
           leaf error {
             description "Show GTP error counters";
             type empty;
           }
         }
         case tunnel {
           leaf tunnel {
             description "Show GTP tunnel counters";
             type empty;
           }
         }
         case packet {
           leaf packet {
             description "Show GTP packet counters";
             type empty;
           }
         }
         case request {
           leaf request {
             description "Show GTP request counters";
             type empty;
           }
         }
         case data-packet {
           leaf data-packet {
             description "Show GTP-U data packet counters";
             type empty;
           }
         }
         case ha {
           leaf ha {
             description "Show GTP HA counters";
             type empty;
           }
         }
         case all {
           leaf all {
             description "Show all GTP counters";
             type empty;
           }
         }
       }
     }
     output {
       choice output_c {
         case output-tag {
           leaf output {
             type string;
           }
         }
         case actual-tag {
           anyxml gtp-show-counters;
         }
         case multichassis-tag {
           anyxml multi-routing-engine-results;
         }
       }
     }
   }
   rpc get-security-gtp-counters-message {
     description "Show GTP message counters";
     input {
       uses command-forwarding;
       choice message-type {
         case v0-create-pdp-req {
           leaf v0-create-pdp-req {
             description "Show GTPv0 create PDP context request message";
             type empty;
           }
         }
         case v0-create-pdp-rsp {
           leaf v0-create-pdp-rsp {
             description "Show GTPv0 create PDP context response message";
             type empty;
           }
         }
         case v0-update-pdp-req {
           leaf v0-update-pdp-req {
             description "Show GTPv0 update PDP context request message";
             type empty;
           }
         }
         case v0-update-pdp-rsp {
           leaf v0-update-pdp-rsp {
             description "Show GTPv0 update PDP context response message";
             type empty;
           }
         }
         case v0-delete-pdp-req {
           leaf v0-delete-pdp-req {
             description "Show GTPv0 delete PDP context request message";
             type empty;
           }
         }
         case v0-delete-pdp-rsp {
           leaf v0-delete-pdp-rsp {
             description "Show GTPv0 delete PDP context response message";
             type empty;
           }
         }
         case v0-create-aa-pdp-req {
           leaf v0-create-aa-pdp-req {
             description "Show GTPv0 create AA PDP context request message";
             type empty;
           }
         }
         case v0-create-aa-pdp-rsp {
           leaf v0-create-aa-pdp-rsp {
             description "Show GTPv0 create AA PDP context response message";
             type empty;
           }
         }
         case v0-delete-aa-pdp-req {
           leaf v0-delete-aa-pdp-req {
             description "Show GTPv0 delete AA PDP context request message";
             type empty;
           }
         }
         case v0-delete-aa-pdp-rsp {
           leaf v0-delete-aa-pdp-rsp {
             description "Show GTPv0 delete AA PDP context response message";
             type empty;
           }
         }
         case v0-sgsn-context-req {
           leaf v0-sgsn-context-req {
             description "Show GTPv0 sgsn context request message";
             type empty;
           }
         }
         case v0-sgsn-context-rsp {
           leaf v0-sgsn-context-rsp {
             description "Show GTPv0 sgsn context response message";
             type empty;
           }
         }
         case v0-sgsn-context-ack {
           leaf v0-sgsn-context-ack {
             description "Show GTPv0 sgsn context acknowledge message";
             type empty;
           }
         }
         case v0-others {
           leaf v0-others {
             description "Show GTPv0 others message";
             type empty;
           }
         }
         case v1-create-pdp-req {
           leaf v1-create-pdp-req {
             description "Show GTPv1 create PDP context request message";
             type empty;
           }
         }
         case v1-create-pdp-rsp {
           leaf v1-create-pdp-rsp {
             description "Show GTPv1 create PDP context response message";
             type empty;
           }
         }
         case v1-update-pdp-req {
           leaf v1-update-pdp-req {
             description "Show GTPv1 update PDP context request message";
             type empty;
           }
         }
         case v1-update-pdp-rsp {
           leaf v1-update-pdp-rsp {
             description "Show GTPv1 update PDP context response message";
             type empty;
           }
         }
         case v1-delete-pdp-req {
           leaf v1-delete-pdp-req {
             description "Show GTPv1 delete PDP context request message";
             type empty;
           }
         }
         case v1-delete-pdp-rsp {
           leaf v1-delete-pdp-rsp {
             description "Show GTPv1 delete PDP context response message";
             type empty;
           }
         }
         case v1-sgsn-context-req {
           leaf v1-sgsn-context-req {
             description "Show GTPv1 sgsn context request message";
             type empty;
           }
         }
         case v1-sgsn-context-rsp {
           leaf v1-sgsn-context-rsp {
             description "Show GTPv1 sgsn context response message";
             type empty;
           }
         }
         case v1-sgsn-context-ack {
           leaf v1-sgsn-context-ack {
             description "Show GTPv1 sgsn context acknowledge message";
             type empty;
           }
         }
         case v1-fwd-reloc-req {
           leaf v1-fwd-reloc-req {
             description "Show GTPv1 forward relocation request message";
             type empty;
           }
         }
         case v1-fwd-reloc-rsp {
           leaf v1-fwd-reloc-rsp {
             description "Show GTPv1 forward relocation response message";
             type empty;
           }
         }
         case v1-others {
           leaf v1-others {
             description "Show GTPv1 others message";
             type empty;
           }
         }
         case v2-create-session-req {
           leaf v2-create-session-req {
             description "Show GTPv2 create session request message";
             type empty;
           }
         }
         case v2-create-session-rsp {
           leaf v2-create-session-rsp {
             description "Show GTPv2 create session response message";
             type empty;
           }
         }
         case v2-delete-session-req {
           leaf v2-delete-session-req {
             description "Show GTPv2 delete session request message";
             type empty;
           }
         }
         case v2-delete-session-rsp {
           leaf v2-delete-session-rsp {
             description "Show GTPv2 delete session response message";
             type empty;
           }
         }
         case v2-create-bearer-req {
           leaf v2-create-bearer-req {
             description "Show GTPv2 create bearer request message";
             type empty;
           }
         }
         case v2-create-bearer-rsp {
           leaf v2-create-bearer-rsp {
             description "Show GTPv2 create bearer response message";
             type empty;
           }
         }
         case v2-modify-bearer-req {
           leaf v2-modify-bearer-req {
             description "Show GTPv2 modify bearer request message";
             type empty;
           }
         }
         case v2-modify-bearer-rsp {
           leaf v2-modify-bearer-rsp {
             description "Show GTPv2 modify bearer response message";
             type empty;
           }
         }
         case v2-delete-bearer-req {
           leaf v2-delete-bearer-req {
             description "Show GTPv2 delete bearer request message";
             type empty;
           }
         }
         case v2-delete-bearer-rsp {
           leaf v2-delete-bearer-rsp {
             description "Show GTPv2 delete bearer response message";
             type empty;
           }
         }
         case v2-context-req {
           leaf v2-context-req {
             description "Show GTPv2 context request message";
             type empty;
           }
         }
         case v2-context-rsp {
           leaf v2-context-rsp {
             description "Show GTPv2 context response message";
             type empty;
           }
         }
         case v2-context-ack {
           leaf v2-context-ack {
             description "Show GTPv2 context acknowledge message";
             type empty;
           }
         }
         case v2-fwd-reloc-req {
           leaf v2-fwd-reloc-req {
             description "Show GTPv2 forward relocation request message";
             type empty;
           }
         }
         case v2-fwd-reloc-rsp {
           leaf v2-fwd-reloc-rsp {
             description "Show GTPv2 forward relocation response message";
             type empty;
           }
         }
         case v2-create-ind-fwd-tnl-req {
           leaf v2-create-ind-fwd-tnl-req {
             description "Show GTPv2 create indirect forward tunnel request message";
             type empty;
           }
         }
         case v2-create-ind-fwd-tnl-rsp {
           leaf v2-create-ind-fwd-tnl-rsp {
             description "Show GTPv2 create indirect forward tunnel response message";
             type empty;
           }
         }
         case v2-others {
           leaf v2-others {
             description "Show GTPv2 others message";
             type empty;
           }
         }
         case brief {
           leaf brief {
             description "Show brief GTP messages";
             type empty;
           }
         }
       }
     }
     output {
       choice output_c {
         case output-tag {
           leaf output {
             type string;
           }
         }
         case actual-tag {
           anyxml gtp-show-counters-message;
         }
         case multichassis-tag {
           anyxml multi-routing-engine-results;
         }
       }
     }
   }
   rpc get-security-gtp-profile {
     description "Show gtp profile";
     input {
       choice profile-choice {
         case profile-name {
           leaf profile-name {
             description "GTP profile name";
             type string {
               length "1 .. 23";
             }
           }
         }
         case all {
           leaf all {
             description "List all GTP profiles";
             type empty;
           }
         }
       }
     }
     output {
       choice output_c {
         case output-tag {
           leaf output {
             type string;
           }
         }
         case actual-tag {
           anyxml gtp-show-profie;
         }
         case multichassis-tag {
           anyxml multi-routing-engine-results;
         }
       }
     }
   }
   rpc get-gtp-gsn-statitics-all {
     description "Show GTP GSN statistics";
     output {
       choice output_c {
         case output-tag {
           leaf output {
             type string;
           }
         }
         case actual-tag {
           anyxml gtp-show-statistics-all;
         }
         case multichassis-tag {
           anyxml multi-routing-engine-results;
         }
       }
     }
   }
   rpc get-gtp-handover-group {
     description "Show SGSN handover group";
     input {
       choice handover-group-name {
         case group-name {
           leaf group-name {
             description "Handover Group name";
             type string {
               length "1 .. 23";
             }
           }
         }
         case all {
           leaf all {
             description "List all handover-group";
             type empty;
           }
         }
       }
     }
     output {
       choice output_c {
         case output-tag {
           leaf output {
             type string;
           }
         }
         case actual-tag {
           anyxml gtp-show-handover-group;
         }
         case multichassis-tag {
           anyxml multi-routing-engine-results;
         }
       }
     }
   }
   rpc get-gtp-ip-group {
     description "Show GTP ip group";
     input {
       choice ip-group-name {
         case group-name {
           leaf group-name {
             description "IP Group name";
             type string {
               length "1 .. 23";
             }
           }
         }
         case all {
           leaf all {
             description "List all ip-group";
             type empty;
           }
         }
       }
     }
     output {
       choice output_c {
         case output-tag {
           leaf output {
             type string;
           }
         }
         case actual-tag {
           anyxml gtp-show-ip-group;
         }
         case multichassis-tag {
           anyxml multi-routing-engine-results;
         }
       }
     }
   }
   rpc get-gtp-message-ie-profile-v1 {
     description "Show GTPv1 message-ie profile";
     input {
       choice msgie-prof-v1-name {
         case msgie-profile-v1-name {
           leaf msgie-profile-v1-name {
             description "GTPv1 message-ie profile name";
             type string {
               length "1 .. 23";
             }
           }
         }
         case all {
           leaf all {
             description "List all GTPv1 message-ie profile";
             type empty;
           }
         }
       }
     }
     output {
       choice output_c {
         case output-tag {
           leaf output {
             type string;
           }
         }
         case actual-tag {
           anyxml gtp-show-msgie-prof-v1;
         }
         case multichassis-tag {
           anyxml multi-routing-engine-results;
         }
       }
     }
   }
   rpc get-gtp-message-ie-profile-v2 {
     description "Show GTPv2 message-ie profile";
     input {
       choice msgie-prof-v2-name {
         case msgie-profile-v2-name {
           leaf msgie-profile-v2-name {
             description "GTPv2 message-ie profile name";
             type string {
               length "1 .. 23";
             }
           }
         }
         case all {
           leaf all {
             description "List all GTPv2 message-ie profile";
             type empty;
           }
         }
       }
     }
     output {
       choice output_c {
         case output-tag {
           leaf output {
             type string;
           }
         }
         case actual-tag {
           anyxml gtp-show-msgie-prof-v2;
         }
         case multichassis-tag {
           anyxml multi-routing-engine-results;
         }
       }
     }
   }
   rpc get-gtp-grouped-ie-profile {
     description "Show GTP grouped-ie profile";
     input {
       choice grpie-prof-name {
         case grpie-profile-name {
           leaf grpie-profile-name {
             description "GTP grouped-ie profile name";
             type string {
               length "1 .. 23";
             }
           }
         }
         case all {
           leaf all {
             description "List all GTP grouped-ie profile";
             type empty;
           }
         }
       }
     }
     output {
       choice output_c {
         case output-tag {
           leaf output {
             type string;
           }
         }
         case actual-tag {
           anyxml gtp-show-grpie-prof;
         }
         case multichassis-tag {
           anyxml multi-routing-engine-results;
         }
       }
     }
   }
   rpc get-gtp-ie-set {
     description "Show GTP IE set";
     input {
       choice ie-set-name_choice {
         case ie-set-name {
           leaf ie-set-name {
             description "GTP IE set name";
             type string {
               length "1 .. 23";
             }
           }
         }
         case all {
           leaf all {
             description "List all GTP IE set";
             type empty;
           }
         }
       }
     }
     output {
       choice output_c {
         case output-tag {
           leaf output {
             type string;
           }
         }
         case actual-tag {
           anyxml gtp-show-gtp-prof-ie-set;
         }
         case multichassis-tag {
           anyxml multi-routing-engine-results;
         }
       }
     }
   }
   rpc get-gtp-message-list {
     description "Show GTP IE set";
     input {
       choice msg-list-name_choice {
         case msg-list-name {
           leaf msg-list-name {
             description "GTP message list name";
             type string {
               length "1 .. 23";
             }
           }
         }
         case all {
           leaf all {
             description "List all GTP message list";
             type empty;
           }
         }
       }
     }
     output {
       choice output_c {
         case output-tag {
           leaf output {
             type string;
           }
         }
         case actual-tag {
           anyxml gtp-show-gtp-msg-list;
         }
         case multichassis-tag {
           anyxml multi-routing-engine-results;
         }
       }
     }
   }
   rpc get-gtp-arl {
     description "Show GTP aggregate rate-limit policy";
     input {
       leaf default {
         description "Default Rate-Limit message list";
         type empty;
         mandatory true;
       }
     }
     output {
       choice output_c {
         case output-tag {
           leaf output {
             type string;
           }
         }
         case actual-tag {
           anyxml gtp-show-gtp-arl;
         }
         case multichassis-tag {
           anyxml multi-routing-engine-results;
         }
       }
     }
   }
   rpc get-gtp-apn-control {
     description "Show GTP apn-control profile";
     input {
       choice apn-ctrl-name_choice {
         case apn-ctrl-name {
           leaf apn-ctrl-name {
             description "GTP apn-control profile name";
             type string {
               length "1 .. 23";
             }
           }
         }
         case all {
           leaf all {
             description "List all GTP apn-control profile";
             type empty;
           }
         }
       }
     }
     output {
       choice output_c {
         case output-tag {
           leaf output {
             type string;
           }
         }
         case actual-tag {
           anyxml gtp-show-apn-control;
         }
         case multichassis-tag {
           anyxml multi-routing-engine-results;
         }
       }
     }
   }
   rpc get-gtp-apn-control-group {
     description "Show GTP apn-control profile group";
     input {
       choice apn-ctrl-grp-name_choice {
         case apn-ctrl-grp-name {
           leaf apn-ctrl-grp-name {
             description "GTP apn-control profile group name";
             type string {
               length "1 .. 23";
             }
           }
         }
         case all {
           leaf all {
             description "List all GTP apn-control-group";
             type empty;
           }
         }
       }
     }
     output {
       choice output_c {
         case output-tag {
           leaf output {
             type string;
           }
         }
         case actual-tag {
           anyxml gtp-show-apn-control-group;
         }
         case multichassis-tag {
           anyxml multi-routing-engine-results;
         }
       }
     }
   }
   rpc get-security-sctp-counters {
     description "Show security sctp counters";
     output {
       choice output_c {
         case output-tag {
           leaf output {
             type string;
           }
         }
         case actual-tag {
           anyxml sctp-show-counters;
         }
         case multichassis-tag {
           anyxml multi-routing-engine-results;
         }
       }
     }
   }
   rpc get-sctp-counters-detail {
     description "Show the detailed sctp counter information";
     output {
       choice output_c {
         case output-tag {
           leaf output {
             type string;
           }
         }
         case actual-tag {
           anyxml sctp_show_counters;
         }
         case multichassis-tag {
           anyxml multi-routing-engine-results;
         }
       }
     }
   }
   rpc get-sctp-association {
     description "Show security sctp association";
     input {
       uses command-forwarding;
       leaf source-ip {
         description "Match association for source IP";
         type jt:ipaddr;
       }
       leaf source-port {
         description "Match association for source port";
         type union {
           type string {
             pattern "<.*>|$.*";
           }
           type uint32 {
             range "1 .. 65535";
           }
         }
       }
       leaf destination-ip {
         description "Match association for destination IP";
         type jt:ipaddr;
       }
       leaf destination-port {
         description "Match association for destination port";
         type union {
           type string {
             pattern "<.*>|$.*";
           }
           type uint32 {
             range "1 .. 65535";
           }
         }
       }
       leaf guid {
         description "Match association for globally unique identifier";
         type string;
       }
       leaf level {
         type enumeration {
           enum "summary" {
             description "Show output summary";
           }
         }
       }
     }
     output {
       choice output_c {
         case output-tag {
           leaf output {
             type string;
           }
         }
         case actual-tag {
           anyxml show-sctp-association-information;
         }
         case multichassis-tag {
           anyxml multi-routing-engine-results;
         }
       }
     }
   }
   rpc get-sctp-association-all {
     description "Show all sctp association entries";
     output {
       choice output_c {
         case output-tag {
           leaf output {
             type string;
           }
         }
         case actual-tag {
           anyxml sctp_show_association;
         }
         case multichassis-tag {
           anyxml multi-routing-engine-results;
         }
       }
     }
   }
   rpc get-sctp-association-init {
     description "Show init sctp association entries";
     output {
       choice output_c {
         case output-tag {
           leaf output {
             type string;
           }
         }
         case actual-tag {
           anyxml sctp_show_association;
         }
         case multichassis-tag {
           anyxml multi-routing-engine-results;
         }
       }
     }
   }
   rpc get-metric-collect-information {
     description "Show AWS CloudWatch metric statistics";
     output {
       choice output_c {
         case output-tag {
           leaf output {
             type string;
           }
         }
         case actual-tag {
           anyxml metric-collect-information;
         }
         case multichassis-tag {
           anyxml multi-routing-engine-results;
         }
       }
     }
   }
   rpc get-log-collect-information {
     description "Show AWS CloudWatch log statistics";
     output {
       choice output_c {
         case output-tag {
           leaf output {
             type string;
           }
         }
         case actual-tag {
           anyxml log-collect-information;
         }
         case multichassis-tag {
           anyxml multi-routing-engine-results;
         }
       }
     }
   }
   rpc get-cloud-ha-information {
     description "Display high-availability information";
     output {
       choice output_c {
         case output-tag {
           leaf output {
             type string;
           }
         }
         case actual-tag {
           anyxml cloud-ha-information;
         }
         case multichassis-tag {
           anyxml multi-routing-engine-results;
         }
       }
     }
   }
   rpc get-ioc-np-cache-stats {
     description "Show IOC NP session cache information";
     output {
       choice output_c {
         case output-tag {
           leaf output {
             type string;
           }
         }
         case actual-tag {
           anyxml ioc-np-cache-stats;
         }
         case multichassis-tag {
           anyxml multi-routing-engine-results;
         }
       }
     }
   }
   rpc get-hakr-keychain-information {
     description "Show all protocols keychain";
     input {
       leaf verbosity {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml hakr-keychain-information;
         }
         case multichassis-tag {
           anyxml multi-routing-engine-results;
         }
       }
     }
   }
   rpc get-mka-session-information {
     description "Show MKA sessions information";
     input {
       leaf verbosity_level {
         default "brief";
         type enumeration {
           enum "summary" {
             description "Display summary output";
           }
           enum "brief" {
             description "Display brief output (default)";
           }
           enum "detail" {
             description "Display detailed output";
           }
         }
       }
     }
     output {
       choice output_c {
         case output-tag {
           leaf output {
             type string;
           }
         }
         case actual-tag {
           anyxml mka-session-information;
         }
         case multichassis-tag {
           anyxml multi-routing-engine-results;
         }
       }
     }
   }
   rpc get-mka-session-interface-information {
     description "Show MKA session on this interface";
     input {
       leaf verbosity_level {
         default "brief";
         type enumeration {
           enum "summary" {
             description "Display summary output";
           }
           enum "brief" {
             description "Display brief output (default)";
           }
           enum "detail" {
             description "Display detailed output";
           }
         }
       }
       leaf interface-name {
         description "Show MKA session for this interface";
         default "all";
         type string {
         }
       }
     }
     output {
       choice output_c {
         case output-tag {
           leaf output {
             type string;
           }
         }
         case actual-tag {
           anyxml mka-session-information;
         }
         case multichassis-tag {
           anyxml multi-routing-engine-results;
         }
       }
     }
   }
   rpc get-mka-statistics {
     description "Show MKA statistics";
     output {
       choice output_c {
         case output-tag {
           leaf output {
             type string;
           }
         }
         case actual-tag {
           anyxml mka-statistics;
         }
         case multichassis-tag {
           anyxml multi-routing-engine-results;
         }
       }
     }
   }
   rpc get-mka-interface-statistics {
     description "Show MKA statistics on this interface";
     input {
       leaf interface-name {
         description "Show MKA statistics for this interface";
         default "all";
         type string {
         }
       }
     }
     output {
       choice output_c {
         case output-tag {
           leaf output {
             type string;
           }
         }
         case actual-tag {
           anyxml mka-statistics;
         }
         case multichassis-tag {
           anyxml multi-routing-engine-results;
         }
       }
     }
   }
   rpc get-macsec-connection-information {
     description "Show MAC Security connections information";
     output {
       choice output_c {
         case output-tag {
           leaf output {
             type string;
           }
         }
         case actual-tag {
           anyxml macsec-connection-information;
         }
         case multichassis-tag {
           anyxml multi-routing-engine-results;
         }
       }
     }
   }
   rpc get-macsec-connection-interface-information {
     description "Show MAC security connections on this interface";
     input {
       leaf interface-name {
         description "Show MAC security connections for this interface";
         default "all";
         type string {
         }
       }
     }
     output {
       choice output_c {
         case output-tag {
           leaf output {
             type string;
           }
         }
         case actual-tag {
           anyxml macsec-connection-information;
         }
         case multichassis-tag {
           anyxml multi-routing-engine-results;
         }
       }
     }
   }
   rpc get-macsec-statistics {
     description "Show MAC Security statistics";
     input {
       leaf verbosity_level {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml macsec-statistics;
         }
         case multichassis-tag {
           anyxml multi-routing-engine-results;
         }
       }
     }
   }
   rpc get-macsec-interface-statistics {
     description "Show MAC security statistics on this interface";
     input {
       leaf verbosity_level {
         default "brief";
         type enumeration {
           enum "brief" {
             description "Display brief output (default)";
           }
           enum "detail" {
             description "Display detailed output";
           }
         }
       }
       leaf interface-name {
         description "Show MAC security statistics for this interface";
         default "all";
         type string {
         }
       }
     }
     output {
       choice output_c {
         case output-tag {
           leaf output {
             type string;
           }
         }
         case actual-tag {
           anyxml macsec-statistics;
         }
         case multichassis-tag {
           anyxml multi-routing-engine-results;
         }
       }
     }
   }
   rpc get-macsec-crypto-algorithms {
     description "Show fips validated algorithms used by MACsec module from crypto library";
     output {
       choice output_c {
         case output-tag {
           leaf output {
             type string;
           }
         }
         case actual-tag {
           anyxml macsec-crypto-algorithms;
         }
         case multichassis-tag {
           anyxml multi-routing-engine-results;
         }
       }
     }
   }
   rpc get-macsec-crypto-version {
     description "Show version of crypto library used by MACsec module";
     output {
       choice output_c {
         case output-tag {
           leaf output {
             type string;
           }
         }
         case actual-tag {
           anyxml macsec-crypto-version;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
