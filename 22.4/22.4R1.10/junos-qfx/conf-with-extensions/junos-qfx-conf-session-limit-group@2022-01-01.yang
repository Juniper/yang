/*
 * Copyright (c) 2022 Juniper Networks, Inc.
 * All rights reserved.
 */
 module junos-qfx-conf-session-limit-group {
   namespace "http://yang.juniper.net/junos-qfx/conf/session-limit-group";

   prefix jc-session-limit-group;

   import junos-common-ddl-extensions {
     prefix junos;
     revision-date 2022-01-01;
   }

   import junos-common-types {
     prefix jt;
     revision-date 2022-01-01;
   }

   import junos-qfx-conf-root {
     prefix jc;
     revision-date 2022-01-01;
   }

   organization "Juniper Networks, Inc.";

   contact "yang-support@juniper.net";

   description "Junos session-limit-group configuration module";

   revision 2022-01-01 {
     description "Junos: 22.4R1.10";
   }

   augment /jc:configuration {
     uses session-limit-group-group;
   }
   augment /jc:configuration/jc:groups {
     uses session-limit-group-group;
   }
   grouping session-limit-group-group {
     list session-limit-group {
       key name;
       ordered-by user;
       description "Session-limit-group configuration";
       status deprecated;
       leaf name {
         description "Name of the group";
         type string {
           length "1 .. 63";
           junos:posix-pattern "^[[:alnum:]][[:alnum:]_-]*$";
           junos:pattern-message "Must be a string beginning with a number or letter and consisting of letters, numbers, dashes and underscores.";
         }
       }
       leaf maximum-sessions {
         description "Maximum number of sessions per tunnel-group";
         type union {
           type uint32;
           type string {
             pattern "<.*>|$.*";
           }
         }
       }
     }
   }
 }
