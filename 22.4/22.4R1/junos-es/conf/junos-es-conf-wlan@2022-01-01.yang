/*
 * Copyright (c) 2022 Juniper Networks, Inc.
 * All rights reserved.
 */
 module junos-es-conf-wlan {
   namespace "http://yang.juniper.net/junos-es/conf/wlan";

   prefix jc-wlan;

   import junos-common-types {
     prefix jt;
     revision-date 2022-01-01;
   }

   import junos-es-conf-root {
     prefix jc;
     revision-date 2022-01-01;
   }

   organization "Juniper Networks, Inc.";

   contact "yang-support@juniper.net";

   description "Junos wlan configuration module";

   revision 2022-01-01 {
     description "Junos: 22.4R1.10";
   }

   augment /jc:configuration {
     uses wlan-group;
   }
   augment /jc:configuration/jc:groups {
     uses wlan-group;
   }
   grouping wlan-group {
     container wlan {
       presence "enable wlan";
       description "Wireless access point configuration";
       uses apply-advanced;
       container admin-authentication {
         description "Authentication information for WLAN access points";
         uses apply-advanced;
         leaf encrypted-password {
           description "Encrypted password";
           type jt:unreadable;
         }
       }
       list access-point {
         key name;
         ordered-by user;
         description "WLAN access point configuration";
         leaf name {
           description "Specify the access point name";
           type string {
           }
         }
         uses apply-advanced;
         leaf description {
           description "Specify the access point description";
           type string {
             length "1 .. 64";
           }
         }
         list interface {
           key name;
           ordered-by user;
           description "Interface device name";
           uses ap-interface-list-type;
         }
         leaf mac-address {
           description "Access point ethernet port MAC address";
           type jt:mac-unicast;
         }
         leaf location {
           description "Location of the access point";
           type string {
             length "1 .. 64";
           }
         }
         choice access-point-type {
           case case_1 {
             container external {
               presence "enable external";
               description "External type access point";
               uses apply-advanced;
               container system {
                 description "System information";
                 uses apply-advanced;
                 leaf ntp-server {
                   description "NTP server name";
                   status deprecated;
                   type string {
                     length "1 .. 256";
                   }
                 }
                 container ports {
                   description "Port configuration";
                   uses apply-advanced;
                   container ethernet {
                     description "Ethernet settings";
                     uses apply-advanced;
                     leaf management-vlan {
                       description "Management VLAN identifier";
                       default "1";
                       type union {
                         type string {
                           pattern "<.*>|$.*";
                         }
                         type int32 {
                           range "1 .. 4094";
                         }
                       }
                     }
                     leaf untagged-vlan {
                       description "Untagged VLAN identifier";
                       default "1";
                       type union {
                         type string {
                           pattern "<.*>|$.*";
                         }
                         type int32 {
                           range "1 .. 4094";
                         }
                       }
                     }
                     choice inet-address {
                       case case_1 {
                         container static {
                           presence "enable static";
                           description "Specify static parameters";
                           uses apply-advanced;
                           leaf address {
                             description "Static IP address";
                             type jt:ipv4prefix;
                           }
                           leaf default-gateway {
                             description "Default gateway IP";
                             type jt:ipaddr;
                           }
                         }
                       }
                     }
                     leaf-list name-server {
                       ordered-by user;
                       description "Domain name server IP address";
                       type jt:ipaddr;
                       max-elements 2;
                     }
                   }
                 }
                 container console {
                   uses apply-advanced;
                   leaf baud-rate {
                     description "Baud-rate values are 9600,19200,38400,57600,115200";
                     default "115200";
                     type union {
                       type int32;
                       type string {
                         pattern "<.*>|$.*";
                       }
                     }
                   }
                 }
                 container services {
                   description "System services configuration";
                   uses apply-advanced;
                   leaf ssh {
                     description "Enable SSH service on the access point";
                     type empty;
                   }
                 }
               }
               container dot1x-supplicant {
                 uses apply-advanced;
                 leaf username {
                   description "Username";
                   type string {
                     length "1 .. 64";
                   }
                 }
                 leaf password {
                   description "Dot1x supplicant mode password";
                   type string {
                     length "1 .. 64";
                   }
                 }
               }
             }
           }
         }
         container access-point-options {
           description "Configure access point options";
           uses ap-options-type;
         }
         container logging-options {
           description "Configure access point logging options";
           uses log-options-type;
         }
         container captive-portal {
           presence "enable captive-portal";
           description "Access point captive portal settings";
           uses apply-advanced;
           container authentication {
             description "Authentication settings for captive portal";
             presence "enable authentication";
             uses captive-portal-auth-type;
           }
           container dhcp {
             presence "enable dhcp";
             description "DHCP settings";
             uses apply-advanced;
             leaf gateway {
               description "Set DHCP server IP address";
               type jt:ipaddr;
             }
             leaf port {
               description "Set DHCP server port";
               default "67";
               type union {
                 type string {
                   pattern "<.*>|$.*";
                 }
                 type uint16 {
                   range "1 .. 65535";
                 }
               }
             }
             leaf relay-agent {
               description "Set DHCP relay agent";
               type jt:ipprefix;
             }
           }
           container splash-page {
             presence "enable splash-page";
             description "Splash page settings";
             uses apply-advanced;
             container title {
               description "Specify the title of splash page";
               presence "enable title";
               uses splash-page-title-type;
             }
             container header {
               description "Specify the header of splash page";
               presence "enable header";
               uses splash-page-header-type;
             }
             container footer {
               description "Specify the footer of splash page";
               presence "enable footer";
               uses splash-page-footer-type;
             }
             leaf background-color {
               description "Specify the background color of splash page";
               type string {
               }
             }
             container logo-image {
               description "Specify the logo image for splash page";
               presence "enable logo-image";
               uses splash-page-logo-image-type;
             }
           }
           container ssl {
             presence "enable ssl";
             description "SSL settings";
             uses apply-advanced;
             choice enable-ssl {
               case case_1 {
                 leaf on {
                   description "Turn on ssl";
                   type empty;
                 }
               }
               case case_2 {
                 leaf off {
                   description "Turn off ssl";
                   type empty;
                 }
               }
             }
             leaf cert-file {
               description "Specify the certification file";
               type string;
             }
           }
           leaf session-timeout {
             description "Specify the session timeout";
             default "300";
             units "seconds";
             type union {
               type uint32;
               type string {
                 pattern "<.*>|$.*";
               }
             }
           }
           leaf idle-timeout {
             description "Specify the idle timeout";
             default "180";
             units "seconds";
             type union {
               type uint32;
               type string {
                 pattern "<.*>|$.*";
               }
             }
           }
         }
         list radio {
           key name;
           ordered-by user;
           description "Access point radio settings";
           max-elements 2;
           leaf name {
             description "Specify radio identifier value (1: 5GHz; 2: 2.4GHz)";
             type union {
               type string {
                 pattern "<.*>|$.*";
               }
               type int32 {
                 range "1 .. 2";
               }
             }
           }
           uses apply-advanced;
           container radio-options {
             description "Configure radio options";
             uses apply-advanced;
             leaf radio-off {
               description "Radio is off";
               type empty;
             }
             leaf dfs-off {
               description "Dynamic frequency selection turn off";
               type empty;
             }
             leaf disable-dot11d {
               description "Disable dot11d regulatory domain support";
               type empty;
             }
             leaf mode {
               description "Mode for radio operation";
               type enumeration {
                 enum "an" {
                   description "Wireless Mode a/n  (IEEE 802.11a/n)";
                 }
                 enum "5GHz" {
                   description "Radio Frequency -5GHz-n";
                 }
                 enum "2.4GHz" {
                   description "Radio Frequency -2.4GHz-n";
                 }
                 enum "acn" {
                   description "Wireless Mode ac/n (IEEE 802.11ac/n)";
                 }
                 enum "gn" {
                   description "Wireless Mode g/n (IEEE 802.11g/n)";
                 }
                 enum "g" {
                   description "Wireless Mode g (IEEE 802.11g)";
                 }
               }
             }
             container channel {
               description "Configure channel settings";
               uses apply-advanced;
               leaf number {
                 description "Provide channel selection";
                 default "auto";
                 type enumeration {
                   enum "1" {
                     description "Channel 1";
                   }
                   enum "2" {
                     description "Channel 2";
                   }
                   enum "3" {
                     description "Channel 3";
                   }
                   enum "4" {
                     description "Channel 4";
                   }
                   enum "5" {
                     description "Channel 5";
                   }
                   enum "6" {
                     description "Channel 6";
                   }
                   enum "7" {
                     description "Channel 7";
                   }
                   enum "8" {
                     description "Channel 8";
                   }
                   enum "9" {
                     description "Channel 9";
                   }
                   enum "10" {
                     description "Channel 10";
                   }
                   enum "11" {
                     description "Channel 11";
                   }
                   enum "12" {
                     description "Channel 12";
                   }
                   enum "13" {
                     description "Channel 13";
                   }
                   enum "36" {
                     description "Channel 36";
                   }
                   enum "40" {
                     description "Channel 40";
                   }
                   enum "44" {
                     description "Channel 44";
                   }
                   enum "48" {
                     description "Channel 48";
                   }
                   enum "52" {
                     description "Channel 52";
                   }
                   enum "56" {
                     description "Channel 56";
                   }
                   enum "60" {
                     description "Channel 60";
                   }
                   enum "64" {
                     description "Channel 64";
                   }
                   enum "100" {
                     description "Channel 100";
                   }
                   enum "104" {
                     description "Channel 104";
                   }
                   enum "108" {
                     description "Channel 108";
                   }
                   enum "112" {
                     description "Channel 112";
                   }
                   enum "116" {
                     description "Channel 116";
                   }
                   enum "120" {
                     description "Channel 120";
                   }
                   enum "124" {
                     description "Channel 124";
                   }
                   enum "128" {
                     description "Channel 128";
                   }
                   enum "132" {
                     description "Channel 132";
                   }
                   enum "136" {
                     description "Channel 136";
                   }
                   enum "140" {
                     description "Channel 140";
                   }
                   enum "144" {
                     description "Channel 144";
                   }
                   enum "149" {
                     description "Channel 149";
                   }
                   enum "153" {
                     description "Channel 153";
                   }
                   enum "157" {
                     description "Channel 157";
                   }
                   enum "161" {
                     description "Channel 161";
                   }
                   enum "165" {
                     description "Channel 165";
                   }
                   enum "auto" {
                     description "Automatically selected";
                   }
                 }
               }
               leaf bandwidth {
                 description "Provide channel bandwidth in MHz(2.4G: 20/40; 5G: 20/40/80)";
                 type union {
                   type int32;
                   type string {
                     pattern "<.*>|$.*";
                   }
                 }
               }
               leaf primary {
                 description "Select primary channel";
                 type enumeration {
                   enum "lower" {
                     description "Set lower channel as primary";
                   }
                   enum "upper" {
                     description "Set upper channel as primary";
                   }
                 }
               }
             }
             leaf space-time-block-coding {
               description "Enable space time block coding";
               type empty;
             }
             leaf protection {
               description "Select protection mode";
               type enumeration {
                 enum "auto" {
                   description "Protection mode- AUTO";
                 }
                 enum "off" {
                   description "Protection mode- OFF";
                 }
               }
             }
             leaf beacon-interval {
               description "Set the beacon interval";
               default "100";
               units "milliseconds";
               type union {
                 type string {
                   pattern "<.*>|$.*";
                 }
                 type int32 {
                   range "20 .. 2000";
                 }
               }
             }
             leaf dtim-period {
               description "Set delivery traffic indication message period (beacon count)";
               default "2";
               type union {
                 type string {
                   pattern "<.*>|$.*";
                 }
                 type int32 {
                   range "1 .. 255";
                 }
               }
             }
             leaf rts-threshold {
               description "Set RTS- threshold";
               default "2347";
               type union {
                 type string {
                   pattern "<.*>|$.*";
                 }
                 type int32 {
                   range "0 .. 2347";
                 }
               }
             }
             leaf no-short-guard-interval {
               description "Disable 802.11n short inter-symbol guard interval";
               type empty;
             }
             leaf fragmentation-threshold {
               description "Packet fragment size(even numbers)";
               default "2346";
               type union {
                 type string {
                   pattern "<.*>|$.*";
                 }
                 type int32 {
                   range "256 .. 2346";
                 }
               }
             }
             leaf maximum-stations {
               description "Set limit on maximum supported stations";
               default "200";
               type union {
                 type string {
                   pattern "<.*>|$.*";
                 }
                 type int32 {
                   range "0 .. 200";
                 }
               }
             }
             leaf transmit-power {
               description "Set transmit power";
               default "100";
               units "percent";
               type union {
                 type string {
                   pattern "<.*>|$.*";
                 }
                 type int32 {
                   range "3 .. 100";
                 }
               }
             }
             leaf fixed-multicast-rate {
               description "Provide multicast rate";
               type enumeration {
                 enum "auto" {
                   description "Auto rate selection";
                 }
                 enum "1" {
                   description "Rate-1Mbps ";
                 }
                 enum "2" {
                   description "Rate-2Mbps ";
                 }
                 enum "5.5" {
                   description "Rate-5.5Mbps ";
                 }
                 enum "6" {
                   description "Rate-6Mbps ";
                 }
                 enum "9" {
                   description "Rate-9Mbps ";
                 }
                 enum "11" {
                   description "Rate-11Mbps ";
                 }
                 enum "12" {
                   description "Rate-12Mbps ";
                 }
                 enum "18" {
                   description "Rate-18Mbps ";
                 }
                 enum "24" {
                   description "Rate-24Mbps ";
                 }
                 enum "36" {
                   description "Rate-36Mbps ";
                 }
                 enum "48" {
                   description "Rate-48Mbps ";
                 }
                 enum "54" {
                   description "Rate-54Mbps ";
                 }
               }
             }
             container transmit-rate-sets {
               description "Specify the transmit rate sets";
               uses transmit-rate-sets;
             }
             container broadcast-multicast-rate-limit {
               description "Configure rate limit for broadcast and multicast traffic";
               uses broadcast-multicast-rate-limit;
             }
           }
           leaf station-isolation {
             description "Isolate the clients connected to the same VAP within a radio";
             type empty;
           }
           list virtual-access-point {
             key name;
             ordered-by user;
             description "Virtual access point configuration";
             max-elements 8;
             uses vap-type;
           }
           container quality-of-service {
             description "Wireless quality of service configuration";
             uses qos-parameter-type;
           }
         }
       }
       container syslog-options {
         description "Configure Access Point Logging options";
         uses apply-advanced;
         leaf log-size {
           description "Configure Max log file size";
           units "kilobytes";
           type union {
             type string {
               pattern "<.*>|$.*";
             }
             type uint32 {
               range "4 .. 1024";
             }
           }
         }
         leaf period {
           description "Configure log fetch interval";
           units "seconds";
           type union {
             type string {
               pattern "<.*>|$.*";
             }
             type int32 {
               range "60 .. 86400";
             }
           }
         }
       }
     }
   }
   grouping ap-interface-list-type {
     description "Logical interface in this cluster";
     leaf name {
       description "Interface device name";
       type union {
         type jt:interface-device;
         type string {
           pattern "<.*>|$.*";
         }
       }
     }
     uses apply-advanced;
   }
   grouping ap-options-type {
     description "Configure access point options";
     uses apply-advanced;
     container country {
       description "Country name";
       uses country;
     }
     container station-mac-filter {
       uses station-mac-filter;
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping broadcast-multicast-rate-limit {
     description "Specify broadcast and multicast rate limit";
     uses apply-advanced;
     leaf rate-limit {
       description "Rate limit";
       default "50";
       units "pps";
       type union {
         type string {
           pattern "<.*>|$.*";
         }
         type int32 {
           range "1 .. 50";
         }
       }
     }
     leaf rate-limit-bursts {
       description "Rate limit bursts";
       default "75";
       units "pps";
       type union {
         type string {
           pattern "<.*>|$.*";
         }
         type int32 {
           range "1 .. 75";
         }
       }
     }
   }
   grouping captive-portal-auth-type {
     description "Configure authentication settings";
     uses apply-advanced;
     choice authentication-type {
       case case_1 {
         container simple-pass {
           description "Simple password configuration";
           presence "enable simple-pass";
           uses simple-pass-type;
         }
       }
       case case_2 {
         container external-server {
           description "External server configuration";
           presence "enable external-server";
           uses external-server-type;
         }
       }
     }
   }
   grouping country {
     uses apply-advanced;
     choice code {
       case case_1 {
         leaf AE {
           description "United Arab Emirates";
           status deprecated;
           type empty;
         }
       }
       case case_2 {
         leaf AG {
           description "Antigua and Barbuda";
           status deprecated;
           type empty;
         }
       }
       case case_3 {
         leaf AN {
           description "Netherlands Antilles";
           status deprecated;
           type empty;
         }
       }
       case case_4 {
         leaf AR {
           description "Argentina";
           status deprecated;
           type empty;
         }
       }
       case case_5 {
         leaf AS {
           description "American Somoa";
           status deprecated;
           type empty;
         }
       }
       case case_6 {
         leaf AT {
           description "Austria";
           type empty;
         }
       }
       case case_7 {
         leaf AU {
           description "Australia";
           type empty;
         }
       }
       case case_8 {
         leaf AW {
           description "Aruba";
           status deprecated;
           type empty;
         }
       }
       case case_9 {
         leaf AZ {
           description "Azerbaijan";
           status deprecated;
           type empty;
         }
       }
       case case_10 {
         leaf BA {
           description "Bosnia";
           status deprecated;
           type empty;
         }
       }
       case case_11 {
         leaf BB {
           description "Barbados";
           status deprecated;
           type empty;
         }
       }
       case case_12 {
         leaf BD {
           description "Bangladesh";
           status deprecated;
           type empty;
         }
       }
       case case_13 {
         leaf BE {
           description "Belgium";
           type empty;
         }
       }
       case case_14 {
         leaf BG {
           description "Bulgaria";
           type empty;
         }
       }
       case case_15 {
         leaf BH {
           description "Bahrain";
           status deprecated;
           type empty;
         }
       }
       case case_16 {
         leaf BM {
           description "Bermuda";
           status deprecated;
           type empty;
         }
       }
       case case_17 {
         leaf BN {
           description "Brunei";
           status deprecated;
           type empty;
         }
       }
       case case_18 {
         leaf BO {
           description "Bolivia";
           status deprecated;
           type empty;
         }
       }
       case case_19 {
         leaf BR {
           description "Brazil";
           status deprecated;
           type empty;
         }
       }
       case case_20 {
         leaf BS {
           description "Bahamas";
           status deprecated;
           type empty;
         }
       }
       case case_21 {
         leaf BT {
           description "Bhutan";
           status deprecated;
           type empty;
         }
       }
       case case_22 {
         leaf BY {
           description "Belarus";
           status deprecated;
           type empty;
         }
       }
       case case_23 {
         leaf CA {
           description "Canada";
           type empty;
         }
       }
       case case_24 {
         leaf CH {
           description "Switzerland";
           status deprecated;
           type empty;
         }
       }
       case case_25 {
         leaf CL {
           description "Chile";
           status deprecated;
           type empty;
         }
       }
       case case_26 {
         leaf CN {
           description "China";
           type empty;
         }
       }
       case case_27 {
         leaf CO {
           description "Colombia";
           status deprecated;
           type empty;
         }
       }
       case case_28 {
         leaf CR {
           description "Costa Rica";
           status deprecated;
           type empty;
         }
       }
       case case_29 {
         leaf CU {
           description "Cuba";
           status deprecated;
           type empty;
         }
       }
       case case_30 {
         leaf CV {
           description "Cape Verde";
           status deprecated;
           type empty;
         }
       }
       case case_31 {
         leaf CY {
           description "Cyprus";
           type empty;
         }
       }
       case case_32 {
         leaf CZ {
           description "Czechia";
           type empty;
         }
       }
       case case_33 {
         leaf DE {
           description "Germany";
           type empty;
         }
       }
       case case_34 {
         leaf DK {
           description "Denmark";
           type empty;
         }
       }
       case case_35 {
         leaf DM {
           description "Dominica";
           status deprecated;
           type empty;
         }
       }
       case case_36 {
         leaf DO {
           description "Dominican Republic";
           status deprecated;
           type empty;
         }
       }
       case case_37 {
         leaf EC {
           description "Ecuador";
           status deprecated;
           type empty;
         }
       }
       case case_38 {
         leaf EE {
           description "Estonia";
           type empty;
         }
       }
       case case_39 {
         leaf EG {
           description "Egypt";
           status deprecated;
           type empty;
         }
       }
       case case_40 {
         leaf ES {
           description "Spain";
           type empty;
         }
       }
       case case_41 {
         leaf FI {
           description "Finland";
           type empty;
         }
       }
       case case_42 {
         leaf FK {
           description "Faulkland Islands";
           status deprecated;
           type empty;
         }
       }
       case case_43 {
         leaf FM {
           description "Federated States of Micronesia";
           status deprecated;
           type empty;
         }
       }
       case case_44 {
         leaf FR {
           description "France";
           type empty;
         }
       }
       case case_45 {
         leaf GB {
           description "United Kingdom";
           type empty;
         }
       }
       case case_46 {
         leaf GF {
           description "French Guiana";
           status deprecated;
           type empty;
         }
       }
       case case_47 {
         leaf GG {
           description "Guernsey";
           status deprecated;
           type empty;
         }
       }
       case case_48 {
         leaf GI {
           description "Gibralter";
           status deprecated;
           type empty;
         }
       }
       case case_49 {
         leaf GP {
           description "Guadeloupe";
           status deprecated;
           type empty;
         }
       }
       case case_50 {
         leaf GR {
           description "Greece";
           type empty;
         }
       }
       case case_51 {
         leaf GT {
           description "Guatemala";
           status deprecated;
           type empty;
         }
       }
       case case_52 {
         leaf GU {
           description "Guam";
           status deprecated;
           type empty;
         }
       }
       case case_53 {
         leaf HK {
           description "Hong Kong";
           status deprecated;
           type empty;
         }
       }
       case case_54 {
         leaf HN {
           description "Honduras";
           status deprecated;
           type empty;
         }
       }
       case case_55 {
         leaf HR {
           description "Croatia";
           type empty;
         }
       }
       case case_56 {
         leaf HT {
           description "Haiti";
           status deprecated;
           type empty;
         }
       }
       case case_57 {
         leaf HU {
           description "Hungary";
           type empty;
         }
       }
       case case_58 {
         leaf ID {
           description "Indonesia";
           type empty;
         }
       }
       case case_59 {
         leaf IE {
           description "Ireland";
           type empty;
         }
       }
       case case_60 {
         leaf IL {
           description "Israel";
           type empty;
         }
       }
       case case_61 {
         leaf IM {
           description "Isle of Man";
           status deprecated;
           type empty;
         }
       }
       case case_62 {
         leaf IN {
           description "India";
           type empty;
         }
       }
       case case_63 {
         leaf IR {
           description "Iran";
           status deprecated;
           type empty;
         }
       }
       case case_64 {
         leaf IS {
           description "Iceland";
           status deprecated;
           type empty;
         }
       }
       case case_65 {
         leaf IT {
           description "Italy";
           type empty;
         }
       }
       case case_66 {
         leaf JE {
           description "Jersey";
           status deprecated;
           type empty;
         }
       }
       case case_67 {
         leaf JM {
           description "Jamaica";
           status deprecated;
           type empty;
         }
       }
       case case_68 {
         leaf JO {
           description "Jordan";
           status deprecated;
           type empty;
         }
       }
       case case_69 {
         leaf JP {
           description "Japan";
           type empty;
         }
       }
       case case_70 {
         leaf KE {
           description "Kenya";
           status deprecated;
           type empty;
         }
       }
       case case_71 {
         leaf KI {
           description "Kiribati";
           status deprecated;
           type empty;
         }
       }
       case case_72 {
         leaf KR {
           description "Korea Republic";
           type empty;
         }
       }
       case case_73 {
         leaf KW {
           description "Kuwait";
           status deprecated;
           type empty;
         }
       }
       case case_74 {
         leaf KY {
           description "Cayman Islands";
           status deprecated;
           type empty;
         }
       }
       case case_75 {
         leaf LA {
           description "LAO People's Democratic Republic";
           status deprecated;
           type empty;
         }
       }
       case case_76 {
         leaf LB {
           description "Lebanon";
           status deprecated;
           type empty;
         }
       }
       case case_77 {
         leaf LI {
           description "Liechtenstein";
           status deprecated;
           type empty;
         }
       }
       case case_78 {
         leaf LK {
           description "Sri Lanka";
           status deprecated;
           type empty;
         }
       }
       case case_79 {
         leaf LS {
           description "Lesotho";
           status deprecated;
           type empty;
         }
       }
       case case_80 {
         leaf LT {
           description "Lithuania";
           type empty;
         }
       }
       case case_81 {
         leaf LU {
           description "Luxembourg";
           type empty;
         }
       }
       case case_82 {
         leaf LV {
           description "Latvia";
           type empty;
         }
       }
       case case_83 {
         leaf MA {
           description "Morocco";
           status deprecated;
           type empty;
         }
       }
       case case_84 {
         leaf MC {
           description "Monaco";
           status deprecated;
           type empty;
         }
       }
       case case_85 {
         leaf MK {
           description "Macedonia";
           status deprecated;
           type empty;
         }
       }
       case case_86 {
         leaf MO {
           description "Macao";
           status deprecated;
           type empty;
         }
       }
       case case_87 {
         leaf MP {
           description "Northern Mariana Islands";
           status deprecated;
           type empty;
         }
       }
       case case_88 {
         leaf MQ {
           description "Martinique";
           status deprecated;
           type empty;
         }
       }
       case case_89 {
         leaf MR {
           description "Mauritania";
           status deprecated;
           type empty;
         }
       }
       case case_90 {
         leaf MT {
           description "Malta";
           type empty;
         }
       }
       case case_91 {
         leaf MU {
           description "Mauritius";
           status deprecated;
           type empty;
         }
       }
       case case_92 {
         leaf MV {
           description "Maldives";
           status deprecated;
           type empty;
         }
       }
       case case_93 {
         leaf MW {
           description "Malawi";
           status deprecated;
           type empty;
         }
       }
       case case_94 {
         leaf MX {
           description "Mexico";
           type empty;
         }
       }
       case case_95 {
         leaf MY {
           description "Malaysia";
           type empty;
         }
       }
       case case_96 {
         leaf NG {
           description "Nigeria";
           status deprecated;
           type empty;
         }
       }
       case case_97 {
         leaf NI {
           description "Nicaragua";
           status deprecated;
           type empty;
         }
       }
       case case_98 {
         leaf NL {
           description "Netherlands";
           type empty;
         }
       }
       case case_99 {
         leaf NO {
           description "Norway";
           status deprecated;
           type empty;
         }
       }
       case case_100 {
         leaf NZ {
           description "New Zealand";
           type empty;
         }
       }
       case case_101 {
         leaf OM {
           description "Oman";
           status deprecated;
           type empty;
         }
       }
       case case_102 {
         leaf PA {
           description "Panama";
           status deprecated;
           type empty;
         }
       }
       case case_103 {
         leaf PE {
           description "Peru";
           status deprecated;
           type empty;
         }
       }
       case case_104 {
         leaf PG {
           description "Papua New Guinea";
           status deprecated;
           type empty;
         }
       }
       case case_105 {
         leaf PH {
           description "Philippines";
           status deprecated;
           type empty;
         }
       }
       case case_106 {
         leaf PK {
           description "Pakistan";
           status deprecated;
           type empty;
         }
       }
       case case_107 {
         leaf PL {
           description "Poland";
           type empty;
         }
       }
       case case_108 {
         leaf PM {
           description "St. Pierre and Miquelon";
           status deprecated;
           type empty;
         }
       }
       case case_109 {
         leaf PR {
           description "Puerto Rico";
           status deprecated;
           type empty;
         }
       }
       case case_110 {
         leaf PT {
           description "Portugal";
           type empty;
         }
       }
       case case_111 {
         leaf RE {
           description "Reunion";
           status deprecated;
           type empty;
         }
       }
       case case_112 {
         leaf RO {
           description "Romania";
           type empty;
         }
       }
       case case_113 {
         leaf RU {
           description "Russia";
           status deprecated;
           type empty;
         }
       }
       case case_114 {
         leaf SA {
           description "Saudi Arabia";
           status deprecated;
           type empty;
         }
       }
       case case_115 {
         leaf SE {
           description "Sweden";
           type empty;
         }
       }
       case case_116 {
         leaf SG {
           description "Singapore";
           status deprecated;
           type empty;
         }
       }
       case case_117 {
         leaf SI {
           description "Slovenia";
           type empty;
         }
       }
       case case_118 {
         leaf SK {
           description "Slovakia";
           type empty;
         }
       }
       case case_119 {
         leaf SV {
           description "El Salvador";
           status deprecated;
           type empty;
         }
       }
       case case_120 {
         leaf SY {
           description "Syria";
           status deprecated;
           type empty;
         }
       }
       case case_121 {
         leaf TH {
           description "Thailand";
           status deprecated;
           type empty;
         }
       }
       case case_122 {
         leaf TJ {
           description "Tajikistan";
           status deprecated;
           type empty;
         }
       }
       case case_123 {
         leaf TN {
           description "Tunisia";
           status deprecated;
           type empty;
         }
       }
       case case_124 {
         leaf TR {
           description "Turkey";
           status deprecated;
           type empty;
         }
       }
       case case_125 {
         leaf TT {
           description "Trinidad & Tobago";
           status deprecated;
           type empty;
         }
       }
       case case_126 {
         leaf TW {
           description "Taiwan";
           status deprecated;
           type empty;
         }
       }
       case case_127 {
         leaf TZ {
           description "Tanzania";
           status deprecated;
           type empty;
         }
       }
       case case_128 {
         leaf UA {
           description "Ukraine";
           status deprecated;
           type empty;
         }
       }
       case case_129 {
         leaf UM {
           description "United States (Minor Outlying Islands)";
           status deprecated;
           type empty;
         }
       }
       case case_130 {
         leaf US {
           description "United States";
           type empty;
         }
       }
       case case_131 {
         leaf UY {
           description "Uruguay";
           status deprecated;
           type empty;
         }
       }
       case case_132 {
         leaf UZ {
           description "Uzbekistan";
           status deprecated;
           type empty;
         }
       }
       case case_133 {
         leaf VA {
           description "Holy See (Vatican City State)";
           status deprecated;
           type empty;
         }
       }
       case case_134 {
         leaf VE {
           description "Venezuela";
           status deprecated;
           type empty;
         }
       }
       case case_135 {
         leaf VG {
           description "Virgin Islands (British)";
           status deprecated;
           type empty;
         }
       }
       case case_136 {
         leaf VI {
           description "Virgin Islands (United States)";
           status deprecated;
           type empty;
         }
       }
       case case_137 {
         leaf VN {
           description "Vietnam";
           type empty;
         }
       }
       case case_138 {
         leaf YT {
           description "Mayotte";
           status deprecated;
           type empty;
         }
       }
       case case_139 {
         leaf ZA {
           description "South Africa";
           status deprecated;
           type empty;
         }
       }
       case case_140 {
         leaf ZM {
           description "Zambia";
           status deprecated;
           type empty;
         }
       }
     }
   }
   grouping external-server-type {
     uses apply-advanced;
     leaf radius-server {
       description "Set RADIUS server IP address";
       type jt:ipaddr;
     }
     leaf radius-port {
       description "Set RADIUS server port number";
       default "1812";
       type union {
         type string {
           pattern "<.*>|$.*";
         }
         type uint16 {
           range "1 .. 65535";
         }
       }
     }
     leaf radius-key {
       description "Secret RADIUS key";
       type string {
         length "1 .. 64";
       }
     }
     leaf radius-eaptype {
       description "Set EAP type";
       type enumeration {
         enum "PAP" {
           description "Enable PAP";
         }
         enum "CHAP" {
           description "Enable CHAP";
         }
       }
     }
   }
   grouping log-options-type {
     uses apply-advanced;
     leaf enable-persistent {
       description "Turn on persistent logging on the access point";
       type empty;
     }
     leaf enable-remote {
       description "Turn on remote logging on the access point";
       type empty;
     }
     leaf log-server-address {
       description "Remote log server IP address";
       type jt:ipv4addr;
     }
     leaf log-server-port {
       description "Remote log serer port";
       type union {
         type string {
           pattern "<.*>|$.*";
         }
         type uint32 {
           range "1 .. 65536";
         }
       }
     }
     leaf log-level {
       description "Event severity, 0 - Errors, 7 - Info";
       type union {
         type string {
           pattern "<.*>|$.*";
         }
         type int32 {
           range "0 .. 7";
         }
       }
     }
   }
   grouping macro-data-type {
     leaf name {
       description "Keyword part of the keyword-value pair";
       type string;
     }
     leaf value {
       description "Value part of the keyword-value pair";
       type string;
     }
   }
   grouping qos-parameter-type {
     uses apply-advanced;
     leaf no-wifi-multimedia {
       description "Disable WIFI multimedia";
       type empty;
     }
     leaf no-acknowledgement {
       description "Disable acknowledgement";
       type empty;
     }
     leaf no-auto-power-save {
       description "Disable auto power save delivery";
       type empty;
     }
     container access-point-queues {
       description "Configure the access point queues";
       uses apply-advanced;
       container voice-queue {
         description "Configure voice queue";
         uses access-point-queue-type;
       }
       container video-queue {
         description "Configure video queue";
         uses access-point-queue-type;
       }
       container best-effort-queue {
         description "Configure best effort queue";
         uses access-point-queue-type;
       }
       container background-queue {
         description "Configure background queue";
         uses access-point-queue-type;
       }
     }
     container station-queues {
       description "Configure the station queues";
       uses apply-advanced;
       container voice-queue {
         description "Configure voice queue";
         uses station-queue-type;
       }
       container video-queue {
         description "Configure video queue";
         uses station-queue-type;
       }
       container best-effort-queue {
         description "Configure best effort queue";
         uses station-queue-type;
       }
       container background-queue {
         description "Configure background queue";
         uses station-queue-type;
       }
     }
   }
   grouping access-point-queue-type {
     description "Access point queue type";
     uses apply-advanced;
     leaf arbitration-inter-frame-space {
       description "Arbitration space between frames";
       type union {
         type string {
           pattern "<.*>|$.*";
         }
         type int32 {
           range "1 .. 255";
         }
       }
     }
     container minimum-contention-window {
       description "Minimum contention window size";
       uses contention-window;
     }
     container maximum-contention-window {
       description "Maximum contention window size";
       uses contention-window;
     }
     leaf maximum-burst {
       description "Specify maximum burst";
       units "microseconds";
       type union {
         type string {
           pattern "<.*>|$.*";
         }
         type int32 {
           range "0 .. 999900";
         }
       }
     }
   }
   grouping contention-window {
     uses apply-advanced;
     leaf window-size {
       description "Values are 1,3,7,15,31,63,127,255,511 and 1023";
       type union {
         type int32;
         type string {
           pattern "<.*>|$.*";
         }
       }
     }
   }
   grouping simple-pass-type {
     uses apply-advanced;
     leaf key {
       description "Set simple password key";
       type string {
         length "8 .. 64";
       }
     }
   }
   grouping splash-page-footer-type {
     uses apply-advanced;
     leaf content {
       type string {
         length "1 .. 256";
       }
     }
     leaf color {
       description "Set the color";
       type string {
       }
     }
     leaf font-size {
       description "Set the font size";
       type union {
         type uint16;
         type string {
           pattern "<.*>|$.*";
         }
       }
     }
   }
   grouping splash-page-header-type {
     uses apply-advanced;
     leaf content {
       type string {
         length "1 .. 256";
       }
     }
     leaf color {
       description "Set the color";
       type string {
       }
     }
     leaf font-size {
       description "Set the font size";
       type union {
         type uint16;
         type string {
           pattern "<.*>|$.*";
         }
       }
     }
   }
   grouping splash-page-logo-image-type {
     uses apply-advanced;
     leaf filename {
       type jt:filename;
     }
   }
   grouping splash-page-title-type {
     uses apply-advanced;
     leaf content {
       type string {
         length "1 .. 64";
       }
     }
     leaf color {
       description "Set the color";
       type string {
       }
     }
     leaf font-size {
       description "Set the font size";
       type union {
         type uint16;
         type string {
           pattern "<.*>|$.*";
         }
       }
     }
   }
   grouping station-mac-filter {
     description "Configure MAC filter";
     uses apply-advanced;
     container allow-list {
       description "Allow the MAC addresseses";
       uses apply-advanced;
       leaf-list mac-address {
         ordered-by user;
         description "List of allowed MAC addresses";
         type jt:mac-unicast;
         max-elements 16;
       }
     }
     container deny-list {
       description "Deny the MAC addresseses";
       uses apply-advanced;
       leaf-list mac-address {
         ordered-by user;
         description "List of denied MAC addresses";
         type jt:mac-unicast;
         max-elements 16;
       }
     }
   }
   grouping station-queue-type {
     description "Station queue type";
     uses apply-advanced;
     leaf arbitration-inter-frame-space {
       description "Arbitration space between frames";
       type union {
         type string {
           pattern "<.*>|$.*";
         }
         type int32 {
           range "1 .. 255";
         }
       }
     }
     container minimum-contention-window {
       description "Specify minimum contention window size";
       uses contention-window;
     }
     container maximum-contention-window {
       description "Specify maximum contention window size";
       uses contention-window;
     }
     leaf transmit-opportunity-limit {
       description "Specify transmission opportunity limit";
       type union {
         type string {
           pattern "<.*>|$.*";
         }
         type int32 {
           range "0 .. 65535";
         }
       }
     }
   }
   grouping transmit-rate-sets {
     description "Specify the transmit rate sets";
     uses apply-advanced;
     list supported-rates {
       key name;
       ordered-by user;
       description "List of supported rates in Mbps";
       max-elements 12;
       uses rates;
     }
     list supported-basic-rates {
       key name;
       ordered-by user;
       description "List of supported basic rates in Mbps";
       max-elements 12;
       uses rates;
     }
   }
   grouping rates {
     leaf name {
       type enumeration {
         enum "1" {
           description "Rate-1Mbps ";
         }
         enum "2" {
           description "Rate-2Mbps ";
         }
         enum "5.5" {
           description "Rate-5.5Mbps ";
         }
         enum "6" {
           description "Rate-6Mbps ";
         }
         enum "9" {
           description "Rate-9Mbps ";
         }
         enum "11" {
           description "Rate-11Mbps ";
         }
         enum "12" {
           description "Rate-12Mbps ";
         }
         enum "18" {
           description "Rate-18Mbps ";
         }
         enum "24" {
           description "Rate-24Mbps ";
         }
         enum "36" {
           description "Rate-36Mbps ";
         }
         enum "48" {
           description "Rate-48Mbps ";
         }
         enum "54" {
           description "Rate-54Mbps ";
         }
       }
     }
     uses apply-advanced;
   }
   grouping vap-type {
     leaf name {
       description "Specify VAP identifier value";
       type union {
         type string {
           pattern "<.*>|$.*";
         }
         type int32 {
           range "0 .. 7";
         }
       }
     }
     uses apply-advanced;
     leaf description {
       description "Specify the virtual access point description";
       type string {
         length "1 .. 64";
       }
     }
     leaf ssid {
       description "SSID value for the virtual access point";
       type string {
         length "2 .. 32";
       }
     }
     leaf vlan {
       description "VLAN id for the virtual access point";
       type union {
         type string {
           pattern "<.*>|$.*";
         }
         type int32 {
           range "1 .. 4094";
         }
       }
     }
     leaf download-limit {
       description "Download rate limit Kbps";
       type union {
         type string {
           pattern "<.*>|$.*";
         }
         type int32 {
           range "256 .. 1048576";
         }
       }
     }
     leaf upload-limit {
       description "Upload rate limit Kbps";
       type union {
         type string {
           pattern "<.*>|$.*";
         }
         type int32 {
           range "256 .. 1048576";
         }
       }
     }
     leaf no-broadcast-ssid {
       description "Disable broadcast SSID";
       type empty;
     }
     container http-redirect {
       description "Configure HTTP redirect setting";
       presence "enable http-redirect";
       uses http-redirect;
     }
     container security {
       description "Configure security settings for the VAP";
       presence "enable security";
       uses security;
     }
     container station-mac-filter {
       uses station-mac-filter;
     }
     leaf maximum-stations {
       description "Set limit on maximum supported stations";
       default "127";
       type union {
         type string {
           pattern "<.*>|$.*";
         }
         type int32 {
           range "1 .. 127";
         }
       }
     }
     leaf station-isolation {
       description "Isolate the clients connected to the same VAP";
       type empty;
     }
     leaf captive-portal {
       description "Enable captive portal";
       type empty;
     }
   }
   grouping http-redirect {
     description "Configure HTTP redirect setting";
     uses apply-advanced;
     leaf redirect-url {
       description "Set the HTTP redirect URL address";
       type string {
         length "1 .. 120";
       }
     }
   }
   grouping security {
     description "Configure one of security settings for the VAP";
     uses apply-advanced;
     leaf mac-authentication-type {
       description "Select MAC authentication type";
       type enumeration {
         enum "disabled" {
           description "Disable MAC authentication";
         }
         enum "local" {
           description "Select local MAC authentication";
         }
         enum "radius" {
           description "Select RADIUS server authentication";
         }
       }
     }
     choice security-type {
       case case_1 {
         container static-wep {
           description "Static WEP configuration";
           presence "enable static-wep";
           uses static-wep;
         }
       }
       case case_2 {
         container dot1x {
           description "Dot1x configuration";
           presence "enable dot1x";
           uses dot1x;
         }
       }
       case case_3 {
         container wpa-personal {
           description "Set WPA personal settings";
           presence "enable wpa-personal";
           uses wpa-personal;
         }
       }
       case case_4 {
         container wpa-enterprise {
           description "Set WAP enterprise settings";
           presence "enable wpa-enterprise";
           uses wpa-enterprise;
         }
       }
       case case_5 {
         leaf none {
           description "Unsecure plain-text communication";
           type empty;
         }
       }
     }
   }
   grouping dot1x {
     uses apply-advanced;
     leaf radius-server {
       description "Set RADIUS server IP address";
       type jt:ipaddr;
     }
     leaf radius-port {
       description "Set RADIUS server port number";
       default "1812";
       type union {
         type string {
           pattern "<.*>|$.*";
         }
         type uint16 {
           range "1 .. 65535";
         }
       }
     }
     leaf radius-key {
       description "Secret RADIUS key";
       type string {
         length "1 .. 64";
       }
     }
     leaf broadcast-key-refresh-rate {
       description "Broadcast key refresh rate";
       units "minutes";
       type union {
         type string {
           pattern "<.*>|$.*";
         }
         type int32 {
           range "0 .. 86400";
         }
       }
     }
     leaf session-key-refresh-rate {
       description "Session key refresh rate";
       units "minutes";
       type union {
         type string {
           pattern "<.*>|$.*";
         }
         type int32 {
           range "0 .. 86400";
         }
       }
     }
   }
   grouping static-wep {
     uses apply-advanced;
     leaf authentication-type {
       description "Select Static WEP authentication type";
       type enumeration {
         enum "open" {
           description "Open type";
         }
         enum "shared" {
           description "Shared type";
         }
         enum "both" {
           description "Both open and shared authentication";
         }
       }
     }
     leaf key-length {
       description "Specify key length (defaults to 64 bits)";
       type enumeration {
         enum "64bits" {
           description "Use 64 bit key (ASCII:5 chars, HEX:10 chars)";
         }
         enum "128bits" {
           description "Use 128 bit key (ASCII:13 chars, HEX:26 chars)";
         }
       }
     }
     leaf key-type {
       description "Specify key type (defaults to ASCII)";
       type enumeration {
         enum "ascii" {
           description "ASCII key (default key-length is 64 bits)";
         }
         enum "hex" {
           description "HEX key (default key-length is 64 bits)";
         }
       }
     }
     leaf transfer-key-index {
       description "Specify transfer key index (1-4)";
       default "1";
       type union {
         type string {
           pattern "<.*>|$.*";
         }
         type int32 {
           range "1 .. 4";
         }
       }
     }
     leaf wep-key-1 {
       description "Specify WEP key (defaults to ASCII 64 bits, 5 chars long)";
       type jt:unreadable;
     }
     leaf wep-key-2 {
       description "Specify WEP key (defaults to ASCII 64 bits, 5 chars long)";
       type jt:unreadable;
     }
     leaf wep-key-3 {
       description "Specify WEP key (defaults to ASCII 64 bits, 5 chars long)";
       type jt:unreadable;
     }
     leaf wep-key-4 {
       description "Specify WEP key (defaults to ASCII 64 bits, 5 chars long)";
       type jt:unreadable;
     }
   }
   grouping wpa-enterprise {
     uses apply-advanced;
     container wpa-version {
       description "Set WPA version";
       uses wpa-version;
     }
     container cipher-suites {
       description "Select the WPA cipher algorithm";
       uses cipher-suites;
     }
     leaf pre-authenticate {
       description "Enable pre-authentication";
       type empty;
     }
     container radius {
       description "RADIUS setting for WPA enterprise";
       presence "enable radius";
       status deprecated;
       uses radius-deprecated;
     }
     leaf radius-server {
       description "Set RADIUS server IP address";
       type jt:ipaddr;
     }
     leaf radius-port {
       description "Set RADIUS server port number";
       default "1812";
       type union {
         type string {
           pattern "<.*>|$.*";
         }
         type uint16 {
           range "1 .. 65535";
         }
       }
     }
     leaf radius-key {
       description "Secret RADIUS key";
       type string {
         length "1 .. 64";
       }
     }
     leaf broadcast-key-refresh-rate {
       description "Broadcast key refresh rate";
       units "minutes";
       type union {
         type string {
           pattern "<.*>|$.*";
         }
         type int32 {
           range "0 .. 86400";
         }
       }
     }
     leaf session-key-refresh-rate {
       description "Session key refresh rate";
       units "minutes";
       type union {
         type string {
           pattern "<.*>|$.*";
         }
         type int32 {
           range "0 .. 86400";
         }
       }
     }
   }
   grouping cipher-suites {
     uses apply-advanced;
     choice suites {
       case case_1 {
         leaf ccmp {
           description "CCMP";
           type empty;
         }
       }
       case case_2 {
         leaf tkip-ccmp {
           description "Use both TKIP and CCMP cipher suites";
           status deprecated;
           type empty;
         }
       }
     }
   }
   grouping radius-deprecated {
     uses apply-advanced;
     leaf radius-server {
       description "Set RADIUS server IP address";
       type jt:ipaddr;
     }
     leaf radius-port {
       description "Set RADIUS server port number";
       default "1812";
       type union {
         type string {
           pattern "<.*>|$.*";
         }
         type uint16 {
           range "1 .. 65535";
         }
       }
     }
     leaf radius-key {
       description "Secret RADIUS key";
       type string {
         length "1 .. 64";
       }
     }
     leaf broadcast-key-refresh-rate {
       description "Broadcast key refresh rate";
       units "minutes";
       type union {
         type string {
           pattern "<.*>|$.*";
         }
         type int32 {
           range "0 .. 86400";
         }
       }
     }
     leaf session-key-refresh-rate {
       description "Session key refresh rate";
       units "minutes";
       type union {
         type string {
           pattern "<.*>|$.*";
         }
         type int32 {
           range "0 .. 86400";
         }
       }
     }
   }
   grouping wpa-personal {
     uses apply-advanced;
     container wpa-version {
       description "Set WPA version";
       uses wpa-version;
     }
     container cipher-suites {
       description "Select the WPA cipher algorithm";
       uses cipher-suites;
     }
     leaf key {
       description "WPA shared key";
       type string {
         length "8 .. 64";
       }
     }
     leaf key-type {
       description "Specify key type (defaults to ASCII)";
       type enumeration {
         enum "ascii" {
           description "ASCII key (default key-length is 64 bits)";
         }
         enum "hex" {
           description "HEX key (default key-length is 64 bits)";
         }
       }
     }
     leaf broadcast-key-refresh-rate {
       description "Broadcast key refresh rate";
       default "0";
       units "minutes";
       type union {
         type string {
           pattern "<.*>|$.*";
         }
         type int32 {
           range "0 .. 86400";
         }
       }
     }
   }
   grouping wpa-version {
     uses apply-advanced;
     choice version {
       case case_1 {
         leaf v1-v2 {
           description "WPA Version 1 and WPA Version 2";
           status deprecated;
           type empty;
         }
       }
       case case_2 {
         leaf v2 {
           description "WPA Version 2";
           type empty;
         }
       }
     }
   }
 }
