/*
 * Copyright (c) 2022 Juniper Networks, Inc.
 * All rights reserved.
 */
 module junos-nfx-rpc-services {
   namespace "http://yang.juniper.net/junos-nfx/rpc/services";

   prefix services;

   import junos-common-ddl-extensions {
     prefix junos;
     revision-date 2022-01-01;
   }

   import junos-common-odl-extensions {
     prefix junos-odl;
     revision-date 2022-01-01;
   }

   import junos-common-types {
     prefix jt;
     revision-date 2022-01-01;
   }

   organization "Juniper Networks, Inc.";

   contact "yang-support@juniper.net";

   description "Junos RPC YANG module for services command(s)";

   revision 2022-01-01 {
     description "Junos: 22.4R1.10";
   }

   rpc get-fwa-statistics {
     description "Show fixed wireless access statistics";
     junos:command "show services fixed-wireless-access statistics";
     output {
       choice output_c {
         case output-tag {
           leaf output {
             type string;
           }
         }
         case actual-tag {
           anyxml fwa-statistics;
         }
         case multichassis-tag {
           anyxml multi-routing-engine-results;
         }
       }
     }
   }
   rpc get-probe-results {
     description "Show probe results";
     junos:command "show services rpm probe-results";
     input {
       leaf owner {
         description "Name of owner";
         type string {
           length "1 .. 32";
         }
       }
       leaf test {
         description "Name of test";
         type string {
           length "1 .. 32";
         }
       }
       leaf source-address {
         description "Filter results based on ipv4 or ipv6 source-address";
         type jt:ipaddr;
       }
       leaf target-address {
         description "Filter results based on ipv4 or ipv6 target-address";
         type jt:ipaddr;
       }
       leaf dst-interface {
         description "Filter results based on destination-interface";
         type union {
           type jt:interface-unit;
           type string {
             pattern "<.*>|$.*";
           }
         }
       }
       leaf status {
         description "Filter based on test status PASS or FAIL";
         type enumeration {
           enum "PASS" {
             description "Dump successful tests";
           }
           enum "FAIL" {
             description "Dump failed tests";
           }
         }
       }
       leaf terse {
         description "Terse output";
         type empty;
       }
       leaf limit {
         description "Dump specified number of results (default is 100)";
         default "100";
         type union {
           type string {
             pattern "<.*>|$.*";
           }
           type uint32 {
             range "1 .. 4294967295";
           }
         }
       }
     }
     output {
       choice output_c {
         case output-tag {
           leaf output {
             type string;
           }
         }
         case actual-tag {
           anyxml probe-results;
         }
         case multichassis-tag {
           anyxml multi-routing-engine-results;
         }
       }
     }
   }
   rpc get-history-results {
     description "Show history results";
     junos:command "show services rpm history-results";
     input {
       leaf verbosity_level {
         default "brief";
         type enumeration {
           enum "brief" {
             description "Display brief output (default)";
           }
           enum "detail" {
             description "Display detailed output";
           }
         }
       }
       leaf owner {
         description "Name of owner";
         type string {
           length "1 .. 32";
         }
         mandatory true;
       }
       leaf test {
         description "Name of test";
         type string {
           length "1 .. 32";
         }
       }
       leaf since {
         description "Show history since YYYY-MM-DD.HH:MM:SS";
         type jt:time;
       }
       leaf source-address {
         description "Filter history based on ipv4 or ipv6 source-address";
         type jt:ipaddr;
       }
       leaf target-address {
         description "Filter history based on ipv4 or ipv6 target-address";
         type jt:ipaddr;
       }
       leaf dst-interface {
         description "Filter based on destination-interface";
         type union {
           type jt:interface-unit;
           type string {
             pattern "<.*>|$.*";
           }
         }
       }
       leaf limit {
         description "Dump specified number of results (default is 100)";
         default "100";
         type union {
           type string {
             pattern "<.*>|$.*";
           }
           type uint32 {
             range "1 .. 4294967295";
           }
         }
       }
     }
     output {
       choice output_c {
         case output-tag {
           leaf output {
             type string;
           }
         }
         case actual-tag {
           anyxml history-results;
         }
         case multichassis-tag {
           anyxml multi-routing-engine-results;
         }
       }
     }
   }
   rpc get-active-servers {
     description "Show configured servers";
     junos:command "show services rpm active-servers";
     output {
       choice output_c {
         case output-tag {
           leaf output {
             type string;
           }
         }
         case actual-tag {
           anyxml active-servers;
         }
         case multichassis-tag {
           anyxml multi-routing-engine-results;
         }
       }
     }
   }
   rpc twamp-information {
     description "Show TWAMP information";
     junos:command "show services rpm twamp";
     output {
       choice output_c {
         case output-tag {
           leaf output {
             type string;
           }
         }
         case multichassis-tag {
           anyxml multi-routing-engine-results;
         }
       }
     }
   }
   rpc twamp-client-information {
     description "Show TWAMP client information";
     junos:command "show services rpm twamp client";
     output {
       choice output_c {
         case output-tag {
           leaf output {
             type string;
           }
         }
         case actual-tag {
           anyxml twamp-client-information;
         }
         case multichassis-tag {
           anyxml multi-routing-engine-results;
         }
       }
     }
   }
   rpc twamp-client-connection-information {
     description "Display connection information";
     junos:command "show services rpm twamp client connection";
     input {
       leaf connection-name {
         description "Control connection name";
         default "all";
         type string;
       }
     }
     output {
       choice output_c {
         case output-tag {
           leaf output {
             type string;
           }
         }
         case multichassis-tag {
           anyxml multi-routing-engine-results;
         }
       }
     }
   }
   rpc twamp-client-test-session {
     description "Display test session information";
     junos:command "show services rpm twamp client session";
     input {
       leaf control-connection {
         description "Control connection name";
         type string {
           length "1 .. 32";
         }
       }
       leaf test-session {
         description "Test session name";
         type string {
           length "1 .. 32";
         }
       }
     }
     output {
       choice output_c {
         case output-tag {
           leaf output {
             type string;
           }
         }
         case multichassis-tag {
           anyxml multi-routing-engine-results;
         }
       }
     }
   }
   rpc twamp-get-probe-results {
     description "Display test session results";
     junos:command "show services rpm twamp client probe-results";
     input {
       leaf control-connection {
         description "Control connection name";
         type string;
       }
       leaf test-session {
         description "Test session name";
         type string;
       }
     }
     output {
       choice output_c {
         case output-tag {
           leaf output {
             type string;
           }
         }
         case actual-tag {
           anyxml probe-results;
         }
         case multichassis-tag {
           anyxml multi-routing-engine-results;
         }
       }
     }
   }
   rpc twamp-get-history-results {
     description "Display test session history results";
     junos:command "show services rpm twamp client history-results";
     input {
       leaf verbosity_level {
         default "brief";
         type enumeration {
           enum "brief" {
             description "Display brief output (default)";
           }
           enum "detail" {
             description "Display detailed output";
           }
         }
       }
       leaf control-connection {
         description "Control connection name";
         type string;
       }
       leaf test-session {
         description "Test session name";
         type string;
       }
       leaf since {
         description "Show history since YYYY-MM-DD.HH:MM:SS";
         type jt:time;
       }
     }
     output {
       choice output_c {
         case output-tag {
           leaf output {
             type string;
           }
         }
         case actual-tag {
           anyxml history-results;
         }
         case multichassis-tag {
           anyxml multi-routing-engine-results;
         }
       }
     }
   }
   rpc twamp-server-information {
     description "Show TWAMP server information";
     junos:command "show services rpm twamp server";
     output {
       choice output_c {
         case output-tag {
           leaf output {
             type string;
           }
         }
         case actual-tag {
           anyxml twamp-server-information;
         }
         case multichassis-tag {
           anyxml multi-routing-engine-results;
         }
       }
     }
   }
   rpc twamp-server-connection-information {
     description "Display connection information";
     junos:command "show services rpm twamp server connection";
     input {
       leaf connection-id {
         description "Connection ID";
         default "all";
         type string;
       }
     }
     output {
       choice output_c {
         case output-tag {
           leaf output {
             type string;
           }
         }
         case multichassis-tag {
           anyxml multi-routing-engine-results;
         }
       }
     }
   }
   rpc twamp-server-session-information {
     description "Display session information";
     junos:command "show services rpm twamp server session";
     input {
       leaf session-id {
         description "Session ID";
         default "all";
         type string;
       }
     }
     output {
       choice output_c {
         case output-tag {
           leaf output {
             type string;
           }
         }
         case multichassis-tag {
           anyxml multi-routing-engine-results;
         }
       }
     }
   }
   rpc get-rfc2544-information {
     description "Show rfc2544 information";
     junos:command "show services rpm rfc2544-benchmarking";
     output {
       choice output_c {
         case output-tag {
           leaf output {
             type string;
           }
         }
         case actual-tag {
           anyxml rfc2544-information;
         }
         case multichassis-tag {
           anyxml multi-routing-engine-results;
         }
       }
     }
   }
   rpc get-test-id-information {
     description "Show rfc2544 test id";
     junos:command "show services rpm rfc2544-benchmarking test-id";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-test-id-information;
         }
         case multichassis-tag {
           anyxml multi-routing-engine-results;
         }
       }
     }
   }
   rpc get-active-tests-information {
     description "Show rfc2544 active tests";
     junos:command "show services rpm rfc2544-benchmarking active-tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-active-tests-information;
         }
         case multichassis-tag {
           anyxml multi-routing-engine-results;
         }
       }
     }
   }
   rpc get-aborted-tests-information {
     description "Show rfc2544 aborted tests";
     junos:command "show services rpm rfc2544-benchmarking aborted-tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-aborted-tests-information;
         }
         case multichassis-tag {
           anyxml multi-routing-engine-results;
         }
       }
     }
   }
   rpc get-completed-tests-information {
     description "Show rfc2544 completed tests";
     junos:command "show services rpm rfc2544-benchmarking completed-tests";
     input {
       leaf verbosity_level {
         default "brief";
         type enumeration {
           enum "brief" {
             description "Display brief output (default)";
           }
           enum "detail" {
             description "Display detailed output";
           }
           enum "extensive" {
             description "Display extensive output";
           }
         }
       }
       leaf test-id {
         description "Test id";
         type union {
           type uint32;
           type string {
             pattern "<.*>|$.*";
           }
         }
       }
     }
     output {
       choice output_c {
         case output-tag {
           leaf output {
             type string;
           }
         }
         case actual-tag {
           anyxml rfc2544-completed-tests-information;
         }
         case multichassis-tag {
           anyxml multi-routing-engine-results;
         }
       }
     }
   }
   rpc get-rfc2544-summary-information {
     description "Show rfc2544 summary";
     junos:command "show services rpm rfc2544-benchmarking summary";
     output {
       choice output_c {
         case output-tag {
           leaf output {
             type string;
           }
         }
         case actual-tag {
           anyxml rfc2544-summary-information;
         }
         case multichassis-tag {
           anyxml multi-routing-engine-results;
         }
       }
     }
   }
   rpc get-pcef-subscribers {
     description "Show subscriber information";
     junos:command "show services pcef subscribers";
     input {
       leaf address {
         description "IPv4 or IPv6 address of subscriber";
         type string;
       }
       leaf interface {
         description "Interface name, or with wildcards (e.g. fe-0/0/*, fe-0/*/*)";
         type union {
           type jt:interface-wildcard;
           type string {
             pattern "<.*>|$.*";
           }
         }
       }
       leaf physical-interface {
         description "Physical Interface name";
         type union {
           type jt:interface-wildcard;
           type string {
             pattern "<.*>|$.*";
           }
         }
       }
       leaf user-name {
         description "Username of subscriber";
         type string;
       }
       leaf logical-system {
         description "Logical system where subscriber resides";
         type string;
       }
       leaf routing-instance {
         description "Routing instance where subscriber resides";
         type string;
       }
       leaf profile-name {
         description "Profile with which subscriber has been activated";
         type string {
           length "1 .. 80";
         }
       }
       leaf agent-circuit-identifier {
         description "Display summary for specified agent circuit identifier";
         type string;
       }
       leaf aci-interface-set-name {
         description "Display summary for specified ACI interface set";
         type string;
       }
       leaf stacked-vlan-id {
         description "Stacked VLAN identifier of subscriber";
         type union {
           type string {
             pattern "<.*>|$.*";
           }
           type uint16 {
             range "0 .. 4094";
           }
         }
       }
       leaf vlan-id {
         description "VLAN identifier of subscriber";
         type union {
           type string {
             pattern "<.*>|$.*";
           }
           type uint16 {
             range "0 .. 4094";
           }
         }
       }
       leaf vpi {
         description "ATM VPI of subscriber";
         type union {
           type string {
             pattern "<.*>|$.*";
           }
           type uint16 {
             range "0 .. 255";
           }
         }
       }
       leaf vci {
         description "ATM VCI of subscriber";
         type union {
           type string {
             pattern "<.*>|$.*";
           }
           type uint16 {
             range "0 .. 65535";
           }
         }
       }
       leaf id {
         description "Identifier of subscriber";
         type string;
       }
       leaf mac-address {
         description "MAC address of subscriber";
         type jt:mac-addr;
       }
       leaf client-type {
         description "Client type of subscriber";
         type enumeration {
           enum "dhcp" {
             description "DHCP clients only";
           }
           enum "vlan" {
             description "VLAN clients only";
           }
           enum "ppp" {
             description "PPP clients only";
           }
           enum "pppoe" {
             description "PPPoE clients only";
           }
           enum "l2tp" {
             description "L2TP clients only";
           }
           enum "static" {
             description "Static clients only";
           }
           enum "vpls-pw" {
             description "VPLS-PW clients only";
           }
           enum "mlppp" {
             description "MLPPP clients only";
           }
           enum "xauth" {
             description "XAuth clients only";
           }
           enum "fwauth" {
             description "FwAuth clients only";
           }
           enum "dot1x" {
             description "Dot1x clients only";
           }
           enum "essm" {
             description "ESSM clients only";
           }
           enum "fwa" {
             description "FWA clients only";
           }
           enum "agf" {
             description "AGF clients only";
           }
         }
       }
       leaf subscriber-state {
         description "State of subscriber";
         type enumeration {
           enum "init" {
             description "INIT state only";
           }
           enum "configured" {
             description "CONFIGURED state only";
           }
           enum "active" {
             description "ACTIVE state only";
           }
           enum "terminating" {
             description "TERMINATING state only";
           }
         }
       }
       leaf display {
         default "terse";
         type enumeration {
           enum "terse" {
             description "Display terse output";
           }
           enum "detail" {
             description "Display detailed output";
           }
           enum "extensive" {
             description "Display extensive output";
           }
           enum "count" {
             description "Display number of subscribers";
           }
         }
       }
     }
     output {
       choice output_c {
         case output-tag {
           leaf output {
             type string;
           }
         }
         case actual-tag {
           anyxml pcef-subscriber;
         }
         case multichassis-tag {
           anyxml multi-routing-engine-results;
         }
       }
     }
   }
   rpc get-pcef-subscribers-summary {
     description "Display pcef subscriber summary";
     junos:command "show services pcef subscribers summary";
     input {
       leaf logical-system {
         description "Display summary for specified logical system";
         type string;
       }
       leaf routing-instance {
         description "Display summary for specified routing instance";
         type string;
       }
       leaf physical-interface {
         description "Physical Interface name";
         type union {
           type jt:interface-wildcard;
           type string {
             pattern "<.*>|$.*";
           }
         }
       }
       leaf port {
         description "Display full subscriber port summary";
         type empty;
       }
       leaf pic {
         description "Display full subscriber pic summary";
         type empty;
       }
       leaf slot {
         description "Display full subscriber slot summary";
         type empty;
       }
       leaf all {
         description "Display full subscriber summary";
         type empty;
       }
     }
     output {
       choice output_c {
         case output-tag {
           leaf output {
             type string;
           }
         }
         case actual-tag {
           anyxml pcef-subscriber;
         }
         case multichassis-tag {
           anyxml multi-routing-engine-results;
         }
       }
     }
   }
   rpc get-pcef-pic {
     description "Show physical interface card information";
     junos:command "show services pcef pic";
     input {
       leaf fpc-slot {
         description "FPC slot number";
         type union {
           type string {
             pattern "<.*>|$.*";
           }
           type uint32;
         }
       }
       leaf pic-slot {
         description "PIC slot number";
         type union {
           type string {
             pattern "<.*>|$.*";
           }
           type uint32;
         }
       }
       leaf display {
         default "terse";
         type enumeration {
           enum "terse" {
             description "Display terse output";
           }
         }
       }
     }
     output {
       choice output_c {
         case output-tag {
           leaf output {
             type string;
           }
         }
         case actual-tag {
           anyxml pcef-pic;
         }
         case multichassis-tag {
           anyxml multi-routing-engine-results;
         }
       }
     }
   }
   rpc get-uac-policies {
     description "Access policies from infranet controller";
     junos:command "show services unified-access-control policies";
     input {
       uses command-forwarding;
       leaf detail {
         description "Display detail output";
         type empty;
       }
       leaf identifier {
         description "Show specified policy information";
         type string;
       }
     }
     output {
       choice output_c {
         case output-tag {
           leaf output {
             type string;
           }
         }
         case actual-tag {
           anyxml uac-policies;
         }
         case multichassis-tag {
           anyxml multi-routing-engine-results;
         }
       }
     }
   }
   rpc get-uac-auth-table {
     description "Show authentication table configured from infranet controller";
     junos:command "show services unified-access-control authentication-table";
     input {
       uses command-forwarding;
       leaf detail {
         description "Display detail output";
         type empty;
       }
       leaf identifier {
         description "Show specified authentication entry";
         type string;
       }
       leaf extended {
         description "Show authentication entries with all roles";
         type empty;
       }
       leaf role {
         description "Show authentication entries matching the role";
         type string;
       }
       leaf ip {
         description "Show authentication entries matching the ip";
         type string;
       }
       leaf user {
         description "Show authentication entries matching the user";
         type string;
       }
     }
     output {
       choice output_c {
         case output-tag {
           leaf output {
             type string;
           }
         }
         case actual-tag {
           anyxml uac-auth-table;
         }
         case multichassis-tag {
           anyxml multi-routing-engine-results;
         }
       }
     }
   }
   rpc get-uac-status {
     description "Show connection status with infranet controller";
     junos:command "show services unified-access-control status";
     output {
       choice output_c {
         case output-tag {
           leaf output {
             type string;
           }
         }
         case actual-tag {
           anyxml uac-status;
         }
         case multichassis-tag {
           anyxml multi-routing-engine-results;
         }
       }
     }
   }
   rpc get-uac-role-entries {
     description "Show list of available roles";
     junos:command "show services unified-access-control roles";
     output {
       choice output_c {
         case output-tag {
           leaf output {
             type string;
           }
         }
         case actual-tag {
           anyxml uac-role-entries;
         }
         case multichassis-tag {
           anyxml multi-routing-engine-results;
         }
       }
     }
   }
   rpc get-uac-counters {
     description "Show unified access control(uac) service related counters";
     junos:command "show services unified-access-control counters";
     output {
       choice output_c {
         case output-tag {
           leaf output {
             type string;
           }
         }
         case actual-tag {
           anyxml uac-counters;
         }
         case multichassis-tag {
           anyxml multi-routing-engine-results;
         }
       }
     }
   }
   rpc get-ift-global-information {
     description "Show inband telemetry information";
     junos:command "show services inband-flow-telemetry global";
     output {
       choice output_c {
         case output-tag {
           leaf output {
             type string;
           }
         }
         case actual-tag {
           anyxml ift-global-information;
         }
         case multichassis-tag {
           anyxml multi-routing-engine-results;
         }
       }
     }
   }
   rpc get-ift-profile-information {
     description "Show inband telemetry profile details";
     junos:command "show services inband-flow-telemetry profile";
     input {
       leaf profile-name {
         description "Name of the profile";
         type string;
       }
     }
     output {
       choice output_c {
         case output-tag {
           leaf output {
             type string;
           }
         }
         case actual-tag {
           anyxml ift-profile-information;
         }
         case multichassis-tag {
           anyxml multi-routing-engine-results;
         }
       }
     }
   }
   rpc get-ift-stats-information {
     description "Show inband telemetry stats information";
     junos:command "show services inband-flow-telemetry stats";
     output {
       choice output_c {
         case output-tag {
           leaf output {
             type string;
           }
         }
         case actual-tag {
           anyxml ift-stats-information;
         }
         case multichassis-tag {
           anyxml multi-routing-engine-results;
         }
       }
     }
   }
   rpc get-nas-statistics-information {
     description "Show N1 message statistics";
     junos:command "show services agf nas statistics";
     output {
       choice output_c {
         case output-tag {
           leaf output {
             type string;
           }
         }
         case actual-tag {
           anyxml nas-statistics-information;
         }
         case multichassis-tag {
           anyxml multi-routing-engine-results;
         }
       }
     }
   }
   rpc get-nas-user-equipment-information {
     description "Show User Equipment information";
     junos:command "show services agf nas user-equipment";
     input {
       choice user_equipment_identifier_choice {
         case ue-id {
           leaf ue-id {
             description "User Equipment identifier";
             type union {
               type uint32;
               type string {
                 pattern "<.*>|$.*";
               }
             }
           }
         }
         case session-id {
           leaf session-id {
             description "User Equipment session identifier";
             type union {
               type uint32;
               type string {
                 pattern "<.*>|$.*";
               }
             }
           }
         }
       }
       leaf level {
         type enumeration {
           enum "brief" {
             description "Display brief information (default)";
           }
           enum "detail" {
             description "Display detailed information";
           }
           enum "extensive" {
             description "Display extensive information";
           }
           enum "summary" {
             description "Display summary information";
           }
         }
       }
     }
     output {
       choice output_c {
         case output-tag {
           leaf output {
             type string;
           }
         }
         case actual-tag {
           anyxml nas-user-equipment-information;
         }
         case multichassis-tag {
           anyxml multi-routing-engine-results;
         }
       }
     }
   }
   rpc get-ngap-amf-information {
     description "Show Access Mobility and Management Function information";
     junos:command "show services agf ngap amf";
     input {
       leaf amf-name {
         description "Configured AMF name";
         type string;
       }
       leaf display {
         type enumeration {
           enum "brief" {
             description "Display brief information (default)";
           }
           enum "detail" {
             description "Display detailed information";
           }
           enum "statistics" {
             description "Display N2 message statistics";
           }
         }
       }
     }
     output {
       choice output_c {
         case output-tag {
           leaf output {
             type string;
           }
         }
         case actual-tag {
           anyxml ngap-amf-information;
         }
         case multichassis-tag {
           anyxml multi-routing-engine-results;
         }
       }
     }
   }
   rpc get-ngap-user-equipment-information {
     description "Show User Equipment information";
     junos:command "show services agf ngap user-equipment";
     input {
       leaf ue-id {
         description "User Equipment identifier";
         type union {
           type uint32;
           type string {
             pattern "<.*>|$.*";
           }
         }
       }
       leaf display {
         type enumeration {
           enum "brief" {
             description "Display brief information (default)";
           }
           enum "detail" {
             description "Display detailed information";
           }
           enum "summary" {
             description "Display summary information";
           }
         }
       }
     }
     output {
       choice output_c {
         case output-tag {
           leaf output {
             type string;
           }
         }
         case actual-tag {
           anyxml ngap-user-equipment-information;
         }
         case multichassis-tag {
           anyxml multi-routing-engine-results;
         }
       }
     }
   }
   rpc get-services-flow-collector-information {
     description "Show flow collector service information";
     junos:command "show services flow-collector";
     input {
       leaf display {
         default "terse";
         type enumeration {
           enum "extensive" {
             description "Display extensive output";
           }
           enum "detail" {
             description "Display detailed output";
           }
           enum "terse" {
             description "Display terse output (default)";
           }
         }
       }
       leaf interface {
         description "Interface name";
         type string;
         mandatory true;
       }
     }
     output {
       choice output_c {
         case output-tag {
           leaf output {
             type string;
           }
         }
         case actual-tag {
           anyxml services-flow-collector-information;
         }
         case multichassis-tag {
           anyxml multi-routing-engine-results;
         }
       }
     }
   }
   rpc get-services-flow-collector-file-information {
     description "Show file status information";
     junos:command "show services flow-collector file";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml services-flow-collector-file-information;
         }
         case multichassis-tag {
           anyxml multi-routing-engine-results;
         }
       }
     }
   }
   rpc get-services-flow-collector-input-information {
     description "Show input status information";
     junos:command "show services flow-collector input";
     input {
       leaf interface {
         description "Interface name";
         type string;
         mandatory true;
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml services-flow-collector-input-information;
         }
         case multichassis-tag {
           anyxml multi-routing-engine-results;
         }
       }
     }
   }
   rpc get-cpcd-pic-statistics {
     description "Show captive portal and content delivery statistics by PIC";
     junos:command "show services captive-portal-content-delivery statistics interface";
     input {
       leaf pic-name {
         type union {
           type jt:interface-name;
           type string {
             pattern "<.*>|$.*";
           }
         }
         mandatory true;
       }
     }
     output {
       choice output_c {
         case output-tag {
           leaf output {
             type string;
           }
         }
         case actual-tag {
           anyxml cpcd-pic-statistics;
         }
         case multichassis-tag {
           anyxml multi-routing-engine-results;
         }
       }
     }
   }
   rpc get-cpcd-profile {
     description "Show profile database";
     junos:command "show services captive-portal-content-delivery profile";
     input {
       leaf profile-name {
         type string;
       }
     }
     output {
       choice output_c {
         case output-tag {
           leaf output {
             type string;
           }
         }
         case actual-tag {
           anyxml cpcd-profile;
         }
         case multichassis-tag {
           anyxml multi-routing-engine-results;
         }
       }
     }
   }
   rpc get-cpcd-rule {
     description "Show rule database";
     junos:command "show services captive-portal-content-delivery rule";
     input {
       leaf rule-name {
         type string;
       }
       leaf term {
         description "Term name";
         type string;
       }
     }
     output {
       choice output_c {
         case output-tag {
           leaf output {
             type string;
           }
         }
         case actual-tag {
           anyxml cpcd-rule;
         }
         case multichassis-tag {
           anyxml multi-routing-engine-results;
         }
       }
     }
   }
   rpc get-cpcd-rule-set {
     description "Show rule set database";
     junos:command "show services captive-portal-content-delivery ruleset";
     input {
       leaf ruleset-name {
         type string;
       }
     }
     output {
       choice output_c {
         case output-tag {
           leaf output {
             type string;
           }
         }
         case actual-tag {
           anyxml cpcd-rule-set;
         }
         case multichassis-tag {
           anyxml multi-routing-engine-results;
         }
       }
     }
   }
   rpc get-cpcd-pic-information {
     description "Show pic database";
     junos:command "show services captive-portal-content-delivery pic";
     input {
       leaf pic-name {
         type union {
           type jt:interface-name;
           type string {
             pattern "<.*>|$.*";
           }
         }
       }
     }
     output {
       choice output_c {
         case output-tag {
           leaf output {
             type string;
           }
         }
         case actual-tag {
           anyxml cpcd-pic-information;
         }
         case multichassis-tag {
           anyxml multi-routing-engine-results;
         }
       }
     }
   }
   rpc get-cpcd-service-set {
     description "Show service set database";
     junos:command "show services captive-portal-content-delivery sset";
     input {
       leaf sset-name {
         type string;
         mandatory true;
       }
       leaf level {
         default "brief";
         type enumeration {
           enum "brief" {
             description "Display brief output (default)";
           }
           enum "detail" {
             description "Display detailed output";
           }
           enum "summary" {
             description "Display summary output";
           }
         }
       }
     }
     output {
       choice output_c {
         case output-tag {
           leaf output {
             type string;
           }
         }
         case actual-tag {
           anyxml cpcd-service-set;
         }
         case multichassis-tag {
           anyxml multi-routing-engine-results;
         }
       }
     }
   }
   rpc get-services-dfc-statistics-information {
     description "Show capture group statistics";
     junos:command "show services dynamic-flow-capture statistics";
     input {
       leaf capture-group {
         description "Capture group name";
         type string;
         mandatory true;
       }
       leaf per-protocol-details {
         description "Shows ipv4 ipv6 also";
         type empty;
       }
     }
     output {
       choice output_c {
         case output-tag {
           leaf output {
             type string;
           }
         }
         case actual-tag {
           anyxml dfc-statistics-information;
         }
         case multichassis-tag {
           anyxml multi-routing-engine-results;
         }
       }
     }
   }
   rpc get-services-dynamic-flow-capture-control-source-information {
     description "Show DFC control source information";
     junos:command "show services dynamic-flow-capture control-source";
     input {
       leaf display {
         default "terse";
         type enumeration {
           enum "detail" {
             description "Display detailed output";
           }
           enum "terse" {
             description "Display terse output (default)";
           }
         }
       }
       leaf capture-group {
         description "Capture group name";
         type string;
         mandatory true;
       }
       leaf source-identifier {
         description "Control source identifier";
         type string;
         mandatory true;
       }
       leaf per-protocol-details {
         description "Shows ipv4 ipv6 also";
         type empty;
       }
     }
     output {
       choice output_c {
         case output-tag {
           leaf output {
             type string;
           }
         }
         case actual-tag {
           anyxml services-dynamic-flow-capture-control-source-information;
         }
         case multichassis-tag {
           anyxml multi-routing-engine-results;
         }
       }
     }
   }
   rpc get-services-dynamic-flow-capture-content-destination-information {
     description "Show DFC content destination information";
     junos:command "show services dynamic-flow-capture content-destination";
     input {
       leaf display {
         default "terse";
         type enumeration {
           enum "terse" {
             description "Display terse output (default)";
           }
         }
       }
       leaf capture-group {
         description "Capture group name";
         type string;
         mandatory true;
       }
       leaf destination-identifier {
         description "Content destination identifier";
         type string;
         mandatory true;
       }
     }
     output {
       choice output_c {
         case output-tag {
           leaf output {
             type string;
           }
         }
         case actual-tag {
           anyxml services-dynamic-flow-capture-content-destination-information;
         }
         case multichassis-tag {
           anyxml multi-routing-engine-results;
         }
       }
     }
   }
   rpc get-dynamic-filtering-statistics {
     description "Show Cloud Connection Status";
     junos:command "show services advanced-anti-malware dynamic-filter status";
     output {
       choice output_c {
         case output-tag {
           leaf output {
             type string;
           }
         }
         case actual-tag {
           anyxml dynamic-filtering-connection-status;
         }
         case multichassis-tag {
           anyxml multi-routing-engine-results;
         }
       }
     }
   }
   rpc get-aamw-statistics {
     description "Show advanced-anti-malware statistics";
     junos:command "show services advanced-anti-malware statistics";
     input {
       uses command-forwarding;
     }
     output {
       choice output_c {
         case output-tag {
           leaf output {
             type string;
           }
         }
         case actual-tag {
           anyxml aamw-statistics;
         }
         case multichassis-tag {
           anyxml multi-routing-engine-results;
         }
       }
     }
   }
   rpc get-aamw-redirect-files {
     description "Show redirect files information";
     junos:command "show services advanced-anti-malware redirect-files";
     input {
       uses command-forwarding;
       leaf file-name {
         description "Show redirect-file content";
         type string;
       }
     }
     output {
       choice output_c {
         case output-tag {
           leaf output {
             type string;
           }
         }
         case actual-tag {
           anyxml aamw-redirect-files;
         }
         case multichassis-tag {
           anyxml multi-routing-engine-results;
         }
       }
     }
   }
   rpc get-aamw-policy {
     description "Show advanced-anti-malware policy";
     junos:command "show services advanced-anti-malware policy";
     input {
       uses command-forwarding;
       leaf policy-name {
         description "Policy name";
         type string;
       }
     }
     output {
       choice output_c {
         case output-tag {
           leaf output {
             type string;
           }
         }
         case actual-tag {
           anyxml aamw-policy;
         }
         case multichassis-tag {
           anyxml multi-routing-engine-results;
         }
       }
     }
   }
   rpc get-aamw-profile {
     description "Show advanced-anti-malware profile";
     junos:command "show services advanced-anti-malware profile";
     input {
       uses command-forwarding;
       leaf profile-name {
         description "Profile name";
         type string;
       }
     }
     output {
       choice output_c {
         case output-tag {
           leaf output {
             type string;
           }
         }
         case actual-tag {
           anyxml aamw-profile;
         }
         case multichassis-tag {
           anyxml multi-routing-engine-results;
         }
       }
     }
   }
   rpc get-aamw-status {
     description "Show advanced-anti-malware status";
     junos:command "show services advanced-anti-malware status";
     output {
       choice output_c {
         case output-tag {
           leaf output {
             type string;
           }
         }
         case actual-tag {
           anyxml aamw-status;
         }
         case multichassis-tag {
           anyxml multi-routing-engine-results;
         }
       }
     }
   }
   rpc get-aamw-version {
     description "Show advanced-anti-malware version";
     junos:command "show services advanced-anti-malware version";
     input {
       uses command-forwarding;
     }
     output {
       choice output_c {
         case output-tag {
           leaf output {
             type string;
           }
         }
         case actual-tag {
           anyxml aamw-version;
         }
         case multichassis-tag {
           anyxml multi-routing-engine-results;
         }
       }
     }
   }
   rpc get-aamw-session-summary {
     description "Show advanced-anti-malware session summary";
     status deprecated;
     junos:command "show services advanced-anti-malware session-summary";
     output {
       choice output_c {
         case output-tag {
           leaf output {
             type string;
           }
         }
         case actual-tag {
           anyxml aamw-session-summary;
         }
         case multichassis-tag {
           anyxml multi-routing-engine-results;
         }
       }
     }
   }
   rpc get-aamw-db-statistics {
     description "Show advanced-anti-malware database-statistics";
     junos:command "show services advanced-anti-malware malware-database-statistics";
     input {
       uses command-forwarding;
     }
     output {
       choice output_c {
         case output-tag {
           leaf output {
             type string;
           }
         }
         case actual-tag {
           anyxml aamw-db-statistics;
         }
         case multichassis-tag {
           anyxml multi-routing-engine-results;
         }
       }
     }
   }
   rpc get-appid-application-signature-detail {
     description "Show application signature details";
     junos:command "show services application-identification application detail";
     input {
       uses command-forwarding;
       leaf application-name {
         type string;
       }
       leaf start {
         description "Show application details from a given position";
         type union {
           type string {
             pattern "<.*>|$.*";
           }
           type uint32 {
             range "1 .. 65535";
           }
         }
       }
       leaf count {
         description "Number of applications to show";
         type union {
           type string {
             pattern "<.*>|$.*";
           }
           type uint32 {
             range "1 .. 65535";
           }
         }
       }
     }
     output {
       choice output_c {
         case output-tag {
           leaf output {
             type string;
           }
         }
         case actual-tag {
           anyxml appid-application-signature-detail;
         }
         case multichassis-tag {
           anyxml multi-routing-engine-results;
         }
       }
     }
   }
   rpc get-appid-application-signature-summary {
     description "Show application signature summary";
     junos:command "show services application-identification application summary";
     output {
       choice output_c {
         case output-tag {
           leaf output {
             type string;
           }
         }
         case actual-tag {
           anyxml appid-application-signature-summary;
         }
         case multichassis-tag {
           anyxml multi-routing-engine-results;
         }
       }
     }
   }
   rpc get-appid-micro-applications-list {
     description "Show micro-applications list";
     junos:command "show services application-identification application micro-applications";
     output {
       choice output_c {
         case output-tag {
           leaf output {
             type string;
           }
         }
         case actual-tag {
           anyxml appid-micro-applications-list;
         }
         case multichassis-tag {
           anyxml multi-routing-engine-results;
         }
       }
     }
   }
   rpc get-appid-non-configurable-application-list {
     description "Show non-configurable application list";
     junos:command "show services application-identification application non-configurable";
     output {
       choice output_c {
         case output-tag {
           leaf output {
             type string;
           }
         }
         case actual-tag {
           anyxml appid-non-configurable-application-list;
         }
         case multichassis-tag {
           anyxml multi-routing-engine-results;
         }
       }
     }
   }
   rpc get-appid-obsolete-application-list {
     description "Show obsolete application list";
     junos:command "show services application-identification application obsolete-applications";
     output {
       choice output_c {
         case output-tag {
           leaf output {
             type string;
           }
         }
         case actual-tag {
           anyxml appid-obsolete-application-list;
         }
         case multichassis-tag {
           anyxml multi-routing-engine-results;
         }
       }
     }
   }
   rpc get-appid-entry-signature-detail {
     description "Show application/group signature details";
     junos:command "show services application-identification entries detail";
     input {
       leaf entry-name {
         type string;
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
     output {
       choice output_c {
         case output-tag {
           leaf output {
             type string;
           }
         }
         case actual-tag {
           anyxml appid-entry-signature-detail;
         }
         case multichassis-tag {
           anyxml multi-routing-engine-results;
         }
       }
     }
   }
   rpc get-appid-entry-signature-filter {
     description "Apply filter on entry details";
     junos:command "show services application-identification entries filter";
     input {
       leaf category {
         description "Filter by entry category";
         type string;
       }
       leaf definition {
         description "Filter by predefined/custom entry";
         type enumeration {
           enum "predefined" {
             description "Predefined app";
           }
           enum "custom" {
             description "Customer defined app";
           }
         }
       }
       leaf entry-name {
         description "Filter by entry name";
         type string;
       }
       leaf risk {
         description "Filter by entry risk";
         type union {
           type string {
             pattern "<.*>|$.*";
           }
           type uint32 {
             range "1 .. 5";
           }
         }
       }
       leaf subcategory {
         description "Filter by entry subcategory";
         type string;
       }
       leaf status {
         description "Filter by entry enabled/disabled";
         type enumeration {
           enum "enabled" {
             description "Application is enabled";
           }
           enum "disabled" {
             description "Application is disabled";
           }
         }
       }
       leaf type {
         description "Filter by application/group entry";
         type enumeration {
           enum "application" {
             description "Application";
           }
           enum "group" {
             description "Group";
           }
         }
       }
       leaf limit {
         description "Limit the number of entries displayed";
         type union {
           type int32;
           type string {
             pattern "<.*>|$.*";
           }
         }
       }
       leaf offset {
         description "Skip number of rows in output";
         type union {
           type int32;
           type string {
             pattern "<.*>|$.*";
           }
         }
       }
     }
     output {
       choice output_c {
         case output-tag {
           leaf output {
             type string;
           }
         }
         case actual-tag {
           anyxml appid-entry-signature-detail;
         }
         case multichassis-tag {
           anyxml multi-routing-engine-results;
         }
       }
     }
   }
   rpc get-appid-entry-category-detail {
     description "List of categories of application available";
     junos:command "show services application-identification entries category-list";
     output {
       choice output_c {
         case output-tag {
           leaf output {
             type string;
           }
         }
         case actual-tag {
           anyxml appid-entry-category-detail;
         }
         case multichassis-tag {
           anyxml multi-routing-engine-results;
         }
       }
     }
   }
   rpc get-appid-entry-subcategory-detail {
     description "List of subcategories of application available";
     junos:command "show services application-identification entries subcategory-list";
     output {
       choice output_c {
         case output-tag {
           leaf output {
             type string;
           }
         }
         case actual-tag {
           anyxml appid-entry-subcategory-detail;
         }
         case multichassis-tag {
           anyxml multi-routing-engine-results;
         }
       }
     }
   }
   rpc get-appid-application-group-detail {
     description "Show application group details";
     junos:command "show services application-identification group detail";
     input {
       uses command-forwarding;
       leaf group-name {
         type string;
       }
     }
     output {
       choice output_c {
         case output-tag {
           leaf output {
             type string;
           }
         }
         case actual-tag {
           anyxml appid-application-group-detail;
         }
         case multichassis-tag {
           anyxml multi-routing-engine-results;
         }
       }
     }
   }
   rpc get-appid-application-group-summary {
     description "Show application group summary";
     junos:command "show services application-identification group summary";
     output {
       choice output_c {
         case output-tag {
           leaf output {
             type string;
           }
         }
         case actual-tag {
           anyxml appid-application-group-summary;
         }
         case multichassis-tag {
           anyxml multi-routing-engine-results;
         }
       }
     }
   }
   rpc get-appid-application-system-cache {
     description "Show application system cache";
     junos:command "show services application-identification application-system-cache";
     input {
       uses command-forwarding;
       choice lsys {
         case logical-system {
         }
         case tenant {
         }
       }
       leaf interface {
         description "Services interface to query";
         type string;
       }
     }
     output {
       choice output_c {
         case output-tag {
           leaf output {
             type string;
           }
         }
         case actual-tag {
           anyxml appid-application-system-cache-information;
         }
         case multichassis-tag {
           anyxml multi-routing-engine-results;
         }
       }
     }
   }
   rpc get-appid-counter {
     description "Show the application identification counters";
     junos:command "show services application-identification counter";
     input {
       uses command-forwarding;
       choice lsys {
         case logical-system {
         }
         case tenant {
         }
       }
       leaf interface {
         description "Services interface to query";
         type string;
       }
     }
     output {
       choice output_c {
         case output-tag {
           leaf output {
             type string;
           }
         }
         case actual-tag {
           anyxml appid-counter-information;
         }
         case multichassis-tag {
           anyxml multi-routing-engine-results;
         }
       }
     }
   }
   rpc get-appid-counter-encrypted {
     description "Counters for SSL encrypted sessions";
     status deprecated;
     junos:command "show services application-identification counter ssl-encrypted-sessions";
     output {
       choice output_c {
         case output-tag {
           leaf output {
             type string;
           }
         }
         case actual-tag {
           anyxml appid-counter-information;
         }
         case multichassis-tag {
           anyxml multi-routing-engine-results;
         }
       }
     }
   }
   rpc get-commit-status {
     description "Show config commit status";
     junos:command "show services application-identification commit-status";
     output {
       choice output_c {
         case output-tag {
           leaf output {
             type string;
           }
         }
         case actual-tag {
           anyxml appid-commit-status;
         }
         case multichassis-tag {
           anyxml multi-routing-engine-results;
         }
       }
     }
   }
   rpc get-appid-application-statistics {
     description "Show the application statistics";
     junos:command "show services application-identification statistics applications";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
     output {
       choice output_c {
         case output-tag {
           leaf output {
             type string;
           }
         }
         case actual-tag {
           anyxml appid-application-statistics-information;
         }
         case multichassis-tag {
           anyxml multi-routing-engine-results;
         }
       }
     }
   }
   rpc get-appid-application-statistics-detail {
     description "Show the application statistics detail";
     junos:command "show services application-identification statistics applications detail";
     input {
       uses command-forwarding;
       choice lsys {
         case logical-system {
         }
         case tenant {
         }
       }
       leaf interval {
         description "Displays current interval application statistics irrespective of interval";
         default "1";
         type union {
           type string {
             pattern "<.*>|$.*";
           }
           type uint32 {
             range 1;
           }
         }
       }
     }
     output {
       choice output_c {
         case output-tag {
           leaf output {
             type string;
           }
         }
         case actual-tag {
           anyxml appid-application-statistics-detail;
         }
         case multichassis-tag {
           anyxml multi-routing-engine-results;
         }
       }
     }
   }
   rpc get-appid-application-group-statistics {
     description "Show the application group statistics";
     junos:command "show services application-identification statistics application-groups";
     input {
       uses command-forwarding;
       choice lsys {
         case logical-system {
         }
         case tenant {
         }
       }
       leaf interval {
         description "Displays current interval application group statistics irrespective of interval";
         default "1";
         type union {
           type string {
             pattern "<.*>|$.*";
           }
           type uint32 {
             range 1;
           }
         }
       }
     }
     output {
       choice output_c {
         case output-tag {
           leaf output {
             type string;
           }
         }
         case actual-tag {
           anyxml appid-application-group-statistics-information;
         }
         case multichassis-tag {
           anyxml multi-routing-engine-results;
         }
       }
     }
   }
   rpc get-application-id-status-information {
     description "Show the application identification status";
     junos:command "show services application-identification status";
     output {
       choice output_c {
         case output-tag {
           leaf output {
             type string;
           }
         }
         case actual-tag {
           anyxml appid-status-information;
         }
         case multichassis-tag {
           anyxml multi-routing-engine-results;
         }
       }
     }
   }
   rpc get-appid-package-version {
     description "Show the current application package version";
     junos:command "show services application-identification version";
     output {
       choice output_c {
         case output-tag {
           leaf output {
             type string;
           }
         }
         case actual-tag {
           anyxml appid-package-version;
         }
         case multichassis-tag {
           anyxml multi-routing-engine-results;
         }
       }
     }
   }
   rpc get-appid-pkt-capture-counter {
     description "Show the application identification packet capture counters";
     junos:command "show services application-identification packet-capture counters";
     output {
       choice output_c {
         case output-tag {
           leaf output {
             type string;
           }
         }
         case actual-tag {
           anyxml appid-pkt-capture-counter-information;
         }
         case multichassis-tag {
           anyxml multi-routing-engine-results;
         }
       }
     }
   }
   rpc get-recent-appid-sigpack-information {
     description "Show the recent application package versions";
     junos:command "show services application-identification recent-appid-sigpack-versions";
     output {
       choice output_c {
         case output-tag {
           leaf output {
             type string;
           }
         }
         case actual-tag {
           anyxml recent-appid-sigpack-information;
         }
         case multichassis-tag {
           anyxml multi-routing-engine-results;
         }
       }
     }
   }
   rpc get-ssl-statistics {
     description "Show ssl proxy statistics";
     junos:command "show services ssl proxy statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-statistics;
         }
         case multichassis-tag {
           anyxml multi-routing-engine-results;
         }
       }
     }
   }
   rpc get-ssl-status {
     description "Show ssl proxy status";
     junos:command "show services ssl proxy status";
     input {
       uses command-forwarding;
       leaf pic-info {
         description "PIC ID";
         type string;
       }
     }
     output {
       choice output_c {
         case output-tag {
           leaf output {
             type string;
           }
         }
         case actual-tag {
           anyxml ssl-status;
         }
         case multichassis-tag {
           anyxml multi-routing-engine-results;
         }
       }
     }
   }
   rpc get-ssl-counters {
     description "Show all ssl proxy counters";
     junos:command "show services ssl proxy counters all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-ssl-error-counters {
     description "Show ssl proxy error counters";
     junos:command "show services ssl proxy counters errors";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-ssl-info-counters {
     description "Show ssl proxy info counters";
     junos:command "show services ssl proxy counters info";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-ssl-proxy-profile-all {
     description "Show all ssl proxy profiles";
     junos:command "show services ssl proxy profile all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-profile-list;
         }
         case multichassis-tag {
           anyxml multi-routing-engine-results;
         }
       }
     }
   }
   rpc get-ssl-proxy-profile-detail {
     description "Show profile information matching the given profile name";
     junos:command "show services ssl proxy profile profile-name";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf profile-name {
         description "Ssl proxy profile name";
         type string;
         mandatory true;
       }
     }
     output {
       choice output_c {
         case output-tag {
           leaf output {
             type string;
           }
         }
         case actual-tag {
           anyxml ssl-profile-detail;
         }
         case multichassis-tag {
           anyxml multi-routing-engine-results;
         }
       }
     }
   }
   rpc get-ssl-proxy-session-cache-entries-summary {
     description "Show summary of session cache entries";
     junos:command "show services ssl proxy session-cache entries summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-sess-cache-entries;
         }
         case multichassis-tag {
           anyxml multi-routing-engine-results;
         }
       }
     }
   }
   rpc get-ssl-proxy-session-cache-entries-detail {
     description "Show detailed output of session cache entries";
     junos:command "show services ssl proxy session-cache entries detail";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-sess-cache-entries;
         }
         case multichassis-tag {
           anyxml multi-routing-engine-results;
         }
       }
     }
   }
   rpc get-ssl-proxy-session-cache-statistics {
     description "Show session cache statistics";
     junos:command "show services ssl proxy session-cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-sess-cache-statistics;
         }
         case multichassis-tag {
           anyxml multi-routing-engine-results;
         }
       }
     }
   }
   rpc get-ssl-proxy-certificate-cache-entries-summary {
     description "Show summary of certificate cache entries";
     junos:command "show services ssl proxy certificate-cache entries summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-cert-cache-entries;
         }
         case multichassis-tag {
           anyxml multi-routing-engine-results;
         }
       }
     }
   }
   rpc get-ssl-proxy-certificate-cache-entries-detail {
     description "Show detailed output of certificate cache entries";
     junos:command "show services ssl proxy certificate-cache entries detail";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-cert-cache-entries;
         }
         case multichassis-tag {
           anyxml multi-routing-engine-results;
         }
       }
     }
   }
   rpc get-ssl-proxy-cert-cache-statistics {
     description "Show certificate cache statistics";
     junos:command "show services ssl proxy certificate-cache statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-proxy-cert-cache-statistics;
         }
         case multichassis-tag {
           anyxml multi-routing-engine-results;
         }
       }
     }
   }
   rpc get-ssl-certificate-all {
     description "Show all ssl certificates";
     junos:command "show services ssl certificate all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-certificate;
         }
         case multichassis-tag {
           anyxml multi-routing-engine-results;
         }
       }
     }
   }
   rpc get-ssl-certificate-id-brief {
     description "Show brief information about certificate id";
     junos:command "show services ssl certificate brief";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       choice output_c {
         case output-tag {
           leaf output {
             type string;
           }
         }
         case actual-tag {
           anyxml ssl-certificate-id-detail;
         }
         case multichassis-tag {
           anyxml multi-routing-engine-results;
         }
       }
     }
   }
   rpc get-ssl-certificate-id-detail {
     description "Show detail information about certificate id";
     junos:command "show services ssl certificate detail";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf certificate-id {
         description "Certificate ID";
         type string;
       }
     }
     output {
       choice output_c {
         case output-tag {
           leaf output {
             type string;
           }
         }
         case actual-tag {
           anyxml ssl-certificate-id-detail;
         }
         case multichassis-tag {
           anyxml multi-routing-engine-results;
         }
       }
     }
   }
   rpc get-terminator-counters {
     description "Show all ssl terminator counters";
     junos:command "show services ssl termination counters all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-terminator-error-counters {
     description "Show ssl terminator error counters";
     junos:command "show services ssl termination counters errors";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-terminator-handshake-counters {
     description "Show ssl terminator handshake counters";
     junos:command "show services ssl termination counters handshake";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-ssl-terminator-profile-all {
     description "Show all ssl terminator profiles";
     junos:command "show services ssl termination profile all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-profile-list;
         }
         case multichassis-tag {
           anyxml multi-routing-engine-results;
         }
       }
     }
   }
   rpc get-ssl-terminator-profile-brief {
     description "Terminator profile name";
     junos:command "show services ssl termination profile brief profile-name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       choice output_c {
         case output-tag {
           leaf output {
             type string;
           }
         }
         case actual-tag {
           anyxml ssl-term-profile-detail;
         }
         case multichassis-tag {
           anyxml multi-routing-engine-results;
         }
       }
     }
   }
   rpc get-ssl-terminator-profile-detail {
     description "Terminator profile name";
     junos:command "show services ssl termination profile detail profile-name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Terminator profile name";
         type string;
       }
     }
     output {
       choice output_c {
         case output-tag {
           leaf output {
             type string;
           }
         }
         case actual-tag {
           anyxml ssl-term-profile-detail;
         }
         case multichassis-tag {
           anyxml multi-routing-engine-results;
         }
       }
     }
   }
   rpc get-initiator-counters {
     description "Show all ssl initiator counters";
     junos:command "show services ssl initiation counters all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-initiator-error-counters {
     description "Show ssl initiator error counters";
     junos:command "show services ssl initiation counters errors";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-initiator-handshake-counters {
     description "Show ssl initiator handshake counters";
     junos:command "show services ssl initiation counters handshake";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-counters;
         }
         case multichassis-tag {
           anyxml multi-routing-engine-results;
         }
       }
     }
   }
   rpc get-ssl-initiator-profile-all {
     description "Show all ssl initiator profiles";
     junos:command "show services ssl initiation profile all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-profile-list;
         }
         case multichassis-tag {
           anyxml multi-routing-engine-results;
         }
       }
     }
   }
   rpc get-ssl-initiator-profile-brief {
     description "Initiator profile name";
     junos:command "show services ssl initiation profile brief profile-name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       choice output_c {
         case output-tag {
           leaf output {
             type string;
           }
         }
         case actual-tag {
           anyxml ssl-term-profile-detail;
         }
         case multichassis-tag {
           anyxml multi-routing-engine-results;
         }
       }
     }
   }
   rpc get-ssl-initiator-profile-detail {
     description "Initiator profile name";
     junos:command "show services ssl initiation profile detail profile-name";
     input {
       uses command-forwarding;
       leaf pic-info {
         description "PIC ID";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf profile_name {
         description "Initiator profile name";
         type string;
       }
     }
     output {
       choice output_c {
         case output-tag {
           leaf output {
             type string;
           }
         }
         case actual-tag {
           anyxml ssl-term-profile-detail;
         }
         case multichassis-tag {
           anyxml multi-routing-engine-results;
         }
       }
     }
   }
   rpc get-ssl-session {
     description "Show ssl session details";
     junos:command "show services ssl session";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
       leaf flow_session_id {
         description "Flow session id";
         type string;
         mandatory true;
       }
     }
     output {
       choice output_c {
         case output-tag {
           leaf output {
             type string;
           }
         }
         case actual-tag {
           anyxml ssl-session;
         }
         case multichassis-tag {
           anyxml multi-routing-engine-results;
         }
       }
     }
   }
   rpc get-ssl-droplogs {
     description "Show ssl droplogs";
     junos:command "show services ssl droplogs";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf pic-info {
         description "PIC ID";
         type string;
       }
     }
     output {
       choice output_c {
         case output-tag {
           leaf output {
             type string;
           }
         }
         case actual-tag {
           anyxml ssl-droplog;
         }
         case multichassis-tag {
           anyxml multi-routing-engine-results;
         }
       }
     }
   }
   rpc get-icap-redir-statistics {
     description "Show ICAP redirect service statistics";
     junos:command "show services icap-redirect statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml icap-redir-statistics;
         }
         case multichassis-tag {
           anyxml multi-routing-engine-results;
         }
       }
     }
   }
   rpc get-icap-redir-status {
     description "Show ICAP redirect profile status";
     junos:command "show services icap-redirect status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml icap-redir-status;
         }
         case multichassis-tag {
           anyxml multi-routing-engine-results;
         }
       }
     }
   }
   rpc get-services-screen-ids-whitelist {
     description "Show white list data";
     junos:command "show services screen whitelist";
     input {
       uses command-forwarding;
       leaf wlist-name {
         description "White list name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml show-ids-whitelist;
         }
         case multichassis-tag {
           anyxml multi-routing-engine-results;
         }
       }
     }
   }
   rpc get-services-screen-ids-status {
     description "Show status of screen object";
     junos:command "show services screen ids-option";
     input {
       uses command-forwarding;
       leaf screen-name {
         description "Screen name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml show-ids-status;
         }
         case multichassis-tag {
           anyxml multi-routing-engine-results;
         }
       }
     }
   }
   rpc get-services-ids-statistics {
     description "Show screen attack statistics information";
     junos:command "show services screen statistics";
     input {
       uses command-forwarding;
       choice filter {
         case service-set {
           leaf service-set {
             description "IDS statistics service-set";
             type string;
           }
         }
         case interface {
           leaf interface {
             description "IDS statistics interface";
             type string;
           }
         }
       }
       leaf ip {
         description "IDS statistics ip";
         type enumeration {
           enum "tunnel" {
             description "IDS statistics ip tunnel";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml ids-statistics;
         }
         case multichassis-tag {
           anyxml multi-routing-engine-results;
         }
       }
     }
   }
   rpc get-screen-drops {
     description "Show screen ids packet drop statistics";
     junos:command "show services service-sets statistics screen-drops";
     input {
       uses command-forwarding;
       choice filter {
         case service-set {
           leaf service-set {
             description "IDS statistics service-set";
             type string;
           }
         }
         case interface {
           leaf interface {
             description "IDS statistics interface";
             type string;
           }
         }
       }
     }
     output {
       choice output_c {
         case output-tag {
           leaf output {
             type string;
           }
         }
         case actual-tag {
           anyxml screen-drops;
         }
         case multichassis-tag {
           anyxml multi-routing-engine-results;
         }
       }
     }
   }
   rpc get-screen-session-limit-counters {
     description "Show service set screen session limit counters";
     junos:command "show services service-sets statistics screen-session-limit-counters";
     input {
       uses command-forwarding;
       choice filter {
         case service-set {
           leaf service-set {
             description "IDS statistics service-set";
             type string;
           }
         }
         case interface {
           leaf interface {
             description "IDS statistics interface";
             type string;
           }
         }
       }
     }
     output {
       choice output_c {
         case output-tag {
           leaf output {
             type string;
           }
         }
         case actual-tag {
           anyxml screen-session-limit-counters;
         }
         case multichassis-tag {
           anyxml multi-routing-engine-results;
         }
       }
     }
   }
   rpc get-service-set-packet-drop-statistics {
     description "Show service set packet drop statistics";
     junos:command "show services service-sets statistics packet-drops";
     input {
       leaf interface {
         description "Name of adaptive services interface";
         type string;
       }
     }
     output {
       choice output_c {
         case output-tag {
           leaf output {
             type string;
           }
         }
         case actual-tag {
           anyxml service-set-packet-drop-statistics;
         }
         case multichassis-tag {
           anyxml multi-routing-engine-results;
         }
       }
     }
   }
   rpc get-service-set-drop-flow-statistics {
     description "Show drop flow stats";
     junos:command "show services service-sets statistics drop-flow-limit";
     input {
       leaf interface {
         description "Name of adaptive services interface";
         type string;
       }
     }
     output {
       choice output_c {
         case output-tag {
           leaf output {
             type string;
           }
         }
         case actual-tag {
           anyxml service-set-drop-flow-statistics;
         }
         case multichassis-tag {
           anyxml multi-routing-engine-results;
         }
       }
     }
   }
   rpc get-service-set-integrity-drops-statistics {
     description "Show header integrity drops";
     junos:command "show services service-sets statistics integrity-drops";
     input {
       leaf service-set {
         description "Name of service set";
         type string;
       }
       leaf interface {
         description "Name of adaptive services interface";
         type string;
       }
     }
     output {
       choice output_c {
         case output-tag {
           leaf output {
             type string;
           }
         }
         case actual-tag {
           anyxml service-set-integrity-drops-statistics;
         }
         case multichassis-tag {
           anyxml multi-routing-engine-results;
         }
       }
     }
   }
   rpc get-service-set-tcp-tracker-statistics {
     description "Show tcp tracker statistics";
     junos:command "show services service-sets statistics tcp";
     input {
       leaf service-set {
         description "Name of service set";
         type string;
       }
       leaf interface {
         description "Name of adaptive services interface";
         type string;
       }
     }
     output {
       choice output_c {
         case output-tag {
           leaf output {
             type string;
           }
         }
         case actual-tag {
           anyxml msp-service-set-tcp-statistics;
         }
         case multichassis-tag {
           anyxml multi-routing-engine-results;
         }
       }
     }
   }
   rpc get-service-set-tcp-mss-statistics {
     description "Show service set TCP MSS statistics";
     junos:command "show services service-sets statistics tcp-mss";
     input {
       leaf interface {
         description "Name of adaptive services interface";
         type string;
       }
     }
     output {
       choice output_c {
         case output-tag {
           leaf output {
             type string;
           }
         }
         case actual-tag {
           anyxml service-set-tcp-mss-statistics;
         }
         case multichassis-tag {
           anyxml multi-routing-engine-results;
         }
       }
     }
   }
   rpc get-service-set-syslog-statistics {
     description "Show service set syslog statistics";
     junos:command "show services service-sets statistics syslog";
     input {
       leaf host {
         description "Syslog host address";
         type string;
       }
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml syslog-stats-interface;
         }
         case multichassis-tag {
           anyxml multi-routing-engine-results;
         }
       }
     }
   }
   rpc get-service-set-jflow-log-statistics {
     description "Show service set jflow-log statistics";
     junos:command "show services service-sets statistics jflow-log";
     input {
       leaf service-set {
         description "Name of service set";
         type string;
       }
       leaf interface {
         description "Name of adaptive services interface";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml jflow-log-stats-interface;
         }
         case multichassis-tag {
           anyxml multi-routing-engine-results;
         }
       }
     }
   }
   rpc get-service-set-ids-drops-statistics {
     description "Show service set IDS drops statistics";
     junos:command "show services service-sets statistics ids drops";
     input {
       leaf service-set {
         description "Name of service set";
         type string;
       }
       leaf interface {
         description "Name of adaptive services interface";
         type string;
       }
     }
     output {
       choice output_c {
         case output-tag {
           leaf output {
             type string;
           }
         }
         case actual-tag {
           anyxml msp-service-set-ids-drops-statistics;
         }
         case multichassis-tag {
           anyxml multi-routing-engine-results;
         }
       }
     }
   }
   rpc get-ids-session-limits-counters-statistics {
     description "Show the session-limits counters";
     junos:command "show services service-sets statistics ids session-limits counters";
     input {
       leaf service-set {
         description "Name of service set";
         type string;
       }
       leaf interface {
         description "Name of adaptive services interface";
         type string;
       }
     }
     output {
       choice output_c {
         case output-tag {
           leaf output {
             type string;
           }
         }
         case actual-tag {
           anyxml ids-session-limits-counters-statistics;
         }
         case multichassis-tag {
           anyxml multi-routing-engine-results;
         }
       }
     }
   }
   rpc get-service-set-memory-statistics {
     description "Show service interface memory utilization";
     junos:command "show services service-sets memory-usage";
     input {
       leaf service-set {
         description "Name of service set";
         type string;
       }
       leaf interface {
         description "Name of adaptive services interface";
         type string;
       }
     }
     output {
       choice output_c {
         case output-tag {
           leaf output {
             type string;
           }
         }
         case actual-tag {
           anyxml service-set-memory-statistics-information;
         }
         case multichassis-tag {
           anyxml multi-routing-engine-results;
         }
       }
     }
   }
   rpc get-service-set-cpu-statistics {
     description "Show service interface CPU utilization as a percentage";
     junos:command "show services service-sets cpu-usage";
     input {
       leaf service-set {
         description "Name of service set";
         type string;
       }
       leaf interface {
         description "Name of adaptive services interface";
         type string;
       }
     }
     output {
       choice output_c {
         case output-tag {
           leaf output {
             type string;
           }
         }
         case actual-tag {
           anyxml service-set-cpu-statistics-information;
         }
         case multichassis-tag {
           anyxml multi-routing-engine-results;
         }
       }
     }
   }
   rpc get-service-set-summary-information {
     description "Show service set summary information";
     junos:command "show services service-sets summary";
     input {
       leaf interface {
         description "Name of adaptive services interface";
         type string;
       }
     }
     output {
       choice output_c {
         case output-tag {
           leaf output {
             type string;
           }
         }
         case actual-tag {
           anyxml service-set-summary-information;
         }
         case multichassis-tag {
           anyxml multi-routing-engine-results;
         }
       }
     }
   }
   rpc get-service-set-plugin-summary {
     description "Show service set plugins summary";
     junos:command "show services service-sets plug-ins";
     input {
       leaf interface {
         description "Name of extension provider interface";
         type string;
       }
     }
     output {
       choice output_c {
         case output-tag {
           leaf output {
             type string;
           }
         }
         case actual-tag {
           anyxml service-set-plugin-summary;
         }
         case multichassis-tag {
           anyxml multi-routing-engine-results;
         }
       }
     }
   }
   rpc retrieve-srv-source-nat-pool-information {
     description "Show source NAT information of this pool";
     junos:command "show services nat source pool";
     input {
       uses command-forwarding;
       choice pool-choice {
         case pool-name {
           leaf pool-name {
             description "Source address pool name";
             type string;
             mandatory true;
           }
         }
         case all {
           leaf all {
             description "Display all source NAT pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-pool-information;
         }
         case multichassis-tag {
           anyxml multi-routing-engine-results;
         }
       }
     }
   }
   rpc get-serv-src-nat-port-block {
     description "Show port block allocation information";
     junos:command "show services nat source port-block";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-port-block;
         }
         case multichassis-tag {
           anyxml multi-routing-engine-results;
         }
       }
     }
   }
   rpc get-serv-det-nat {
     description "Show deterministic port block allocation information";
     junos:command "show services nat source deterministic";
     input {
       uses command-forwarding;
       leaf pool {
         description "Source NAT pool name";
         type string;
       }
       choice ip-choice {
         case host-ip {
           leaf host-ip {
             description "Internal host IP address";
             type jt:ipaddr;
           }
         }
         case xlated-ip {
           leaf xlated-ip {
             description "Xlated IP address";
             type jt:ipaddr;
           }
         }
       }
       leaf xlated-port {
         description "Translated port";
         type union {
           type uint16;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-deterministic;
         }
         case multichassis-tag {
           anyxml multi-routing-engine-results;
         }
       }
     }
   }
   rpc get-serv-det-nat-host-sddr-range {
     description "Show deterministic host address range without overlap";
     junos:command "show services nat source deterministic host-address-range";
     input {
       uses command-forwarding;
       leaf pool {
         description "Source NAT pool name";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-det-host-sddr-range;
         }
         case multichassis-tag {
           anyxml multi-routing-engine-results;
         }
       }
     }
   }
   rpc get-srv-source-nat-rule-sets-information {
     description "Show source NAT rule-set information";
     junos:command "show services nat source rule";
     input {
       uses command-forwarding;
       choice rule-choice {
         case rule-name {
           leaf rule-name {
             description "Source NAT rule name";
             type string {
               length "1 .. 64";
             }
             mandatory true;
           }
         }
         case all {
           leaf all {
             description "Display all source NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-rule-sets-information;
         }
         case multichassis-tag {
           anyxml multi-routing-engine-results;
         }
       }
     }
   }
   rpc get-srv-source-nat-rule-app-information {
     description "Show source NAT rule application information";
     junos:command "show services nat source rule-application";
     input {
       uses command-forwarding;
       choice rule-choice {
         case rule-name {
           leaf rule-name {
             description "Source NAT rule name";
             type string {
               length "1 .. 64";
             }
             mandatory true;
           }
         }
         case all {
           leaf all {
             description "Display all source NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-rule-application-information;
         }
         case multichassis-tag {
           anyxml multi-routing-engine-results;
         }
       }
     }
   }
   rpc retrieve-srv-source-nat-summary {
     description "Show source NAT summary information";
     junos:command "show services nat source summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml source-nat-summary;
         }
         case multichassis-tag {
           anyxml multi-routing-engine-results;
         }
       }
     }
   }
   rpc get-nat-endpoint-independent-mapping {
     description "Show NAT Endpoint Independent mapping";
     junos:command "show services nat source mappings endpoint-independent";
     input {
       uses command-forwarding;
       leaf private {
         description "Private IP/IPv6 prefix to use as filter";
         type string;
       }
       leaf public {
         description "Public IP prefix to use as filter";
         type string;
       }
       leaf pool-name {
         description "Name of pool";
         type string;
       }
     }
     output {
       choice output_c {
         case output-tag {
           leaf output {
             type string;
           }
         }
         case actual-tag {
           anyxml nat-endpoint-independent-mapping-information;
         }
         case multichassis-tag {
           anyxml multi-routing-engine-results;
         }
       }
     }
   }
   rpc get-nat-app-mapping {
     description "Show NAT address pooling paired mapping";
     junos:command "show services nat source mappings address-pooling-paired";
     input {
       uses command-forwarding;
       leaf private {
         description "Private IP/IPv6 prefix to use as filter";
         type string;
       }
       leaf public {
         description "Public IP prefix to use as filter";
         type string;
       }
       leaf pool-name {
         description "Name of pool";
         type string;
       }
     }
     output {
       choice output_c {
         case output-tag {
           leaf output {
             type string;
           }
         }
         case actual-tag {
           anyxml nat-app-mapping-information;
         }
         case multichassis-tag {
           anyxml multi-routing-engine-results;
         }
       }
     }
   }
   rpc get-nat-mapping-pcp {
     description "Show NAT PCP mapping";
     junos:command "show services nat source mappings pcp";
     output {
       choice output_c {
         case output-tag {
           leaf output {
             type string;
           }
         }
         case actual-tag {
           anyxml nat-mapping-pcp-information;
         }
         case multichassis-tag {
           anyxml multi-routing-engine-results;
         }
       }
     }
   }
   rpc get-nat-mapping {
     description "Show NAT mapping";
     junos:command "show services nat source mappings detail";
     input {
       uses command-forwarding;
       leaf pool-name {
         description "Name of pool";
         type string;
       }
     }
     output {
       choice output_c {
         case output-tag {
           leaf output {
             type string;
           }
         }
         case actual-tag {
           anyxml nat-mapping-information;
         }
         case multichassis-tag {
           anyxml multi-routing-engine-results;
         }
       }
     }
   }
   rpc get-nat-mapping-summary {
     description "Show NAT mapping entries count";
     junos:command "show services nat source mappings summary";
     output {
       choice output_c {
         case output-tag {
           leaf output {
             type string;
           }
         }
         case actual-tag {
           anyxml nat-mapping-summary;
         }
         case multichassis-tag {
           anyxml multi-routing-engine-results;
         }
       }
     }
   }
   rpc get-srv-dst-nat-pool-information {
     description "Show destination NAT address-pool information";
     junos:command "show services nat destination pool";
     input {
       uses command-forwarding;
       choice pool-choice {
         case pool-name {
           leaf pool-name {
             description "Destination address pool name";
             type string {
               length "1 .. 64";
             }
             mandatory true;
           }
         }
         case all {
           leaf all {
             description "Display all destination NAT address-pool information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-pool-information;
         }
         case multichassis-tag {
           anyxml multi-routing-engine-results;
         }
       }
     }
   }
   rpc get-srv-dst-nat-rule-sets-information {
     description "Show destination NAT rule-set information";
     junos:command "show services nat destination rule";
     input {
       uses command-forwarding;
       choice rule-choice {
         case rule-name {
           leaf rule-name {
             description "Destination NAT rule name";
             type string {
               length "1 .. 64";
             }
             mandatory true;
           }
         }
         case all {
           leaf all {
             description "Display all destination NAT rule-sets information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-rule-sets;
         }
         case multichassis-tag {
           anyxml multi-routing-engine-results;
         }
       }
     }
   }
   rpc get-srv-dst-nat-rule-app-information {
     description "Show destination NAT rule application information";
     junos:command "show services nat destination rule-application";
     input {
       uses command-forwarding;
       choice rule-choice {
         case rule-name {
           leaf rule-name {
             description "Destination NAT rule name";
             type string {
               length "1 .. 64";
             }
             mandatory true;
           }
         }
         case all {
           leaf all {
             description "Display all destination NAT rule with application configured information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-rule-application-information;
         }
         case multichassis-tag {
           anyxml multi-routing-engine-results;
         }
       }
     }
   }
   rpc retrieve-srv-dst-nat-summary-information {
     description "Show destination NAT summary information";
     junos:command "show services nat destination summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml destination-nat-summary-information;
         }
         case multichassis-tag {
           anyxml multi-routing-engine-results;
         }
       }
     }
   }
   rpc retrieve-srv-source-nat-pool-resource-usage {
     description "Show source pool resource usage information";
     junos:command "show services nat resource-usage source-pool";
     input {
       uses command-forwarding;
       choice pool-choice {
         case pool-name {
           leaf pool-name {
             description "Source address pool name";
             type string;
             mandatory true;
           }
         }
         case all {
           leaf all {
             description "Display all source NAT pool resource usage";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml source-nat-pool-resource-usage;
         }
         case multichassis-tag {
           anyxml multi-routing-engine-results;
         }
       }
     }
   }
   rpc get-srv-static-nat-rule-information {
     description "Show static NAT rule information";
     junos:command "show services nat static rule";
     input {
       uses command-forwarding;
       choice rule-choice {
         case rule-name {
           leaf rule-name {
             description "Static NAT rule name";
             type string {
               length "1 .. 64";
             }
             mandatory true;
           }
         }
         case all {
           leaf all {
             description "Display all static NAT rule information";
             type empty;
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
     }
     output {
       choice output_c {
         case output-tag {
           leaf output {
             type string;
           }
         }
         case actual-tag {
           anyxml static-nat-rule-information;
         }
         case multichassis-tag {
           anyxml multi-routing-engine-results;
         }
       }
     }
   }
   rpc get-service-nat-pool-information {
     description "Show NAT pools information";
     junos:command "show services nat pool";
     input {
       leaf pool-name {
         description "Name of pool";
         type string;
       }
       leaf display {
         default "brief";
         type enumeration {
           enum "brief" {
             description "Display brief output (default)";
           }
           enum "detail" {
             description "Display detailed output";
           }
         }
       }
     }
     output {
       choice output_c {
         case output-tag {
           leaf output {
             type string;
           }
         }
         case actual-tag {
           anyxml service-nat-pool-information;
         }
         case multichassis-tag {
           anyxml multi-routing-engine-results;
         }
       }
     }
   }
   rpc get-service-detnat-information {
     description "Show deterministic NAT internal-host information";
     junos:command "show services nat deterministic-nat internal-host";
     input {
       leaf nat-address {
         description "NAT address";
         type string;
         mandatory true;
       }
       leaf nat-port {
         description "NAT port";
         type string;
         mandatory true;
       }
     }
     output {
       choice output_c {
         case output-tag {
           leaf output {
             type string;
           }
         }
         case actual-tag {
           anyxml service-detnat-information;
         }
         case multichassis-tag {
           anyxml multi-routing-engine-results;
         }
       }
     }
   }
   rpc get-service-detnat-pb-information {
     description "Show deterministic NAT port blocks assigned to internal-host";
     junos:command "show services nat deterministic-nat nat-port-block";
     input {
       leaf internal-address {
         description "Subscriber IP address";
         type string;
         mandatory true;
       }
     }
     output {
       choice output_c {
         case output-tag {
           leaf output {
             type string;
           }
         }
         case actual-tag {
           anyxml service-detnat-information;
         }
         case multichassis-tag {
           anyxml multi-routing-engine-results;
         }
       }
     }
   }
   rpc get-service-nat-ipv6-multicast-information {
     description "Show interfaces with IPv6 multicast filter";
     junos:command "show services nat ipv6-multicast-interfaces";
     output {
       choice output_c {
         case output-tag {
           leaf output {
             type string;
           }
         }
         case actual-tag {
           anyxml service-nat-ipv6-multicast-interfaces-information;
         }
         case multichassis-tag {
           anyxml multi-routing-engine-results;
         }
       }
     }
   }
   rpc get-service-nat-mapping-address-pooling-paired {
     description "Show NAT Address Pooling Paired mapping";
     junos:command "show services nat mappings address-pooling-paired";
     input {
       leaf private {
         description "Private IP/IPv6 prefix to use as filter";
         type string;
       }
       leaf public {
         description "Public IP/IPv6 prefix to use as filter";
         type string;
       }
     }
     output {
       choice output_c {
         case output-tag {
           leaf output {
             type string;
           }
         }
         case actual-tag {
           anyxml service-nat-mapping-address-pooling-paired;
         }
         case multichassis-tag {
           anyxml multi-routing-engine-results;
         }
       }
     }
   }
   rpc get-service-nat-mapping-endpoint-independent {
     description "Show NAT Endpoint Independent mapping";
     junos:command "show services nat mappings endpoint-independent";
     input {
       leaf private {
         description "Private IP/IPv6 prefix to use as filter";
         type string;
       }
       leaf public {
         description "Public IP prefix to use as filter";
         type string;
       }
     }
     output {
       choice output_c {
         case output-tag {
           leaf output {
             type string;
           }
         }
         case actual-tag {
           anyxml service-nat-mapping-endpoint-independent;
         }
         case multichassis-tag {
           anyxml multi-routing-engine-results;
         }
       }
     }
   }
   rpc get-service-nat-mapping-pcp {
     description "Show NAT PCP mapping";
     junos:command "show services nat mappings pcp";
     output {
       choice output_c {
         case output-tag {
           leaf output {
             type string;
           }
         }
         case actual-tag {
           anyxml service-nat-mapping-pcp;
         }
         case multichassis-tag {
           anyxml multi-routing-engine-results;
         }
       }
     }
   }
   rpc get-service-nat-mapping-summary {
     description "Show NAT mapping entries count";
     junos:command "show services nat mappings summary";
     output {
       choice output_c {
         case output-tag {
           leaf output {
             type string;
           }
         }
         case actual-tag {
           anyxml service-nat-mapping-summary;
         }
         case multichassis-tag {
           anyxml multi-routing-engine-results;
         }
       }
     }
   }
   rpc get-service-nat-mapping-brief {
     description "Show NAT mapping brief";
     junos:command "show services nat mappings brief";
     input {
       leaf pool-name {
         description "Name of pool";
         type string;
       }
     }
     output {
       choice output_c {
         case output-tag {
           leaf output {
             type string;
           }
         }
         case actual-tag {
           anyxml service-nat-mapping-address-pooling-paired;
         }
         case multichassis-tag {
           anyxml multi-routing-engine-results;
         }
       }
     }
   }
   rpc get-service-nat-mapping-detail {
     description "Show NAT mapping detail";
     junos:command "show services nat mappings detail";
     input {
       leaf pool-name {
         description "Name of pool";
         type string;
       }
     }
     output {
       choice output_c {
         case output-tag {
           leaf output {
             type string;
           }
         }
         case actual-tag {
           anyxml service-nat-mapping-endpoint-independent;
         }
         case multichassis-tag {
           anyxml multi-routing-engine-results;
         }
       }
     }
   }
   rpc get-service-nat-mapping-nptv6 {
     description "Show nptv6 translated address";
     junos:command "show services nat mappings nptv6";
     input {
       leaf address {
         description "IPV6 Address";
         type jt:ipv6addr;
         mandatory true;
       }
       leaf direction {
         type enumeration {
           enum "internal" {
             description "Internal-address";
           }
           enum "external" {
             description "External-address";
           }
         }
         mandatory true;
       }
     }
     output {
       choice output_c {
         case output-tag {
           leaf output {
             type string;
           }
         }
         case actual-tag {
           anyxml service-nat-mapping-nptv6;
         }
         case multichassis-tag {
           anyxml multi-routing-engine-results;
         }
       }
     }
   }
   rpc get-service-nat-statistics-information {
     description "Show NAT statistics";
     junos:command "show services nat statistics";
     input {
       leaf interface {
         description "Name of extension provider interface";
         type string;
       }
     }
     output {
       choice output_c {
         case output-tag {
           leaf output {
             type string;
           }
         }
         case actual-tag {
           anyxml service-nat-statistics-information;
         }
         case multichassis-tag {
           anyxml multi-routing-engine-results;
         }
       }
     }
   }
   rpc get-services-firewall-policies {
     description "Show services policies";
     junos:command "show services policies";
     input {
       uses command-forwarding;
       leaf policy-name {
         description "Show the policy information matching the given policy name";
         type string;
       }
       leaf detail {
         description "Show the detailed information";
         type empty;
       }
       leaf start {
         description "Show the policies from a given position";
         type union {
           type string {
             pattern "<.*>|$.*";
           }
           type uint32 {
             range "1 .. 65535";
           }
         }
       }
       leaf count {
         description "Number of policies to show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf service-set {
         description "Name of service set";
         type string;
       }
       leaf interface {
         description "Name of adaptive services interface";
         type string;
       }
       leaf stateful-firewall-rule {
         description "Show policy info matching given stateful-firewall-rule name";
         type string;
       }
     }
     output {
       choice output_c {
         case output-tag {
           leaf output {
             type string;
           }
         }
         case actual-tag {
           anyxml services-policies;
         }
         case multichassis-tag {
           anyxml multi-routing-engine-results;
         }
       }
     }
   }
   rpc get-services-firewall-policies-information {
     description "Show the policy information";
     junos:command "show services policies information";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml policy-internal-information;
         }
         case multichassis-tag {
           anyxml multi-routing-engine-results;
         }
       }
     }
   }
   rpc get-services-policy-checksum-information {
     description "Show policy information checksum";
     junos:command "show services policies checksum";
     input {
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
         case all-logical-systems-tenants {
           leaf all-logical-systems-tenants {
             description "All multitenancy systems";
             type empty;
           }
         }
       }
     }
     output {
       choice output_c {
         case output-tag {
           leaf output {
             type string;
           }
         }
         case actual-tag {
           anyxml policy-context-checksum-info;
         }
         case multichassis-tag {
           anyxml multi-routing-engine-results;
         }
       }
     }
   }
   rpc get-services-policies-hit-count {
     description "Show the hit count of policies";
     junos:command "show services policies hit-count";
     input {
       uses command-forwarding;
       leaf order {
         description "Policy order";
         type enumeration {
           enum "ascending" {
             description "Ascending order";
           }
           enum "descending" {
             description "Descending order";
           }
         }
       }
       leaf less-than {
         description "Maximum hit-count ";
         type union {
           type string {
             pattern "<.*>|$.*";
           }
           type uint32 {
             range "0 .. 4294967295";
           }
         }
       }
       leaf greater-than {
         description "Minimum hit-count ";
         type union {
           type string {
             pattern "<.*>|$.*";
           }
           type uint32 {
             range "0 .. 4294967295";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml policy-hit-count-service-router;
         }
         case multichassis-tag {
           anyxml multi-routing-engine-results;
         }
       }
     }
   }
   rpc get-security-metadata-dns-statistics {
     description "Show security metadata streaming DNS statistics";
     junos:command "show services security-metadata-streaming dns statistics";
     input {
       uses command-forwarding;
     }
     output {
       choice output_c {
         case output-tag {
           leaf output {
             type string;
           }
         }
         case actual-tag {
           anyxml sm-dns-statistics;
         }
         case multichassis-tag {
           anyxml multi-routing-engine-results;
         }
       }
     }
   }
   rpc get-security-metadata-statistics {
     description "Show security metadata streaming HTTP statistics";
     junos:command "show services security-metadata-streaming http statistics";
     input {
       uses command-forwarding;
     }
     output {
       choice output_c {
         case output-tag {
           leaf output {
             type string;
           }
         }
         case actual-tag {
           anyxml security-metadata-statistics;
         }
         case multichassis-tag {
           anyxml multi-routing-engine-results;
         }
       }
     }
   }
   rpc get-security-metadata-streaming-whitelist {
     description "Show security metadata streaming HTTP whitelist";
     junos:command "show services security-metadata-streaming http whitelist";
     input {
       uses command-forwarding;
     }
     output {
       choice output_c {
         case output-tag {
           leaf output {
             type string;
           }
         }
         case actual-tag {
           anyxml security-dynamic-address;
         }
         case multichassis-tag {
           anyxml multi-routing-engine-results;
         }
       }
     }
   }
   rpc get-av-policy {
     description "Show anti-virus policy";
     junos:command "show services anti-virus policy";
     input {
       uses command-forwarding;
       leaf policy-name {
         description "Policy name";
         type string;
       }
     }
     output {
       choice output_c {
         case output-tag {
           leaf output {
             type string;
           }
         }
         case actual-tag {
           anyxml av-policy;
         }
         case multichassis-tag {
           anyxml multi-routing-engine-results;
         }
       }
     }
   }
   rpc get-av-statistics {
     description "Show anti-virus statistic";
     junos:command "show services anti-virus statistics";
     input {
       uses command-forwarding;
     }
     output {
       choice output_c {
         case output-tag {
           leaf output {
             type string;
           }
         }
         case actual-tag {
           anyxml av-statistics;
         }
         case multichassis-tag {
           anyxml multi-routing-engine-results;
         }
       }
     }
   }
   rpc get-user-group-all-debug-counters {
     description "Show debug counters";
     junos:command "show services user-identification debug-counters";
     output {
       choice output_c {
         case output-tag {
           leaf output {
             type string;
           }
         }
         case actual-tag {
           anyxml user-group-debug-counters;
         }
         case multichassis-tag {
           anyxml multi-routing-engine-results;
         }
       }
     }
   }
   rpc get-user-group-ager-debug-counters {
     junos:command "show services user-identification debug-counters ager";
     output {
       choice output_c {
         case output-tag {
           leaf output {
             type string;
           }
         }
         case actual-tag {
           anyxml user-group-debug-counters;
         }
         case multichassis-tag {
           anyxml multi-routing-engine-results;
         }
       }
     }
   }
   rpc get-user-group-batch-query-debug-counters {
     junos:command "show services user-identification debug-counters batch-query";
     output {
       choice output_c {
         case output-tag {
           leaf output {
             type string;
           }
         }
         case actual-tag {
           anyxml user-group-debug-counters;
         }
         case multichassis-tag {
           anyxml multi-routing-engine-results;
         }
       }
     }
   }
   rpc get-user-group-ip-query-debug-counters {
     junos:command "show services user-identification debug-counters ip-query";
     output {
       choice output_c {
         case output-tag {
           leaf output {
             type string;
           }
         }
         case actual-tag {
           anyxml user-group-debug-counters;
         }
         case multichassis-tag {
           anyxml multi-routing-engine-results;
         }
       }
     }
   }
   rpc get-user-group-message-exchange-debug-counters {
     junos:command "show services user-identification debug-counters message-exchange";
     output {
       choice output_c {
         case output-tag {
           leaf output {
             type string;
           }
         }
         case actual-tag {
           anyxml user-group-debug-counters;
         }
         case multichassis-tag {
           anyxml multi-routing-engine-results;
         }
       }
     }
   }
   rpc get-user-group-general-debug-counters {
     junos:command "show services user-identification debug-counters general";
     output {
       choice output_c {
         case output-tag {
           leaf output {
             type string;
           }
         }
         case actual-tag {
           anyxml user-group-debug-counters;
         }
         case multichassis-tag {
           anyxml multi-routing-engine-results;
         }
       }
     }
   }
   rpc get-authentication-table-counter {
     description "Show authentication table entry internal counter";
     junos:command "show services user-identification authentication-table counter";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-counter;
         }
         case multichassis-tag {
           anyxml multi-routing-engine-results;
         }
       }
     }
   }
   rpc get-authentication-table-by-address {
     description "Show authentication table entry by ip-address";
     junos:command "show services user-identification authentication-table ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-by-address;
         }
         case multichassis-tag {
           anyxml multi-routing-engine-results;
         }
       }
     }
   }
   rpc get-authentication-table-by-address-type {
     description "Show authentication table entry with auth type by ip-address";
     junos:command "show services user-identification authentication-table ip-address-type";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-by-address;
         }
         case multichassis-tag {
           anyxml multi-routing-engine-results;
         }
       }
     }
   }
   rpc get-authentication-table-all {
     description "Show the entire authentication table in the userid daemon";
     junos:command "show services user-identification authentication-table authentication-source all";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml authentication-table-all;
         }
         case multichassis-tag {
           anyxml multi-routing-engine-results;
         }
       }
     }
   }
   rpc get-authentication-table-all-by-group {
     description "Show authentication table entry by group name";
     junos:command "show services user-identification authentication-table authentication-source all group";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-all-by-group;
         }
         case multichassis-tag {
           anyxml multi-routing-engine-results;
         }
       }
     }
   }
   rpc get-authentication-table-all-by-user {
     description "Show authentication table entry by user name";
     junos:command "show services user-identification authentication-table authentication-source all user";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-all-by-user;
         }
         case multichassis-tag {
           anyxml multi-routing-engine-results;
         }
       }
     }
   }
   rpc get-authentication-table-all-type {
     description "Show the entire authentication table in the userid daemon";
     junos:command "show services user-identification authentication-table authentication-source all-type";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml authentication-table-all;
         }
         case multichassis-tag {
           anyxml multi-routing-engine-results;
         }
       }
     }
   }
   rpc get-authentication-table-all-type-by-group {
     description "Show authentication table entry by group name";
     junos:command "show services user-identification authentication-table authentication-source all-type group";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-all-by-group;
         }
         case multichassis-tag {
           anyxml multi-routing-engine-results;
         }
       }
     }
   }
   rpc get-authentication-table-all-type-by-user {
     description "Show authentication table entry by user name";
     junos:command "show services user-identification authentication-table authentication-source all-type user";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-all-by-user;
         }
         case multichassis-tag {
           anyxml multi-routing-engine-results;
         }
       }
     }
   }
   rpc get-authentication-table-cp {
     description "Authentication source from Aruba ClearPass";
     junos:command "show services user-identification authentication-table authentication-source aruba-clearpass";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml authentication-table-cp;
         }
         case multichassis-tag {
           anyxml multi-routing-engine-results;
         }
       }
     }
   }
   rpc get-authentication-table-cp-by-group {
     description "Show authentication table entry by group name";
     junos:command "show services user-identification authentication-table authentication-source aruba-clearpass group";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-cp-by-group;
         }
         case multichassis-tag {
           anyxml multi-routing-engine-results;
         }
       }
     }
   }
   rpc get-authentication-table-cp-by-user {
     description "Show authentication table entry by user name";
     junos:command "show services user-identification authentication-table authentication-source aruba-clearpass user";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-cp-by-user;
         }
         case multichassis-tag {
           anyxml multi-routing-engine-results;
         }
       }
     }
   }
   rpc get-authentication-table-ad {
     description "Show the active directory authentication table";
     junos:command "show services user-identification authentication-table authentication-source active-directory";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml authentication-table-ad;
         }
         case multichassis-tag {
           anyxml multi-routing-engine-results;
         }
       }
     }
   }
   rpc get-authentication-table-ad-by-group {
     description "Show authentication table entry by group name";
     junos:command "show services user-identification authentication-table authentication-source active-directory group";
     input {
       uses command-forwarding;
       leaf group-name {
         description "Group name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-ad-by-group;
         }
         case multichassis-tag {
           anyxml multi-routing-engine-results;
         }
       }
     }
   }
   rpc get-authentication-table-ad-by-user {
     description "Show authentication table entry by user name";
     junos:command "show services user-identification authentication-table authentication-source active-directory user";
     input {
       uses command-forwarding;
       leaf user-name {
         description "User name";
         type string {
           length "1 .. 65";
         }
         mandatory true;
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-ad-by-user;
         }
         case multichassis-tag {
           anyxml multi-routing-engine-results;
         }
       }
     }
   }
   rpc get-authentication-table-ims {
     description "Identity management server";
     junos:command "show services user-identification authentication-table authentication-source identity-management";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
       leaf source-name {
         description "Authentication source name";
         type string {
           length "1 .. 65";
         }
       }
       leaf domain {
         description "Show identity-management-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml authentication-table-ims;
         }
         case multichassis-tag {
           anyxml multi-routing-engine-results;
         }
       }
     }
   }
   rpc get-authentication-table-ims-by-group {
     description "Show authentication table entry by group name";
     junos:command "show services user-identification authentication-table authentication-source identity-management group";
     input {
       uses command-forwarding;
       leaf group-name {
         description "Group name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-ims-by-group;
         }
         case multichassis-tag {
           anyxml multi-routing-engine-results;
         }
       }
     }
   }
   rpc get-authentication-table-ims-by-user {
     description "Show authentication table entry by user name";
     junos:command "show services user-identification authentication-table authentication-source identity-management user";
     input {
       uses command-forwarding;
       leaf user-name {
         description "User name";
         type string {
           length "1 .. 65";
         }
         mandatory true;
       }
       leaf source-name {
         description "Authentication source name";
         type string {
           length "1 .. 65";
         }
       }
       leaf domain {
         description "Show authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml authentication-table-ims-by-user;
         }
         case multichassis-tag {
           anyxml multi-routing-engine-results;
         }
       }
     }
   }
   rpc get-domain-controller-status {
     description "Show domain-controller status";
     junos:command "show services user-identification active-directory-access domain-controller status";
     input {
       uses command-forwarding;
       leaf domain {
         description "Show domain-controller status per domain";
         type string {
           length "1 .. 65";
         }
       }
       leaf level {
         default "brief";
         type enumeration {
           enum "brief" {
             description "Show brief output (default)";
           }
           enum "extensive" {
             description "Show extensive output";
           }
         }
       }
     }
     output {
       choice output_c {
         case output-tag {
           leaf output {
             type string;
           }
         }
         case actual-tag {
           anyxml domain-controller-status;
         }
         case multichassis-tag {
           anyxml multi-routing-engine-results;
         }
       }
     }
   }
   rpc get-ip-user-mapping-statistics {
     description "Show ip-user-mapping statistics";
     junos:command "show services user-identification active-directory-access statistics ip-user-mapping";
     input {
       uses command-forwarding;
       leaf domain {
         description "Show ip-user-mapping statistics per domain";
         type string {
           length "1 .. 65";
         }
       }
     }
     output {
       choice output_c {
         case output-tag {
           leaf output {
             type string;
           }
         }
         case actual-tag {
           anyxml ip-user-mapping-statistics;
         }
         case multichassis-tag {
           anyxml multi-routing-engine-results;
         }
       }
     }
   }
   rpc get-ip-user-probe-statistics {
     description "Show ip-user-probe statistics";
     junos:command "show services user-identification active-directory-access statistics ip-user-probe";
     input {
       uses command-forwarding;
       leaf domain {
         description "Show ip-user-probe statistics per domain";
         type string {
           length "1 .. 65";
         }
       }
     }
     output {
       choice output_c {
         case output-tag {
           leaf output {
             type string;
           }
         }
         case actual-tag {
           anyxml ip-user-probe-statistics;
         }
         case multichassis-tag {
           anyxml multi-routing-engine-results;
         }
       }
     }
   }
   rpc get-user-group-mapping-statistics {
     description "Show user-group-mapping statistics";
     junos:command "show services user-identification active-directory-access statistics user-group-mapping";
     input {
       uses command-forwarding;
       leaf domain {
         description "Show user-group-mapping statistics per domain";
         type string {
           length "1 .. 65";
         }
       }
     }
     output {
       choice output_c {
         case output-tag {
           leaf output {
             type string;
           }
         }
         case actual-tag {
           anyxml user-group-mapping-statistics;
         }
         case multichassis-tag {
           anyxml multi-routing-engine-results;
         }
       }
     }
   }
   rpc get-all-configuration {
     description "Show active-directory-access configuration";
     junos:command "show services user-identification active-directory-access configuration";
     output {
       choice output_c {
         case output-tag {
           leaf output {
             type string;
           }
         }
         case actual-tag {
           anyxml all-configuration;
         }
         case multichassis-tag {
           anyxml multi-routing-engine-results;
         }
       }
     }
   }
   rpc get-users-by-group {
     description "Show specified group's users. If timeout, wait several minutes and try again.";
     junos:command "show services user-identification active-directory-access user-group-mapping group";
     input {
       uses command-forwarding;
       leaf group-name {
         description "Specified group name";
         type string {
           length "1 .. 65";
         }
         mandatory true;
       }
       leaf domain {
         description "Show users per domain";
         type string {
           length "1 .. 65";
         }
         mandatory true;
       }
     }
     output {
       choice output_c {
         case output-tag {
           leaf output {
             type string;
           }
         }
         case actual-tag {
           anyxml users-by-group;
         }
         case multichassis-tag {
           anyxml multi-routing-engine-results;
         }
       }
     }
   }
   rpc get-groups-by-user {
     description "Show specified user's groups. If timeout, wait several minutes and try again.";
     junos:command "show services user-identification active-directory-access user-group-mapping user";
     input {
       uses command-forwarding;
       leaf user-name {
         description "Specified user name";
         type string {
           length "1 .. 65";
         }
         mandatory true;
       }
       leaf domain {
         description "Show groups per domain";
         type string {
           length "1 .. 65";
         }
         mandatory true;
       }
       leaf in-local-cache {
         description "Show only groups in local cache";
         type empty;
       }
     }
     output {
       choice output_c {
         case output-tag {
           leaf output {
             type string;
           }
         }
         case actual-tag {
           anyxml groups-by-user;
         }
         case multichassis-tag {
           anyxml multi-routing-engine-results;
         }
       }
     }
   }
   rpc get-user-group-mapping-status {
     description "Show user-group-mapping status";
     junos:command "show services user-identification active-directory-access user-group-mapping status";
     input {
       uses command-forwarding;
       leaf domain {
         description "Show user-group-mapping status per domain";
         type string {
           length "1 .. 65";
         }
       }
     }
     output {
       choice output_c {
         case output-tag {
           leaf output {
             type string;
           }
         }
         case actual-tag {
           anyxml user-group-mapping-status;
         }
         case multichassis-tag {
           anyxml multi-routing-engine-results;
         }
       }
     }
   }
   rpc get-ad-ug-mapping-fetching {
     description "Show user-group-mapping fetching";
     junos:command "show services user-identification active-directory-access user-group-mapping fetch";
     output {
       choice output_c {
         case output-tag {
           leaf output {
             type string;
           }
         }
         case multichassis-tag {
           anyxml multi-routing-engine-results;
         }
       }
     }
   }
   rpc get-fetching-status {
     description "Show user-group-mapping fetching status";
     junos:command "show services user-identification active-directory-access user-group-mapping fetch status";
     output {
       choice output_c {
         case output-tag {
           leaf output {
             type string;
           }
         }
         case actual-tag {
           anyxml fetching-status;
         }
         case multichassis-tag {
           anyxml multi-routing-engine-results;
         }
       }
     }
   }
   rpc get-periodic-fetching {
     description "Show user-group-mapping periodic fetching";
     junos:command "show services user-identification active-directory-access user-group-mapping periodic-fetch";
     output {
       choice output_c {
         case output-tag {
           leaf output {
             type string;
           }
         }
         case multichassis-tag {
           anyxml multi-routing-engine-results;
         }
       }
     }
   }
   rpc get-periodic-fetching-status {
     description "Show user-group-mapping periodic fetching status";
     junos:command "show services user-identification active-directory-access user-group-mapping periodic-fetch status";
     output {
       choice output_c {
         case output-tag {
           leaf output {
             type string;
           }
         }
         case actual-tag {
           anyxml periodic-fetching-status;
         }
         case multichassis-tag {
           anyxml multi-routing-engine-results;
         }
       }
     }
   }
   rpc get-periodic-fetching-configuration {
     description "Show user-group-mapping periodic fetching configuration";
     junos:command "show services user-identification active-directory-access user-group-mapping periodic-fetch configuration";
     output {
       choice output_c {
         case output-tag {
           leaf output {
             type string;
           }
         }
         case actual-tag {
           anyxml periodic-fetching-configuration;
         }
         case multichassis-tag {
           anyxml multi-routing-engine-results;
         }
       }
     }
   }
   rpc get-ad-ug-mapping-refreshing {
     description "Show user-group-mapping refreshing";
     junos:command "show services user-identification active-directory-access user-group-mapping refresh";
     output {
       choice output_c {
         case output-tag {
           leaf output {
             type string;
           }
         }
         case multichassis-tag {
           anyxml multi-routing-engine-results;
         }
       }
     }
   }
   rpc get-refreshing-status {
     description "Show user-group-mapping refreshing status";
     junos:command "show services user-identification active-directory-access user-group-mapping refresh status";
     output {
       choice output_c {
         case output-tag {
           leaf output {
             type string;
           }
         }
         case actual-tag {
           anyxml refreshing-status;
         }
         case multichassis-tag {
           anyxml multi-routing-engine-results;
         }
       }
     }
   }
   rpc get-all-groups {
     description "Show all groups";
     junos:command "show services user-identification active-directory-access group-list";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml group-list;
         }
         case multichassis-tag {
           anyxml multi-routing-engine-results;
         }
       }
     }
   }
   rpc get-all-users {
     description "Show all users";
     junos:command "show services user-identification active-directory-access user-list";
     input {
       uses command-forwarding;
       leaf domain {
         description "Show groups per domain";
         type string {
           length "1 .. 65";
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml group-list;
         }
         case multichassis-tag {
           anyxml multi-routing-engine-results;
         }
       }
     }
   }
   rpc get-ad-auth-table-all-information {
     description "Show the entire active directory authentication table";
     junos:command "show services user-identification active-directory-access active-directory-authentication-table all";
     input {
       uses command-forwarding;
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml active-directory-authentication-table;
         }
         case multichassis-tag {
           anyxml multi-routing-engine-results;
         }
       }
     }
   }
   rpc get-ad-auth-table-by-address-information {
     description "Show active directory authentication table entry by ip-address";
     junos:command "show services user-identification active-directory-access active-directory-authentication-table ip-address";
     input {
       uses command-forwarding;
       leaf ip-address {
         description "IP address";
         type jt:ipaddr;
         mandatory true;
       }
     }
     output {
       choice output_c {
         case output-tag {
           leaf output {
             type string;
           }
         }
         case multichassis-tag {
           anyxml multi-routing-engine-results;
         }
       }
     }
   }
   rpc get-ad-auth-table-by-group-information {
     description "Show active directory authentication table entry by group name";
     junos:command "show services user-identification active-directory-access active-directory-authentication-table group";
     input {
       uses command-forwarding;
       leaf group-name {
         description "Group name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc get-ad-auth-table-by-user-information {
     description "Show active directory authentication table entry by user name";
     junos:command "show services user-identification active-directory-access active-directory-authentication-table user";
     input {
       uses command-forwarding;
       leaf user-name {
         description "User name";
         type string {
           length "1 .. 65";
         }
         mandatory true;
       }
       leaf domain {
         description "Show active-directory-authentication-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case multichassis-tag {
           anyxml multi-routing-engine-results;
         }
       }
     }
   }
   rpc get-cp-user-query-statistics {
     description "Show ClearPass user query counters";
     junos:command "show services user-identification authentication-source aruba-clearpass user-query counters";
     output {
       choice output_c {
         case output-tag {
           leaf output {
             type string;
           }
         }
         case actual-tag {
           anyxml cp-user-query-statistics;
         }
         case multichassis-tag {
           anyxml multi-routing-engine-results;
         }
       }
     }
   }
   rpc get-cp-user-query-status {
     description "Show ClearPass user query status";
     junos:command "show services user-identification authentication-source aruba-clearpass user-query status";
     output {
       choice output_c {
         case output-tag {
           leaf output {
             type string;
           }
         }
         case actual-tag {
           anyxml cp-user-query-status;
         }
         case multichassis-tag {
           anyxml multi-routing-engine-results;
         }
       }
     }
   }
   rpc get-device-identity-table-all {
     description "Show the entire device identity table";
     junos:command "show services user-identification device-information table all";
     input {
       uses command-forwarding;
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml device-identity-table-all;
         }
         case multichassis-tag {
           anyxml multi-routing-engine-results;
         }
       }
     }
   }
   rpc get-device-identity-table-by-address {
     description "Show device identity table entry by ip-address";
     junos:command "show services user-identification device-information table ip-address";
     input {
       uses command-forwarding;
       leaf ip-address {
         description "IP address";
         type jt:ipaddr;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml device-identity-table-by-address;
         }
         case multichassis-tag {
           anyxml multi-routing-engine-results;
         }
       }
     }
   }
   rpc get-device-identity-table-by-device-id {
     description "Show device identity table entry by device id";
     junos:command "show services user-identification device-information table device-id";
     input {
       uses command-forwarding;
       leaf device-id {
         description "Device ID";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml device-identity-table-by-device-id;
         }
         case multichassis-tag {
           anyxml multi-routing-engine-results;
         }
       }
     }
   }
   rpc get-device-identity-table-by-group {
     description "Show device identity table entry by group name";
     junos:command "show services user-identification device-information table group";
     input {
       uses command-forwarding;
       leaf group-name {
         description "Group name";
         type string {
           length "1 .. 65";
         }
         mandatory true;
       }
       leaf domain {
         description "Show device-identity-table per domain";
         type string {
           length "1 .. 65";
         }
       }
       leaf level {
         default "brief";
         type enumeration {
           enum "brief" {
             description "Show brief output (default)";
           }
           enum "extensive" {
             description "Show extensive output";
           }
         }
       }
       leaf start {
         description "Start of show";
         type union {
           type string {
             pattern "<.*>|$.*";
           }
           type uint32 {
             range "1 .. 65535";
           }
         }
       }
       leaf count {
         description "Number of show";
         type union {
           type string {
             pattern "<.*>|$.*";
           }
           type uint32 {
             range "1 .. 65535";
           }
         }
       }
     }
     output {
       choice output_c {
         case output-tag {
           leaf output {
             type string;
           }
         }
         case actual-tag {
           anyxml device-identity-table-by-group;
         }
         case multichassis-tag {
           anyxml multi-routing-engine-results;
         }
       }
     }
   }
   rpc dump-property-lib {
     description "Dump property lib content";
     junos:command "show services user-identification device-information end-user-profile property-lib-dump";
     output {
       choice output_c {
         case output-tag {
           leaf output {
             type string;
           }
         }
         case actual-tag {
           anyxml dump-property-lib;
         }
         case multichassis-tag {
           anyxml multi-routing-engine-results;
         }
       }
     }
   }
   rpc get-end-user-profile-address {
     description "Specified all address of specified end-user-profile";
     junos:command "show services user-identification device-information end-user-profile address";
     input {
       leaf profile-name {
         description "Specified profile name";
         type string {
           length "1 .. 65";
         }
       }
       leaf ip-start {
         description "IP from address";
         type jt:ipaddr;
       }
       leaf ip-end {
         description "IP to address";
         type jt:ipaddr;
       }
       leaf sort-by-profile {
         description "Sort by end-user-profile";
         type empty;
       }
       choice lsys {
         case logical-system {
           leaf logical-system {
             description "Logical-system name";
             type string;
           }
         }
         case root-logical-system {
           leaf root-logical-system {
             description "Root logical-system (default)";
             type empty;
           }
         }
         case tenant {
           leaf tenant {
             description "Tenant name";
             type string;
           }
         }
       }
     }
     output {
       choice output_c {
         case output-tag {
           leaf output {
             type string;
           }
         }
         case actual-tag {
           anyxml get-end-user-profile-address;
         }
         case multichassis-tag {
           anyxml multi-routing-engine-results;
         }
       }
     }
   }
   rpc get-end-user-profile-statistics {
     description "Show end-user-profile ip-mapping statistics";
     junos:command "show services user-identification device-information end-user-profile ip-mapping statistics";
     output {
       choice output_c {
         case output-tag {
           leaf output {
             type string;
           }
         }
         case actual-tag {
           anyxml get-end-user-profile-statistics;
         }
         case multichassis-tag {
           anyxml multi-routing-engine-results;
         }
       }
     }
   }
   rpc get-jims-query-statistics {
     description "Show identity management query counters";
     junos:command "show services user-identification identity-management counters";
     output {
       choice output_c {
         case output-tag {
           leaf output {
             type string;
           }
         }
         case actual-tag {
           anyxml jims-query-statistics;
         }
         case multichassis-tag {
           anyxml multi-routing-engine-results;
         }
       }
     }
   }
   rpc get-jims-query-status {
     description "Show identity management query status";
     junos:command "show services user-identification identity-management status";
     output {
       choice output_c {
         case output-tag {
           leaf output {
             type string;
           }
         }
         case actual-tag {
           anyxml jims-query-status;
         }
         case multichassis-tag {
           anyxml multi-routing-engine-results;
         }
       }
     }
   }
   rpc get-jims-more-info {
     description "Show more information of identity management";
     junos:command "show services user-identification identity-management more-info";
     output {
       choice output_c {
         case output-tag {
           leaf output {
             type string;
           }
         }
         case actual-tag {
           anyxml jims-more-info;
         }
         case multichassis-tag {
           anyxml multi-routing-engine-results;
         }
       }
     }
   }
   rpc get-jims-validator-info {
     description "Show counter and status of jims validator query server of identity management";
     junos:command "show services user-identification identity-management jims-validator";
     output {
       choice output_c {
         case output-tag {
           leaf output {
             type string;
           }
         }
         case multichassis-tag {
           anyxml multi-routing-engine-results;
         }
       }
     }
   }
   rpc get-jims-validator-query-statistics {
     description "Show identity management jims validator query counters";
     junos:command "show services user-identification identity-management jims-validator counters";
     output {
       choice output_c {
         case output-tag {
           leaf output {
             type string;
           }
         }
         case actual-tag {
           anyxml jims-validator-query-statistics;
         }
         case multichassis-tag {
           anyxml multi-routing-engine-results;
         }
       }
     }
   }
   rpc get-jims-validator-query-status {
     description "Show identity management jims validator query status";
     junos:command "show services user-identification identity-management jims-validator status";
     output {
       choice output_c {
         case output-tag {
           leaf output {
             type string;
           }
         }
         case actual-tag {
           anyxml jims-validator-query-status;
         }
         case multichassis-tag {
           anyxml multi-routing-engine-results;
         }
       }
     }
   }
   rpc get-dispatcher-statistics {
     description "Show statistics";
     junos:command "show services user-identification dispatcher statistics";
     output {
       choice output_c {
         case output-tag {
           leaf output {
             type string;
           }
         }
         case actual-tag {
           anyxml get-dispatcher-statistics;
         }
         case multichassis-tag {
           anyxml multi-routing-engine-results;
         }
       }
     }
   }
   rpc get-ld-jims-query-statistics {
     description "Show logical domain identity management query counters";
     junos:command "show services user-identification logical-domain-identity-management counters";
     output {
       choice output_c {
         case output-tag {
           leaf output {
             type string;
           }
         }
         case actual-tag {
           anyxml ld-jims-query-statistics;
         }
         case multichassis-tag {
           anyxml multi-routing-engine-results;
         }
       }
     }
   }
   rpc get-ld-jims-query-status {
     description "Show logical domain identity management query status";
     junos:command "show services user-identification logical-domain-identity-management status";
     output {
       choice output_c {
         case output-tag {
           leaf output {
             type string;
           }
         }
         case actual-tag {
           anyxml ld-jims-query-status;
         }
         case multichassis-tag {
           anyxml multi-routing-engine-results;
         }
       }
     }
   }
   rpc get-validate-statistics-from-jims {
     description "Show validate statistics device/group/user from JIMS";
     junos:command "show services user-identification validate-statistics";
     output {
       choice output_c {
         case output-tag {
           leaf output {
             type string;
           }
         }
         case multichassis-tag {
           anyxml multi-routing-engine-results;
         }
       }
     }
   }
   rpc get-web-proxy-session-detail {
     description "Show web proxy session detail";
     junos:command "show services web-proxy session detail";
     output {
       choice output_c {
         case output-tag {
           leaf output {
             type string;
           }
         }
         case actual-tag {
           anyxml web-proxy-session;
         }
         case multichassis-tag {
           anyxml multi-routing-engine-results;
         }
       }
     }
   }
   rpc get-web-proxy-session-summary {
     description "Show web proxy session summary";
     junos:command "show services web-proxy session summary";
     output {
       choice output_c {
         case output-tag {
           leaf output {
             type string;
           }
         }
         case actual-tag {
           anyxml web-proxy-session;
         }
         case multichassis-tag {
           anyxml multi-routing-engine-results;
         }
       }
     }
   }
   rpc get-web-proxy-statistics {
     description "Show Web proxy staticstics";
     junos:command "show services web-proxy statistics";
     output {
       choice output_c {
         case output-tag {
           leaf output {
             type string;
           }
         }
         case actual-tag {
           anyxml web-proxy-statistics;
         }
         case multichassis-tag {
           anyxml multi-routing-engine-results;
         }
       }
     }
   }
   rpc get-web-proxy-dns-fc-entries {
     description "Show web proxy forwarding cache information";
     junos:command "show services web-proxy dns forwarding-cache";
     output {
       choice output_c {
         case output-tag {
           leaf output {
             type string;
           }
         }
         case actual-tag {
           anyxml web-proxy-dns-fc-entries;
         }
         case multichassis-tag {
           anyxml multi-routing-engine-results;
         }
       }
     }
   }
   rpc get-web-proxy-dns-fc-entries-dump {
     description "Show web proxy forwarding cache information for specified dns-name";
     junos:command "show services web-proxy dns forwarding-cache dump";
     input {
       leaf dns-name {
         description "Show DNS cache matching the given DNS name";
         type string;
         mandatory true;
       }
     }
     output {
       choice output_c {
         case output-tag {
           leaf output {
             type string;
           }
         }
         case actual-tag {
           anyxml web-proxy-dns-fc-entries;
         }
         case multichassis-tag {
           anyxml multi-routing-engine-results;
         }
       }
     }
   }
   rpc get-web-proxy-dns-fc-statistics {
     description "Show Web proxy staticstics";
     junos:command "show services web-proxy dns forwarding-cache statistics";
     output {
       choice output_c {
         case output-tag {
           leaf output {
             type string;
           }
         }
         case actual-tag {
           anyxml web-proxy-dns-fc-statistics;
         }
         case multichassis-tag {
           anyxml multi-routing-engine-results;
         }
       }
     }
   }
   rpc get-web-proxy-dns-gc-entries {
     description "Show web proxy global cache information";
     junos:command "show services web-proxy dns global-cache";
     output {
       choice output_c {
         case output-tag {
           leaf output {
             type string;
           }
         }
         case actual-tag {
           anyxml web-proxy-dns-fc-entries;
         }
         case multichassis-tag {
           anyxml multi-routing-engine-results;
         }
       }
     }
   }
   rpc get-web-proxy-dns-gc-entries-dump {
     description "Show web proxy global cache information for specified dnsname";
     junos:command "show services web-proxy dns global-cache dump";
     input {
       uses command-forwarding;
       leaf dns-name {
         description "Show DNS cache matching the given DNS name";
         type string;
       }
     }
     output {
       choice output_c {
         case output-tag {
           leaf output {
             type string;
           }
         }
         case actual-tag {
           anyxml web-proxy-dns-fc-entries;
         }
         case multichassis-tag {
           anyxml multi-routing-engine-results;
         }
       }
     }
   }
   rpc get-web-proxy-dns-gc-statistics {
     description "Show Web proxy global staticstics";
     junos:command "show services web-proxy dns global-cache statistics";
     output {
       choice output_c {
         case output-tag {
           leaf output {
             type string;
           }
         }
         case actual-tag {
           anyxml web-proxy-dns-gc-statistics;
         }
         case multichassis-tag {
           anyxml multi-routing-engine-results;
         }
       }
     }
   }
   rpc get-lrf-statistics {
     description "Show lrf statistics";
     junos:command "show services lrf statistics";
     output {
       choice output_c {
         case output-tag {
           leaf output {
             type string;
           }
         }
         case actual-tag {
           anyxml lrf-statistics-summary;
         }
         case multichassis-tag {
           anyxml multi-routing-engine-results;
         }
       }
     }
   }
   rpc get-lrf-collector-statistics {
     description "Show lrf collector statistics";
     junos:command "show services lrf collector statistics";
     input {
       leaf collector-name {
         description "Name of collector";
         type string;
       }
     }
     output {
       choice output_c {
         case output-tag {
           leaf output {
             type string;
           }
         }
         case actual-tag {
           anyxml lrf-collector-statistics-summary;
         }
         case multichassis-tag {
           anyxml multi-routing-engine-results;
         }
       }
     }
   }
   rpc get-lrf-rule-statistics {
     description "Show lrf rule statistics";
     junos:command "show services lrf rule statistics";
     input {
       leaf rule-name {
         description "Name of rule";
         type string;
       }
     }
     output {
       choice output_c {
         case output-tag {
           leaf output {
             type string;
           }
         }
         case actual-tag {
           anyxml lrf-rule-statistics-summary;
         }
         case multichassis-tag {
           anyxml multi-routing-engine-results;
         }
       }
     }
   }
   rpc get-lrf-template {
     description "Show lrf template";
     junos:command "show services lrf template";
     input {
       leaf template-type {
         description "Template type";
         type enumeration {
           enum "ipv4" {
             description "Ipv4 template type";
           }
           enum "ipv4-extended" {
             description "Ipv4 extended template type";
           }
           enum "ipv6" {
             description "Ipv6 template type";
           }
           enum "ipv6-extended" {
             description "Ipv6 extended template type";
           }
           enum "transport-layer" {
             description "Transport layer template type";
           }
           enum "flow-id" {
             description "Flow id template type";
           }
           enum "ipflow" {
             description "IPFlow type";
           }
           enum "ipflow-ts" {
             description "IPFlow TS type";
           }
           enum "ipflow-extended" {
             description "IPFlow extended type";
           }
           enum "device-data" {
             description "Device data template type";
           }
           enum "l7-app" {
             description "L7 APP template type";
           }
           enum "http" {
             description "HTTP type";
           }
           enum "mobile-subscriber" {
             description "Mobile subscriber type";
           }
           enum "subscriber-data" {
             description "Subscriber data type";
           }
           enum "ifl-subscriber" {
             description "IFL based subscriber type";
           }
           enum "wireline-subscriber" {
             description "Wireline subscriber type";
           }
           enum "ipflow-tcp-ts" {
             description "IPFLOW TCP timestamp type (IBM specific)";
           }
           enum "ipflow-tcp" {
             description "IPFLOW TCP type";
           }
           enum "video" {
             description "Video type";
           }
           enum "dns" {
             description "DNS type";
           }
           enum "status-code-distribution" {
             description "Status code distribution for HTTP and DNS";
           }
           enum "pcc" {
             description "PCC type";
           }
         }
         mandatory true;
       }
     }
     output {
       choice output_c {
         case output-tag {
           leaf output {
             type string;
           }
         }
         case actual-tag {
           anyxml lrf-template;
         }
         case multichassis-tag {
           anyxml multi-routing-engine-results;
         }
       }
     }
   }
   rpc get-service-accounting-information {
     description "Show sampled accounting service";
     junos:command "show services accounting";
     output {
       choice output_c {
         case output-tag {
           leaf output {
             type string;
           }
         }
         case actual-tag {
           anyxml service-accounting-information;
         }
         case multichassis-tag {
           anyxml multi-routing-engine-results;
         }
       }
     }
   }
   rpc get-service-accounting-status-information {
     description "Show service accounting parameters";
     junos:command "show services accounting status";
     input {
       leaf status-information {
         description "Name of service, wildcard, or 'all'";
         type string;
       }
     }
     output {
       choice output_c {
         case output-tag {
           leaf output {
             type string;
           }
         }
         case actual-tag {
           anyxml service-accounting-status-information;
         }
         case multichassis-tag {
           anyxml multi-routing-engine-results;
         }
       }
     }
   }
   rpc get-service-accounting-status-inline-jflow-information {
     description "Show service accounting inline Jflow parameters";
     junos:command "show services accounting status inline-jflow";
     input {
       leaf inline-jflow-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-information;
         }
         case multichassis-tag {
           anyxml multi-routing-engine-results;
         }
       }
     }
   }
   rpc get-service-accounting-usage-information {
     description "Show CPU usage";
     junos:command "show services accounting usage";
     input {
       leaf usage-information {
         description "Name of service, wildcard, or 'all'";
         type string;
       }
     }
     output {
       choice output_c {
         case output-tag {
           leaf output {
             type string;
           }
         }
         case actual-tag {
           anyxml service-accounting-usage-information;
         }
         case multichassis-tag {
           anyxml multi-routing-engine-results;
         }
       }
     }
   }
   rpc get-service-accounting-memory-information {
     description "Show memory information";
     junos:command "show services accounting memory";
     input {
       leaf memory-information {
         description "Name of service, wildcard, or 'all'";
         type string;
       }
     }
     output {
       choice output_c {
         case output-tag {
           leaf output {
             type string;
           }
         }
         case actual-tag {
           anyxml service-accounting-memory-information;
         }
         case multichassis-tag {
           anyxml multi-routing-engine-results;
         }
       }
     }
   }
   rpc get-service-accounting-flow-information {
     description "Show flow information";
     junos:command "show services accounting flow";
     input {
       leaf flow-information {
         description "Name of service, wildcard, or 'all'";
         type string;
       }
       leaf logical-system {
         description "Name of logical system";
         type string {
           junos:posix-pattern "^[a-zA-Z0-9_-]{1,63}$";
           junos:pattern-message "Logical-system name is a string consisting of up         to 63 letters, numbers, dashes and underscores";
         }
       }
     }
     output {
       choice output_c {
         case output-tag {
           leaf output {
             type string;
           }
         }
         case actual-tag {
           anyxml service-accounting-flow-information;
         }
         case multichassis-tag {
           anyxml multi-routing-engine-results;
         }
       }
     }
   }
   rpc get-service-accounting-status-inline-jflow-flow-information {
     description "Show service accounting inline Jflow flow information";
     junos:command "show services accounting flow inline-jflow";
     input {
       leaf inline-jflow-flow-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-flow-infomation;
         }
         case multichassis-tag {
           anyxml multi-routing-engine-results;
         }
       }
     }
   }
   rpc get-service-accounting-flow-detail {
     description "Show flow detail";
     junos:command "show services accounting flow-detail";
     input {
       leaf flow-detail-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf destination-prefix {
         description "Filter term destination prefix";
         type string;
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
       leaf source-as {
         description "Filter term source AS";
         type union {
           type uint32;
           type string {
             pattern "<.*>|$.*";
           }
         }
       }
       leaf destination-as {
         description "Filter term destination AS";
         type union {
           type uint32;
           type string {
             pattern "<.*>|$.*";
           }
         }
       }
       leaf tos {
         description "Filter term ToS";
         type union {
           type uint32;
           type string {
             pattern "<.*>|$.*";
           }
         }
       }
       leaf proto {
         description "Filter term protocol";
         type union {
           type uint32;
           type string {
             pattern "<.*>|$.*";
           }
         }
       }
     }
     output {
       choice output_c {
         case output-tag {
           leaf output {
             type string;
           }
         }
         case actual-tag {
           anyxml service-accounting-flow-detail;
         }
         case multichassis-tag {
           anyxml multi-routing-engine-results;
         }
       }
     }
   }
   rpc get-service-accounting-aggregation-information {
     description "Show aggregation information";
     junos:command "show services accounting aggregation";
     output {
       choice output_c {
         case output-tag {
           leaf output {
             type string;
           }
         }
         case actual-tag {
           anyxml service-accounting-aggregation-information;
         }
         case multichassis-tag {
           anyxml multi-routing-engine-results;
         }
       }
     }
   }
   rpc get-service-accounting-aggregation-as-information {
     description "Show aggregation type AS";
     junos:command "show services accounting aggregation as";
     input {
       leaf as-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-as {
         description "Filter term source-as";
         type union {
           type uint32;
           type string {
             pattern "<.*>|$.*";
           }
         }
       }
       leaf destination-as {
         description "Filter term destination AS";
         type union {
           type uint32;
           type string {
             pattern "<.*>|$.*";
           }
         }
       }
       leaf input-snmp-interface-index {
         description "Filter term input SNMP interface index";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-as-information;
         }
         case multichassis-tag {
           anyxml multi-routing-engine-results;
         }
       }
     }
   }
   rpc get-service-accounting-aggregation-protocol-port-information {
     description "Show aggregation type protocol-port";
     junos:command "show services accounting aggregation protocol-port";
     input {
       leaf protocol-port-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf proto {
         description "Filter term protocol";
         type union {
           type uint32;
           type string {
             pattern "<.*>|$.*";
           }
         }
       }
       leaf source-port {
         description "Filter term source port";
         type union {
           type uint32;
           type string {
             pattern "<.*>|$.*";
           }
         }
       }
       leaf destination-port {
         description "Filter term destination port";
         type union {
           type uint32;
           type string {
             pattern "<.*>|$.*";
           }
         }
       }
     }
     output {
       choice output_c {
         case output-tag {
           leaf output {
             type string;
           }
         }
         case actual-tag {
           anyxml service-accounting-aggregation-protocol-port-information;
         }
         case multichassis-tag {
           anyxml multi-routing-engine-results;
         }
       }
     }
   }
   rpc get-service-accounting-aggregation-source-prefix-information {
     description "Show aggregation type source-prefix";
     junos:command "show services accounting aggregation source-prefix";
     input {
       leaf source-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
     }
     output {
       choice output_c {
         case output-tag {
           leaf output {
             type string;
           }
         }
         case actual-tag {
           anyxml service-accounting-aggregation-source-prefix-information;
         }
         case multichassis-tag {
           anyxml multi-routing-engine-results;
         }
       }
     }
   }
   rpc get-service-accounting-aggregation-destination-prefix-information {
     description "Show aggregation type destination-prefix";
     junos:command "show services accounting aggregation destination-prefix";
     input {
       leaf destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-destination-prefix-information;
         }
         case multichassis-tag {
           anyxml multi-routing-engine-results;
         }
       }
     }
   }
   rpc get-service-accounting-aggregation-source-destination-prefix-information {
     description "Show aggregation type source-destination-prefix";
     junos:command "show services accounting aggregation source-destination-prefix";
     input {
       leaf source-destination-prefix-information {
         description "Name of service, wildcard, or 'all'";
         type string;
       }
       leaf limit {
         description "Maximum number of flows to display";
         type union {
           type uint32;
           type string {
             pattern "<.*>|$.*";
           }
         }
       }
       leaf order {
         description "Order for displaying flows";
         type enumeration {
           enum "bytes" {
             description "Display largest number of bytes first";
           }
           enum "packets" {
             description "Display largest number of packets first";
           }
         }
       }
       leaf display {
         default "terse";
         type enumeration {
           enum "extensive" {
             description "Display extensive output";
           }
           enum "detail" {
             description "Display detailed output";
           }
           enum "terse" {
             description "Display terse output (default)";
           }
         }
       }
       leaf source-prefix {
         description "Filter term source prefix";
         type string;
       }
       leaf source-as {
         description "Filter term source-as";
         type union {
           type uint32;
           type string {
             pattern "<.*>|$.*";
           }
         }
       }
       leaf input-snmp-interface-index {
         description "Filter term input SNMP interface index";
         type union {
           type uint32;
           type string {
             pattern "<.*>|$.*";
           }
         }
       }
       leaf destination-prefix {
         description "Filter term destination prefix";
         type string;
       }
       leaf destination-as {
         description "Filter term destination-as";
         type union {
           type uint32;
           type string {
             pattern "<.*>|$.*";
           }
         }
       }
       leaf output-snmp-interface-index {
         description "Filter term output SNMP interface index";
         type union {
           type uint32;
           type string {
             pattern "<.*>|$.*";
           }
         }
       }
     }
     output {
       choice output_c {
         case output-tag {
           leaf output {
             type string;
           }
         }
         case actual-tag {
           anyxml service-accounting-aggregation-source-destination-prefix-information;
         }
         case multichassis-tag {
           anyxml multi-routing-engine-results;
         }
       }
     }
   }
   rpc get-service-accounting-aggregation-template-information {
     description "Show aggregation type template";
     junos:command "show services accounting aggregation template";
     input {
       leaf template-name {
         description "Name of template";
         type string;
         mandatory true;
       }
       leaf logical-system {
         description "Name of logical system";
         type string {
           junos:posix-pattern "^[a-zA-Z0-9_-]{1,63}$";
           junos:pattern-message "Logical-system name is a string consisting of up         to 63 letters, numbers, dashes and underscores";
         }
       }
       leaf display {
         default "terse";
         type enumeration {
           enum "extensive" {
             description "Display extensive output";
           }
           enum "detail" {
             description "Display detailed output";
           }
           enum "terse" {
             description "Display terse output (default)";
           }
         }
       }
     }
     output {
       choice output_c {
         case output-tag {
           leaf output {
             type string;
           }
         }
         case actual-tag {
           anyxml service-accounting-aggregation-template-information;
         }
         case multichassis-tag {
           anyxml multi-routing-engine-results;
         }
       }
     }
   }
   rpc get-service-accounting-errors-information {
     description "Show error statistics";
     junos:command "show services accounting errors";
     input {
       leaf error-information {
         description "Name of service, wildcard, or 'all'";
         type string;
       }
     }
     output {
       choice output_c {
         case output-tag {
           leaf output {
             type string;
           }
         }
         case actual-tag {
           anyxml service-accounting-errors-information;
         }
         case multichassis-tag {
           anyxml multi-routing-engine-results;
         }
       }
     }
   }
   rpc get-service-accounting-error-inline-jflow-information {
     description "Show service accounting inline Jflow error information";
     junos:command "show services accounting errors inline-jflow";
     input {
       leaf inline-jflow-error-information {
         description "FPC Slot for inline Jflow";
         type union {
           type string {
             pattern "<.*>|$.*";
           }
           type uint32;
         }
       }
     }
     output {
       choice output_c {
         case output-tag {
           leaf output {
             type string;
           }
         }
         case actual-tag {
           anyxml service-accouting-inline-jflow-error-infomation;
         }
         case multichassis-tag {
           anyxml multi-routing-engine-results;
         }
       }
     }
   }
   rpc get-packet-distribution-information {
     description "Show packet size distribution";
     junos:command "show services accounting packet-size-distribution";
     input {
       leaf packet-size-distribution-information {
         description "Name of service, wildcard, or 'all'";
         type string;
       }
     }
     output {
       choice output_c {
         case output-tag {
           leaf output {
             type string;
           }
         }
         case actual-tag {
           anyxml packet-distribution-information;
         }
         case multichassis-tag {
           anyxml multi-routing-engine-results;
         }
       }
     }
   }
   rpc get-service-video-monitoring-information {
     description "Show video-monitoring information";
     junos:command "show services video-monitoring";
     output {
       choice output_c {
         case output-tag {
           leaf output {
             type string;
           }
         }
         case actual-tag {
           anyxml service-video-monitoring-information;
         }
         case multichassis-tag {
           anyxml multi-routing-engine-results;
         }
       }
     }
   }
   rpc get-service-video-monitoring-mdi-information {
     description "Show MDI flows information";
     junos:command "show services video-monitoring mdi";
     output {
       choice output_c {
         case output-tag {
           leaf output {
             type string;
           }
         }
         case actual-tag {
           anyxml service-video-monitoring-mdii-information;
         }
         case multichassis-tag {
           anyxml multi-routing-engine-results;
         }
       }
     }
   }
   rpc get-service-video-monitoring-mdi-stats-information {
     description "Show MDI flows stats information";
     junos:command "show services video-monitoring mdi stats";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml service-video-monitoring-mdi-stats-information;
         }
         case multichassis-tag {
           anyxml multi-routing-engine-results;
         }
       }
     }
   }
   rpc get-service-video-monitoring-mdi-errors-information {
     description "Show MDI flows error information";
     junos:command "show services video-monitoring mdi errors";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml service-video-monitoring-mdi-errors-information;
         }
         case multichassis-tag {
           anyxml multi-routing-engine-results;
         }
       }
     }
   }
   rpc get-service-video-monitoring-mdi-flows-information {
     description "Show MDI flows information";
     junos:command "show services video-monitoring mdi flow";
     input {
       leaf fpc-slot {
         description "FPC Slot number";
         type union {
           type string {
             pattern "<.*>|$.*";
           }
           type uint32;
         }
         mandatory true;
       }
       leaf flow-count {
         description "Count of flows to display";
         type union {
           type string {
             pattern "<.*>|$.*";
           }
           type uint32 {
             range "1 .. 10000";
           }
         }
       }
       leaf flow-identifier {
         description "Flow Identifier";
         type union {
           type uint32;
           type string {
             pattern "<.*>|$.*";
           }
         }
       }
       leaf source-address {
         description "Source address of flow";
         type jt:ipprefix-optional;
       }
       leaf destination-address {
         description "Destination address of flow";
         type jt:ipprefix-optional;
       }
       leaf source-port {
         description "Source port of flow";
         type union {
           type uint32;
           type string {
             pattern "<.*>|$.*";
           }
         }
       }
       leaf destination-port {
         description "Destination port of flow";
         type union {
           type uint32;
           type string {
             pattern "<.*>|$.*";
           }
         }
       }
       leaf template-name {
         description "Template name";
         type string;
       }
       leaf ifl-name {
         description "Interface name";
         type union {
           type jt:interface-name;
           type string {
             pattern "<.*>|$.*";
           }
         }
       }
       leaf flow-direction {
         description "Direction of flow";
         type enumeration {
           enum "input" {
             description "Input flows";
           }
           enum "output" {
             description "Output flows";
           }
         }
       }
       leaf flow-type {
         description "Type of flow";
         type enumeration {
           enum "udp" {
             description "UDP flows";
           }
           enum "rtp" {
             description "RTP flows";
           }
         }
       }
       leaf flow-family-type {
         description "Type of flow";
         type enumeration {
           enum "flow-over-ipv4" {
             description "Flows over IPv4";
           }
           enum "flow-over-ipv4-over-mpls" {
             description "Flows over IPv4 over MPLS";
           }
           enum "flow-over-ipv6" {
             description "Flows over IPv6";
           }
           enum "flow-over-ipv6-over-mpls" {
             description "Flows over IPv6 over MPLS";
           }
         }
       }
       leaf split-display {
         description "Display terse/details output with DF and MLR in split format";
         type enumeration {
           enum "df-mlr-split-view" {
             description "Display detailed/brief flow output with DF and MLR split";
           }
         }
       }
       leaf flow-display {
         description "Display terse/details output";
         type enumeration {
           enum "detail" {
             description "Display detailed output";
           }
           enum "brief" {
             description "Display breif output (default)";
           }
         }
       }
     }
     output {
       choice output_c {
         case output-tag {
           leaf output {
             type string;
           }
         }
         case actual-tag {
           anyxml service-video-monitoring-mdi-flows-information;
         }
         case multichassis-tag {
           anyxml multi-routing-engine-results;
         }
       }
     }
   }
   rpc get-services-video-monitoring-mdi-alarms-information {
     description "Show Alarm information";
     junos:command "show services video-monitoring mdi alarms";
     output {
       choice output_c {
         case output-tag {
           leaf output {
             type string;
           }
         }
         case actual-tag {
           anyxml services-video-monitoring-mdi-alarms-information;
         }
         case multichassis-tag {
           anyxml multi-routing-engine-results;
         }
       }
     }
   }
   rpc get-services-video-monitoring-mdi-alarms-stats-information {
     description "Show MDI alarm stats information";
     junos:command "show services video-monitoring mdi alarms stats";
     input {
       leaf fpc-slot {
         description "FPC Slot number";
         type union {
           type string {
             pattern "<.*>|$.*";
           }
           type uint32;
         }
         mandatory true;
       }
     }
     output {
       choice output_c {
         case output-tag {
           leaf output {
             type string;
           }
         }
         case actual-tag {
           anyxml services-video-monitoring-mdi-alarms-stats-information;
         }
         case multichassis-tag {
           anyxml multi-routing-engine-results;
         }
       }
     }
   }
   rpc get-service-inline-monitoring-information {
     description "Show inline-monitoring information";
     junos:command "show services inline-monitoring";
     output {
       choice output_c {
         case output-tag {
           leaf output {
             type string;
           }
         }
         case multichassis-tag {
           anyxml multi-routing-engine-results;
         }
       }
     }
   }
   rpc get-service-inline-monitoring-stats-information {
     description "Show inline-monitoring statistical information";
     junos:command "show services inline-monitoring statistics";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-service-inline-monitoring-flow-ctr-map {
     description "Show inline-monitoring flow counter mapping";
     junos:command "show services inline-monitoring flow-counter-mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-service-inline-monitoring-flow-feature-map {
     description "Show inline-monitoring flow feature mapping";
     junos:command "show services inline-monitoring flow-feature-mapping";
     input {
       leaf fpc-slot {
         description "FPC Slot number";
         type union {
           type string {
             pattern "<.*>|$.*";
           }
           type uint32;
         }
         mandatory true;
       }
     }
     output {
       choice output_c {
         case output-tag {
           leaf output {
             type string;
           }
         }
         case multichassis-tag {
           anyxml multi-routing-engine-results;
         }
       }
     }
   }
   rpc get-services-mobile-edge-peers-info {
     description "Show SAEGW peers";
     junos:command "show services mobile-edge peers";
     output {
       choice output_c {
         case output-tag {
           leaf output {
             type string;
           }
         }
         case actual-tag {
           anyxml services-mobile-edge-peers-info;
         }
         case multichassis-tag {
           anyxml multi-routing-engine-results;
         }
       }
     }
   }
   rpc get-services-mobile-edge-peers-stats-info {
     description "Show SAEGW peers statistics";
     junos:command "show services mobile-edge peers statistics";
     output {
       choice output_c {
         case output-tag {
           leaf output {
             type string;
           }
         }
         case actual-tag {
           anyxml services-mobile-edge-peers-stats-info;
         }
         case multichassis-tag {
           anyxml multi-routing-engine-results;
         }
       }
     }
   }
   rpc get-services-mobile-edge-sessions-information {
     description "Show sessions";
     junos:command "show services mobile-edge sessions";
     output {
       choice output_c {
         case output-tag {
           leaf output {
             type string;
           }
         }
         case actual-tag {
           anyxml services-mobile-edge-sessions-information;
         }
         case multichassis-tag {
           anyxml multi-routing-engine-results;
         }
       }
     }
   }
   rpc get-services-mobile-edge-sessions-detail-info {
     description "Display session detail output";
     junos:command "show services mobile-edge sessions detail";
     output {
       choice output_c {
         case output-tag {
           leaf output {
             type string;
           }
         }
         case actual-tag {
           anyxml services-mobile-edge-sessions-detail-info;
         }
         case multichassis-tag {
           anyxml multi-routing-engine-results;
         }
       }
     }
   }
   rpc get-services-mobile-edge-sessions-detail-cpp {
     description "Display session detail output for control plane peers";
     junos:command "show services mobile-edge sessions detail control-plane-peers";
     input {
       leaf address {
         description "Display session detail output for control plane peer";
         type string;
         mandatory true;
       }
     }
     output {
       choice output_c {
         case output-tag {
           leaf output {
             type string;
           }
         }
         case actual-tag {
           anyxml services-mobile-edge-sessions-detail-cpp;
         }
         case multichassis-tag {
           anyxml multi-routing-engine-results;
         }
       }
     }
   }
   rpc get-services-mobile-edge-sessions-extensive {
     description "Display session extensive output";
     junos:command "show services mobile-edge sessions extensive";
     input {
       leaf get-services-mobile-edge-session-extensive {
         description "Display session extensive output of local-seid";
         type string;
       }
     }
     output {
       choice output_c {
         case output-tag {
           leaf output {
             type string;
           }
         }
         case actual-tag {
           anyxml services-mobile-edge-sessions-extensive;
         }
         case multichassis-tag {
           anyxml multi-routing-engine-results;
         }
       }
     }
   }
   rpc get-services-mobile-edge-session-summary {
     description "Display summary output";
     junos:command "show services mobile-edge sessions summary";
     output {
       choice output_c {
         case output-tag {
           leaf output {
             type string;
           }
         }
         case actual-tag {
           anyxml services-mobile-edge-session-summary;
         }
         case multichassis-tag {
           anyxml multi-routing-engine-results;
         }
       }
     }
   }
   rpc get-services-mobile-edge-session-summary-cpp {
     description "Display control plane peers summary output";
     junos:command "show services mobile-edge sessions summary control-plane-peers";
     input {
       leaf address {
         description "Display control plane peers <IP ADDRESS> summary output";
         type string;
       }
     }
     output {
       choice output_c {
         case output-tag {
           leaf output {
             type string;
           }
         }
         case actual-tag {
           anyxml services-mobile-edge-session-summary-cpp;
         }
         case multichassis-tag {
           anyxml multi-routing-engine-results;
         }
       }
     }
   }
   rpc get-services-mobile-edge-session-summary-anp {
     description "Display access network peers summary output";
     junos:command "show services mobile-edge sessions summary access-network-peers";
     input {
       leaf address {
         description "Display access network peers summary output";
         type string;
       }
     }
     output {
       choice output_c {
         case output-tag {
           leaf output {
             type string;
           }
         }
         case actual-tag {
           anyxml services-mobile-edge-session-summary-anp;
         }
         case multichassis-tag {
           anyxml multi-routing-engine-results;
         }
       }
     }
   }
   rpc get-services-mobile-edge-session-summary-pic {
     description "Display pic summary output";
     junos:command "show services mobile-edge sessions summary pic";
     input {
       leaf pic-name {
         description "Display pic summary output of <pfe-x/y>";
         type string {
           junos:posix-pattern "^(pfe-)[1-9]?[0-9]/[1-9]?[0-9]$";
           junos:pattern-message "Invalid PIC name pfe-x/y.";
         }
       }
     }
     output {
       choice output_c {
         case output-tag {
           leaf output {
             type string;
           }
         }
         case actual-tag {
           anyxml services-mobile-edge-session-summary-pic;
         }
         case multichassis-tag {
           anyxml multi-routing-engine-results;
         }
       }
     }
   }
   rpc get-services-mobile-edge-session-summary-slot {
     description "Display slot summary output";
     junos:command "show services mobile-edge sessions summary slot";
     input {
       leaf slot-name {
         description "Display slot summary output of <pfe-x>";
         type string {
           junos:posix-pattern "^(pfe-)[1-9]?[0-9]$";
           junos:pattern-message "Invalid slot name pfe-x.";
         }
       }
     }
     output {
       choice output_c {
         case output-tag {
           leaf output {
             type string;
           }
         }
         case actual-tag {
           anyxml services-mobile-edge-session-summary-slot;
         }
         case multichassis-tag {
           anyxml multi-routing-engine-results;
         }
       }
     }
   }
   rpc get-services-mobile-edge-session-summary-apns {
     description "Display APN name summary output";
     junos:command "show services mobile-edge sessions summary apns";
     input {
       leaf apn-name {
         description "Display summary output of APN <APN-NAME>";
         type string {
           length "1 .. 100";
         }
       }
     }
     output {
       choice output_c {
         case output-tag {
           leaf output {
             type string;
           }
         }
         case actual-tag {
           anyxml services-mobile-edge-session-summary-apns;
         }
         case multichassis-tag {
           anyxml multi-routing-engine-results;
         }
       }
     }
   }
   rpc get-services-mobile-edge-session-summary-ag {
     description "Display anchor group summary output";
     junos:command "show services mobile-edge sessions summary anchor-group";
     input {
       leaf apfe-name {
         description "Display summary output of anchor-group apfe<x>";
         type string {
           length "1 .. 100";
           junos:posix-pattern "^(apfe)";
           junos:pattern-message "Invalid name apfe<x>.";
         }
       }
     }
     output {
       choice output_c {
         case output-tag {
           leaf output {
             type string;
           }
         }
         case actual-tag {
           anyxml services-mobile-edge-session-summary-ag;
         }
         case multichassis-tag {
           anyxml multi-routing-engine-results;
         }
       }
     }
   }
   rpc get-services-mobile-edge-session-summary-cnp {
     description "Display core network peers summary output";
     junos:command "show services mobile-edge sessions summary core-network-peers";
     input {
       leaf address {
         description "Display core network peers summary output";
         type string;
       }
     }
     output {
       choice output_c {
         case output-tag {
           leaf output {
             type string;
           }
         }
         case actual-tag {
           anyxml services-mobile-edge-session-summary-cnp;
         }
         case multichassis-tag {
           anyxml multi-routing-engine-results;
         }
       }
     }
   }
   rpc get-services-mobile-edge-sessions-cpp-info {
     description "Display session output for control plane peers";
     junos:command "show services mobile-edge sessions control-plane-peers";
     input {
       leaf address {
         description "Display session output for control plane peer";
         type string;
       }
     }
     output {
       choice output_c {
         case output-tag {
           leaf output {
             type string;
           }
         }
         case actual-tag {
           anyxml services-mobile-edge-sessions-cpp-info;
         }
         case multichassis-tag {
           anyxml multi-routing-engine-results;
         }
       }
     }
   }
   rpc get-services-mobile-edge-summary-info {
     description "Show SAE gateway summary";
     junos:command "show services mobile-edge summary";
     output {
       choice output_c {
         case output-tag {
           leaf output {
             type string;
           }
         }
         case actual-tag {
           anyxml services-mobile-edge-summary-info;
         }
         case multichassis-tag {
           anyxml multi-routing-engine-results;
         }
       }
     }
   }
   rpc get-services-mobile-edge-apfe-dl-cos {
     description "Show APFE CoS settings";
     junos:command "show services mobile-edge anchor class-of-service";
     output {
       choice output_c {
         case output-tag {
           leaf output {
             type string;
           }
         }
         case actual-tag {
           anyxml services-mobile-edge-apfe-dl-cos;
         }
         case multichassis-tag {
           anyxml multi-routing-engine-results;
         }
       }
     }
   }
   rpc get-services-mobile-edge-resources-cac-stats {
     description "CAC status and statistics";
     junos:command "show services mobile-edge resources call-admission-control statistics";
     output {
       choice output_c {
         case output-tag {
           leaf output {
             type string;
           }
         }
         case actual-tag {
           anyxml services-mobile-edge-resources-cac-stats;
         }
         case multichassis-tag {
           anyxml multi-routing-engine-results;
         }
       }
     }
   }
   rpc get-analytics-agent-information {
     description "Show analytics service agent information";
     junos:command "show services analytics agent";
     input {
       leaf level {
         default "brief";
         type enumeration {
           enum "detail" {
             description "Display detailed data";
           }
           enum "brief" {
             description "Display brief data (default)";
           }
         }
       }
     }
     output {
       choice output_c {
         case output-tag {
           leaf output {
             type string;
           }
         }
         case actual-tag {
           anyxml analytics-agent-information;
         }
         case multichassis-tag {
           anyxml multi-routing-engine-results;
         }
       }
     }
   }
   rpc get-secintel-category-feed {
     description "Show category detail information";
     junos:command "show services security-intelligence category detail";
     input {
       uses command-forwarding;
       leaf category-name {
         description "Category name";
         type string;
         mandatory true;
       }
       leaf feed-name {
         description "Feed name";
         type string;
         mandatory true;
       }
       leaf start {
         description "Start number";
         type union {
           type uint32;
           type string {
             pattern "<.*>|$.*";
           }
         }
       }
       leaf count {
         description "Total number";
         type union {
           type uint32;
           type string {
             pattern "<.*>|$.*";
           }
         }
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml secintel-category-feed;
         }
         case multichassis-tag {
           anyxml multi-routing-engine-results;
         }
       }
     }
   }
   rpc get-secintel-category-summary {
     description "Show category summary";
     junos:command "show services security-intelligence category summary";
     input {
       uses command-forwarding;
       leaf category-name {
         description "Show specified category summary";
         type string;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml secintel-category-summary;
         }
         case multichassis-tag {
           anyxml multi-routing-engine-results;
         }
       }
     }
   }
   rpc get-secintel-category-list {
     description "Show all category names";
     junos:command "show services security-intelligence category list";
     output {
       choice output_c {
         case output-tag {
           leaf output {
             type string;
           }
         }
         case actual-tag {
           anyxml secintel-category-list;
         }
         case multichassis-tag {
           anyxml multi-routing-engine-results;
         }
       }
     }
   }
   rpc get-secintel-update-status {
     description "Show update status";
     junos:command "show services security-intelligence update status";
     output {
       choice output_c {
         case output-tag {
           leaf output {
             type string;
           }
         }
         case actual-tag {
           anyxml secintel-update-status;
         }
         case multichassis-tag {
           anyxml multi-routing-engine-results;
         }
       }
     }
   }
   rpc get-secintel-recommended-action {
     description "Show security intelligence recommended action ";
     junos:command "show services security-intelligence recommended-action";
     input {
       uses command-forwarding;
       leaf category-name {
         description "Show category recommended action";
         type string;
       }
     }
     output {
       choice output_c {
         case output-tag {
           leaf output {
             type string;
           }
         }
         case actual-tag {
           anyxml secintel-recommended-action;
         }
         case multichassis-tag {
           anyxml multi-routing-engine-results;
         }
       }
     }
   }
   rpc get-secintel-redirect-files {
     description "Show redirect files information";
     junos:command "show services security-intelligence redirect-files";
     input {
       uses command-forwarding;
       leaf file-name {
         description "Show redirect-file content";
         type string {
           junos:posix-pattern "![*]";
           junos:pattern-message "File name cannot contain '*', please use tab for filename completion";
         }
       }
     }
     output {
       choice output_c {
         case output-tag {
           leaf output {
             type string;
           }
         }
         case actual-tag {
           anyxml secintel-redirect-files;
         }
         case multichassis-tag {
           anyxml multi-routing-engine-results;
         }
       }
     }
   }
   rpc get-secintel-post-status {
     description "Show sec-profiling feed post status";
     junos:command "show services security-intelligence sec-profiling-feed status";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml secintel-post-status;
         }
         case multichassis-tag {
           anyxml multi-routing-engine-results;
         }
       }
     }
   }
   rpc get-secintel-statistics {
     description "Show security intelligence statistics";
     junos:command "show services security-intelligence statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml secintel-statistics;
         }
         case multichassis-tag {
           anyxml multi-routing-engine-results;
         }
       }
     }
   }
   rpc get-secintel-statistics-profile {
     description "Show security intelligence profile statistics";
     junos:command "show services security-intelligence statistics profile";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml secintel-statistics-profile;
         }
         case multichassis-tag {
           anyxml multi-routing-engine-results;
         }
       }
     }
   }
   rpc get-dns-statistics {
     description "Show security intelligence dns-statistics";
     junos:command "show services security-intelligence dns-statistics";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-statistics;
         }
         case multichassis-tag {
           anyxml multi-routing-engine-results;
         }
       }
     }
   }
   rpc get-dns-statistics-profile {
     description "Show security intelligence dns-profile statistics";
     junos:command "show services security-intelligence dns-statistics profile";
     input {
       uses command-forwarding;
       leaf profile-name {
         description "Profile name";
         type string;
         mandatory true;
       }
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-statistics-profile;
         }
         case multichassis-tag {
           anyxml multi-routing-engine-results;
         }
       }
     }
   }
   rpc get-dns-filtering-cache {
     description "Show DNS-Filtering cache";
     junos:command "show services dns-filtering cache";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-filtering-cache;
         }
         case multichassis-tag {
           anyxml multi-routing-engine-results;
         }
       }
     }
   }
   rpc get-dns-filtering-cache-summary {
     description "Show DNS-Filtering Cache Summary";
     junos:command "show services dns-filtering cache summary";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-filtering-cache-summary;
         }
         case multichassis-tag {
           anyxml multi-routing-engine-results;
         }
       }
     }
   }
   rpc get-dns-filtering-cache-c2 {
     description "Show DNS-Filtering Cache C2-Entries";
     junos:command "show services dns-filtering cache c2";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-filtering-cache-c2;
         }
         case multichassis-tag {
           anyxml multi-routing-engine-results;
         }
       }
     }
   }
   rpc get-dns-filtering-cache-benign {
     description "Show DNS-Filtering Cache Benign-Entries";
     junos:command "show services dns-filtering cache benign";
     input {
       uses command-forwarding;
       choice lsys {
         case logical-system {
         }
         case root-logical-system {
           leaf root-logical-system {
             description "Root logical-system (default)";
             type empty;
           }
         }
         case tenant {
         }
         case all-logical-systems-tenants {
           leaf all-logical-systems-tenants {
             description "All multitenancy systems";
             type empty;
           }
         }
       }
     }
     output {
       choice output_c {
         case output-tag {
           leaf output {
             type string;
           }
         }
         case actual-tag {
           anyxml dns-filtering-cache-benign;
         }
         case multichassis-tag {
           anyxml multi-routing-engine-results;
         }
       }
     }
   }
   rpc get-services-match-policies {
     description "Show match-policy information";
     junos:command "show services match-policies";
     input {
       leaf service-set {
         description "Name of service set";
         type string;
       }
       leaf source-ip {
         description "Source address";
         type jt:ipprefix;
       }
       leaf source-port {
         description "Source port to use as match";
         type union {
           type uint16;
           type string {
             pattern "<.*>|$.*";
           }
         }
       }
       leaf destination-ip {
         description "Destination address";
         type jt:ipprefix;
       }
       leaf destination-port {
         description "Destination port to use as match";
         type union {
           type uint16;
           type string {
             pattern "<.*>|$.*";
           }
         }
       }
       leaf protocol {
         description "IP protocol name or number";
         type string;
       }
       leaf result-count {
         description "The number of policy matches to display";
         type union {
           type uint16;
           type string {
             pattern "<.*>|$.*";
           }
         }
       }
       leaf match-direction {
         description "Match direction";
         type enumeration {
           enum "input" {
             description "Direction input";
           }
           enum "output" {
             description "Direction output";
           }
         }
       }
     }
     output {
       choice output_c {
         case output-tag {
           leaf output {
             type string;
           }
         }
         case actual-tag {
           anyxml services-match-policies-information;
         }
         case multichassis-tag {
           anyxml multi-routing-engine-results;
         }
       }
     }
   }
   rpc get-service-cos-statistics-information {
     description "Show statistics";
     junos:command "show services cos statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-cos-statistics-information;
         }
         case multichassis-tag {
           anyxml multi-routing-engine-results;
         }
       }
     }
   }
   rpc get-service-cos-diffserv-statistics {
     description "Show Diffserv marking statistics";
     junos:command "show services cos statistics diffserv";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
     output {
       choice output_c {
         case output-tag {
           leaf output {
             type string;
           }
         }
         case actual-tag {
           anyxml service-cos-diffserv-statistics;
         }
         case multichassis-tag {
           anyxml multi-routing-engine-results;
         }
       }
     }
   }
   rpc get-service-cos-forwarding-class-statistics {
     description "Show forwarding Class statistics";
     junos:command "show services cos statistics forwarding-class";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
     }
     output {
       choice output_c {
         case output-tag {
           leaf output {
             type string;
           }
         }
         case actual-tag {
           anyxml service-cos-forwarding-class-statistics;
         }
         case multichassis-tag {
           anyxml multi-routing-engine-results;
         }
       }
     }
   }
   rpc get-service-hcm-statistics-information {
     description "Show hcm statistics";
     junos:command "show services hcm statistics";
     input {
       leaf rule {
         description "Name of HCM tag rule";
         type string;
       }
     }
     output {
       choice output_c {
         case output-tag {
           leaf output {
             type string;
           }
         }
         case actual-tag {
           anyxml service-hcm-statistics-information;
         }
         case multichassis-tag {
           anyxml multi-routing-engine-results;
         }
       }
     }
   }
   rpc get-service-hcm-pic-statistics-information {
     description "Show hcm pic statistics";
     junos:command "show services hcm pic-statistics";
     input {
       leaf interface {
         description "Name of extension provider interface";
         type string;
       }
     }
     output {
       choice output_c {
         case output-tag {
           leaf output {
             type string;
           }
         }
         case actual-tag {
           anyxml service-hcm-pic-statistics-information;
         }
         case multichassis-tag {
           anyxml multi-routing-engine-results;
         }
       }
     }
   }
   rpc get-service-mss-sessions-information {
     description "Show mobile subscriber data sessions";
     junos:command "show services mobile sessions";
     input {
       leaf imsi {
         description "IMSI of subscriber";
         type string {
           length "5 .. 15";
         }
       }
     }
     output {
       choice output_c {
         case output-tag {
           leaf output {
             type string;
           }
         }
         case actual-tag {
           anyxml service-mss-sessions-information;
         }
         case multichassis-tag {
           anyxml multi-routing-engine-results;
         }
       }
     }
   }
   rpc get-service-hcm-sessions-stats {
     description "Show hcm session statistics";
     junos:command "show services mobile hcm statistics";
     input {
       leaf imsi {
         description "IMSI of subscriber";
         type string {
           length "5 .. 15";
         }
         mandatory true;
       }
     }
     output {
       choice output_c {
         case output-tag {
           leaf output {
             type string;
           }
         }
         case actual-tag {
           anyxml service-hcm-sessions-stats;
         }
         case multichassis-tag {
           anyxml multi-routing-engine-results;
         }
       }
     }
   }
   rpc get-service-tdf-sessions-information {
     description "Show traffic-detection-function subscriber data sessions";
     junos:command "show services traffic-detection-function sessions";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output_c {
         case output-tag {
           leaf output {
             type string;
           }
         }
         case actual-tag {
           anyxml service-tdf-sessions-information;
         }
         case multichassis-tag {
           anyxml multi-routing-engine-results;
         }
       }
     }
   }
   rpc get-service-tdf-hcm-sessions-stats {
     description "Show hcm session statistics";
     junos:command "show services traffic-detection-function hcm statistics";
     input {
       leaf routing-instance {
         description "Name of routing instance";
         type string;
         mandatory true;
       }
       leaf ipv4-address {
         description "Show sessions for matching IPv4 address";
         type string;
       }
       leaf ipv6-address {
         description "Show sessions for matching IPv6 address";
         type string;
       }
       leaf subscriber-name {
         description "Show sessions for matching Subscriber name";
         type string;
       }
     }
     output {
       choice output_c {
         case output-tag {
           leaf output {
             type string;
           }
         }
         case actual-tag {
           anyxml service-tdf-hcm-sessions-stats;
         }
         case multichassis-tag {
           anyxml multi-routing-engine-results;
         }
       }
     }
   }
   rpc get-service-pgcp-flow-table-information {
     description "Show PGCP flow table entries";
     junos:command "show services pgcp flows";
     output {
       choice output_c {
         case output-tag {
           leaf output {
             type string;
           }
         }
         case actual-tag {
           anyxml service-pgcp-flow-table-information;
         }
         case multichassis-tag {
           anyxml multi-routing-engine-results;
         }
       }
     }
   }
   rpc get-service-pgcp-flow-table-information-gateway {
     description "Show packet-gateway-control-protocol information for gateway";
     junos:command "show services pgcp flows gateway";
     input {
       leaf gateway-name {
         description "Gateway name";
         type string;
         mandatory true;
       }
       leaf gate-id {
         description "Gate id";
         type union {
           type uint64;
           type string {
             pattern "<.*>|$.*";
           }
         }
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf get-service-pgcp-flow-count-information {
         description "Show count of matching entries";
         type empty;
       }
       leaf level {
         default "brief";
         type enumeration {
           enum "brief" {
             description "Display brief output";
           }
           enum "extensive" {
             description "Display extensive output";
           }
         }
       }
       leaf backup-data-pic {
         description "Show flows table by querying the backup Data-PIC";
         type empty;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-flow-table-gateway-information;
         }
         case multichassis-tag {
           anyxml multi-routing-engine-results;
         }
       }
     }
   }
   rpc get-service-pgcp-conversation-information {
     description "Show PGCP conversations";
     junos:command "show services pgcp conversations";
     output {
       choice output_c {
         case output-tag {
           leaf output {
             type string;
           }
         }
         case actual-tag {
           anyxml service-pgcp-conversation-information;
         }
         case multichassis-tag {
           anyxml multi-routing-engine-results;
         }
       }
     }
   }
   rpc get-service-pgcp-conversation-information-gateway {
     description "Show PGCP conversations for gateway";
     junos:command "show services pgcp conversations gateway";
     input {
       leaf gateway-name {
         description "Gateway name";
         type string;
         mandatory true;
       }
       leaf service-set {
         description "Name of service set";
         type string;
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf source-routing-instance {
         description "Source routing-instance";
         type string;
       }
       leaf destination-routing-instance {
         description "Destination routing-instance";
         type string;
       }
       leaf protocol {
         description "IP protocol type to use as filter";
         type string;
       }
       leaf level {
         default "brief";
         type enumeration {
           enum "brief" {
             description "Display brief output";
           }
           enum "extensive" {
             description "Display extensive output";
           }
         }
       }
       leaf backup-data-pic {
         description "Show conversations information by querying the backup Data-PIC";
         type empty;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-conversation-gateway-information;
         }
         case multichassis-tag {
           anyxml multi-routing-engine-results;
         }
       }
     }
   }
   rpc get-pgcpd-active-configuration {
     description "Show pgcpd active-configuration";
     junos:command "show services pgcp active-configuration";
     output {
       choice output_c {
         case output-tag {
           leaf output {
             type string;
           }
         }
         case actual-tag {
           anyxml pgcpd-active-configuration;
         }
         case multichassis-tag {
           anyxml multi-routing-engine-results;
         }
       }
     }
   }
   rpc get-service-pgcp-active-configuration-gateway {
     description "Show gateway active configuration";
     junos:command "show services pgcp active-configuration gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-active-configuration-gateway;
         }
         case multichassis-tag {
           anyxml multi-routing-engine-results;
         }
       }
     }
   }
   rpc get-service-pgcp-statistics {
     description "Show pgcpd statistics";
     junos:command "show services pgcp statistics";
     output {
       choice output_c {
         case output-tag {
           leaf output {
             type string;
           }
         }
         case actual-tag {
           anyxml service-pgcp-statistics;
         }
         case multichassis-tag {
           anyxml multi-routing-engine-results;
         }
       }
     }
   }
   rpc get-service-pgcp-statistics-gateway {
     description "Show gateway statistics";
     junos:command "show services pgcp statistics gateway";
     input {
       leaf gateway-name {
         description "Gateway name";
         type string;
         mandatory true;
       }
       leaf display {
         default "brief";
         type enumeration {
           enum "brief" {
             description "Display brief output (default)";
           }
           enum "extensive" {
             description "Display extensive output";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-statistics-gateway;
         }
         case multichassis-tag {
           anyxml multi-routing-engine-results;
         }
       }
     }
   }
   rpc get-service-pgcp-terminations {
     description "Show list of terminations";
     junos:command "show services pgcp terminations";
     output {
       choice output_c {
         case output-tag {
           leaf output {
             type string;
           }
         }
         case actual-tag {
           anyxml service-pgcp-terminations;
         }
         case multichassis-tag {
           anyxml multi-routing-engine-results;
         }
       }
     }
   }
   rpc get-service-pgcp-terminations-gateway {
     description "Show list of terminations for gateway";
     junos:command "show services pgcp terminations gateway";
     input {
       leaf gateway-name {
         description "Gateway name";
         type string;
         mandatory true;
       }
       leaf termination-prefix {
         description "Termination-prefix to use as filter, default * (all)";
         type string;
       }
       leaf display {
         default "brief";
         type enumeration {
           enum "h248" {
             description "Display H248 output format";
           }
           enum "brief" {
             description "Display brief output (default)";
           }
           enum "count" {
             description "Show count of matching entries";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-terminations-gateway;
         }
         case multichassis-tag {
           anyxml multi-routing-engine-results;
         }
       }
     }
   }
   rpc get-service-pgcp-gates {
     description "Show list of gates";
     junos:command "show services pgcp gates";
     output {
       choice output_c {
         case output-tag {
           leaf output {
             type string;
           }
         }
         case actual-tag {
           anyxml service-pgcp-gates;
         }
         case multichassis-tag {
           anyxml multi-routing-engine-results;
         }
       }
     }
   }
   rpc get-service-pgcp-gates-gateway {
     description "Show all gates for gateway";
     junos:command "show services pgcp gates gateway";
     input {
       leaf gateway-name {
         description "Gateway name";
         type string;
         mandatory true;
       }
       leaf display {
         default "brief";
         type enumeration {
           enum "extensive" {
             description "Display extensive output";
           }
           enum "brief" {
             description "Display brief output (default)";
           }
           enum "count" {
             description "Show count of matching entries";
           }
         }
       }
       leaf source-routing-instance {
         description "Source routing-instance";
         type string;
       }
       leaf destination-routing-instance {
         description "Destination routing-instance";
         type string;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-gates-gateway;
         }
         case multichassis-tag {
           anyxml multi-routing-engine-results;
         }
       }
     }
   }
   rpc get-service-pgcp-gate {
     description "Show gate according to gate-id";
     junos:command "show services pgcp gate";
     output {
       choice output_c {
         case output-tag {
           leaf output {
             type string;
           }
         }
         case actual-tag {
           anyxml service-pgcp-gate;
         }
         case multichassis-tag {
           anyxml multi-routing-engine-results;
         }
       }
     }
   }
   rpc get-service-pgcp-gate-gateway {
     description "Show gate for gateway";
     junos:command "show services pgcp gate gateway";
     input {
       leaf gateway-name {
         description "Gateway name";
         type string;
         mandatory true;
       }
       leaf gate-id {
         description "Gate id";
         type union {
           type uint64;
           type string {
             pattern "<.*>|$.*";
           }
         }
         mandatory true;
       }
       leaf display {
         default "brief";
         type enumeration {
           enum "extensive" {
             description "Display extensive output";
           }
           enum "brief" {
             description "Display brief output (default)";
           }
           enum "statistics" {
             description "Display statistics for gate";
           }
           enum "session-mirroring" {
             description "Display session mirroring for gate";
           }
         }
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml service-pgcp-gate-gateway;
         }
         case multichassis-tag {
           anyxml multi-routing-engine-results;
         }
       }
     }
   }
   rpc get-services-pgcpd-root-termination {
     description "Show root termination h248 information";
     junos:command "show services pgcp root-termination";
     output {
       choice output_c {
         case output-tag {
           leaf output {
             type string;
           }
         }
         case actual-tag {
           anyxml services-pgcpd-root-termination;
         }
         case multichassis-tag {
           anyxml multi-routing-engine-results;
         }
       }
     }
   }
   rpc get-services-pgcpd-root-termination-gateway {
     description "Show root termination h248 information for gateway";
     junos:command "show services pgcp root-termination gateway";
     input {
       leaf gateway-name {
         description "Gateway name";
         type string;
         mandatory true;
       }
       leaf redundancy-option {
         default "master";
         type enumeration {
           enum "master" {
             description "Query the master RE or ms-pic (default)";
           }
           enum "backup" {
             description "Query the backup ms-pic";
           }
         }
       }
     }
     output {
       choice output_c {
         case output-tag {
           leaf output {
             type string;
           }
         }
         case actual-tag {
           anyxml services-pgcpd-root-termination-gateway;
         }
         case multichassis-tag {
           anyxml multi-routing-engine-results;
         }
       }
     }
   }
   rpc get-service-border-signaling-gateway-statistics-calls {
     description "Show border signaling gateway calls statistics";
     junos:command "show services border-signaling-gateway calls";
     output {
       choice output_c {
         case output-tag {
           leaf output {
             type string;
           }
         }
         case actual-tag {
           anyxml bsg-statistics-calls-details;
         }
         case multichassis-tag {
           anyxml multi-routing-engine-results;
         }
       }
     }
   }
   rpc get-service-border-signaling-gateway-statistics-calls-by-sp {
     description "Show border signaling gateway calls statistics grouped by service-point";
     junos:command "show services border-signaling-gateway calls by-service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls;
         }
         case multichassis-tag {
           anyxml multi-routing-engine-results;
         }
       }
     }
   }
   rpc get-service-border-signaling-gateway-statistics-calls-by-server {
     description "Show border signaling gateway calls statistics grouped by server";
     junos:command "show services border-signaling-gateway calls by-server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls;
         }
         case multichassis-tag {
           anyxml multi-routing-engine-results;
         }
       }
     }
   }
   rpc get-service-border-signaling-gateway-statistics-calls-duration-by-sp {
     description "Show border signaling gateway calls duration statistics grouped by service-point";
     junos:command "show services border-signaling-gateway calls-duration by-service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-calls-duration-detals;
         }
         case multichassis-tag {
           anyxml multi-routing-engine-results;
         }
       }
     }
   }
   rpc get-service-border-signaling-gateway-statistics-calls-duration-by-server {
     description "Show border signaling gateway calls duration statistics grouped by server";
     junos:command "show services border-signaling-gateway calls-duration by-server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-calls-duration-detals;
         }
         case multichassis-tag {
           anyxml multi-routing-engine-results;
         }
       }
     }
   }
   rpc get-service-border-signaling-gateway-statistics-failed-calls-by-sp {
     description "Show border signaling gateway failed calls statistics grouped by service-point";
     junos:command "show services border-signaling-gateway calls-failed by-service-point";
     input {
       leaf service-point-name {
         description "Service point name or prefix";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls-failed-details;
         }
         case multichassis-tag {
           anyxml multi-routing-engine-results;
         }
       }
     }
   }
   rpc get-service-border-signaling-gateway-statistics-failed-calls-by-server {
     description "Show border signaling gateway failed calls statistics grouped by server";
     junos:command "show services border-signaling-gateway calls-failed by-server";
     input {
       leaf server-name {
         description "Server name";
         type string;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-calls-failed-details;
         }
         case multichassis-tag {
           anyxml multi-routing-engine-results;
         }
       }
     }
   }
   rpc get-service-bsg-denied-messages {
     description "Show information about dropped messages";
     junos:command "show services border-signaling-gateway denied-messages";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-denied-messages-details;
         }
         case multichassis-tag {
           anyxml multi-routing-engine-results;
         }
       }
     }
   }
   rpc get-service-border-signaling-gateway-statistics-admission-control {
     description "Show border signaling gateway admission control profile statistics statistics";
     junos:command "show services border-signaling-gateway admission-control";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-statistics-admission-control;
         }
         case multichassis-tag {
           anyxml multi-routing-engine-results;
         }
       }
     }
   }
   rpc get-service-border-signaling-gateway-information-by-request-uri {
     description "Show border signaling gateway information by request uri";
     junos:command "show services border-signaling-gateway by-request-uri";
     input {
       leaf gateway {
         description "Name of border signaling gateway";
         type string;
         mandatory true;
       }
       leaf uri {
         description "URI";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-border-signaling-gateway-information-by-contact {
     description "Show border signaling gateway information by contact";
     junos:command "show services border-signaling-gateway by-contact";
     input {
       leaf gateway {
         description "Name of border signaling gateway";
         type string;
         mandatory true;
       }
       leaf contact {
         description "Contact";
         type string;
       }
       leaf display {
         default "brief";
         type enumeration {
           enum "brief" {
             description "Display brief output (default)";
           }
           enum "summary" {
             description "Display summary output";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-bsg-information-by-call-context-id {
     description "Show border signaling gateway information by call context ID";
     junos:command "show services border-signaling-gateway by-call-context-id";
     input {
       leaf gateway {
         description "Name of border signaling gateway";
         type string;
         mandatory true;
       }
       leaf context-id {
         description "Call context ID";
         type union {
           type uint32;
           type string {
             pattern "<.*>|$.*";
           }
         }
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-information-details;
         }
         case multichassis-tag {
           anyxml multi-routing-engine-results;
         }
       }
     }
   }
   rpc get-service-bsg-status-information {
     description "Show border signaling gateway status information";
     junos:command "show services border-signaling-gateway status";
     input {
       leaf gateway {
         description "Name of border signaling gateway";
         type string;
         mandatory true;
       }
       leaf display {
         default "brief";
         type enumeration {
           enum "brief" {
             description "Display brief output (default)";
           }
           enum "detail" {
             description "Display detailed output";
           }
         }
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-status-information;
         }
         case multichassis-tag {
           anyxml multi-routing-engine-results;
         }
       }
     }
   }
   rpc get-border-signaling-gateway-name-resolution-cache-by-fqdn {
     description "Show records for the Fully Qualified Domain Name";
     junos:command "show services border-signaling-gateway name-resolution-cache by-fqdn";
     input {
       leaf fqdn {
         description "Fully Qualified Domain Name";
         type string;
         mandatory true;
       }
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-name-resolution-cache-information;
         }
         case multichassis-tag {
           anyxml multi-routing-engine-results;
         }
       }
     }
   }
   rpc get-service-border-signaling-gateway-name-resolution-cache-all {
     description "Show contents of the cache";
     junos:command "show services border-signaling-gateway name-resolution-cache all";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-name-resolution-cache-information;
         }
         case multichassis-tag {
           anyxml multi-routing-engine-results;
         }
       }
     }
   }
   rpc get-service-border-signaling-gateway-routing-blacklist {
     description "Show border signaling gateway servers blacklist content";
     junos:command "show services border-signaling-gateway routing-blacklist";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-routing-blacklist;
         }
         case multichassis-tag {
           anyxml multi-routing-engine-results;
         }
       }
     }
   }
   rpc get-service-bsg-registrations {
     description "Show border signaling gateway registrations statistics";
     junos:command "show services border-signaling-gateway registrations";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-registrations;
         }
         case multichassis-tag {
           anyxml multi-routing-engine-results;
         }
       }
     }
   }
   rpc get-service-bsg-registrations-statistics {
     description "Show registration statistics";
     junos:command "show services border-signaling-gateway registrations statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-registrations;
         }
         case multichassis-tag {
           anyxml multi-routing-engine-results;
         }
       }
     }
   }
   rpc get-service-bsg-registrations-realm-statistics {
     description "Realm statistics";
     junos:command "show services border-signaling-gateway registrations realm";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf realm-name {
         type string;
       }
     }
     output {
       choice output_c {
         case output-tag {
           leaf output {
             type string;
           }
         }
         case actual-tag {
           anyxml bsg-registrations-realm;
         }
         case multichassis-tag {
           anyxml multi-routing-engine-results;
         }
       }
     }
   }
   rpc get-service-border-signaling-gateway-address-of-record {
     description "Show border signaling gateway address of record";
     junos:command "show services border-signaling-gateway address-of-record";
     output {
       choice output_c {
         case output-tag {
           leaf output {
             type string;
           }
         }
         case actual-tag {
           anyxml bsg-address-of-records;
         }
         case multichassis-tag {
           anyxml multi-routing-engine-results;
         }
       }
     }
   }
   rpc get-service-border-signaling-gateway-address-of-record-bindings {
     description "Show address of record bindings";
     junos:command "show services border-signaling-gateway address-of-record bindings";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
       leaf address-of-record {
         description "Address of record name";
         type string;
       }
       leaf detail {
         description "Detail mode";
         type empty;
       }
     }
     output {
       choice output_c {
         case output-tag {
           leaf output {
             type string;
           }
         }
         case actual-tag {
           anyxml bsg-address-of-record-bindings;
         }
         case multichassis-tag {
           anyxml multi-routing-engine-results;
         }
       }
     }
   }
   rpc get-service-border-signaling-gateway-charging-status {
     description "Show border signaling gateway accounting status";
     junos:command "show services border-signaling-gateway accounting status";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-charging-status;
         }
         case multichassis-tag {
           anyxml multi-routing-engine-results;
         }
       }
     }
   }
   rpc get-service-border-signaling-gateway-charging-statistics {
     description "Show border signaling gateway accounting statistics";
     junos:command "show services border-signaling-gateway accounting statistics";
     input {
       leaf gateway {
         description "Name of border signaling gateway";
         type string;
         mandatory true;
       }
       leaf redundancy-option {
         default "master";
         type enumeration {
           enum "master" {
             description "Query the master border signaling gateway (default)";
           }
           enum "backup" {
             description "Query the backup border signaling gateway";
           }
         }
       }
     }
     output {
       choice output_c {
         case output-tag {
           leaf output {
             type string;
           }
         }
         case actual-tag {
           anyxml bsg-charging-statistics;
         }
         case multichassis-tag {
           anyxml multi-routing-engine-results;
         }
       }
     }
   }
   rpc get-service-msp-flow-table-information {
     description "Show flow table entries";
     junos:command "show services flows";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf get-service-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-msp-session-table {
     description "Show session table entries";
     junos:command "show services sessions";
     input {
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       choice output_c {
         case output-tag {
           leaf output {
             type string;
           }
         }
         case actual-tag {
           anyxml msp-session-table;
         }
         case multichassis-tag {
           anyxml multi-routing-engine-results;
         }
       }
     }
   }
   rpc get-service-msp-sess-count-information {
     description "Show count of matching entries";
     junos:command "show services sessions count";
     input {
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of extension provider interface";
         type string;
       }
     }
     output {
       choice output_c {
         case output-tag {
           leaf output {
             type string;
           }
         }
         case actual-tag {
           anyxml service-msp-sess-count-information;
         }
         case multichassis-tag {
           anyxml multi-routing-engine-results;
         }
       }
     }
   }
   rpc get-service-msp-sess-softwire {
     description "Show softwire session table entries";
     junos:command "show services sessions softwire";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
     }
     output {
       choice output_c {
         case output-tag {
           leaf output {
             type string;
           }
         }
         case actual-tag {
           anyxml msp-session-table;
         }
         case multichassis-tag {
           anyxml multi-routing-engine-results;
         }
       }
     }
   }
   rpc get-usf-service-softwire-table-information {
     description "Show softwire flow entries";
     junos:command "show services sessions softwire flow-details";
     output {
       choice output_c {
         case output-tag {
           leaf output {
             type string;
           }
         }
         case actual-tag {
           anyxml usf-service-softwire-table-information;
         }
         case multichassis-tag {
           anyxml multi-routing-engine-results;
         }
       }
     }
   }
   rpc get-service-msp-sess-softwire-count-info {
     description "Show softwire count of matching entries";
     junos:command "show services sessions softwire count";
     input {
       leaf source-prefix {
         description "Source prefix to use as filter";
         type string;
       }
       leaf destination-prefix {
         description "Destination prefix to use as filter";
         type string;
       }
       leaf service-set {
         description "Name of service set";
         type string;
       }
       leaf interface {
         description "Name of extension provider interface";
         type string;
       }
     }
     output {
       choice output_c {
         case output-tag {
           leaf output {
             type string;
           }
         }
         case actual-tag {
           anyxml service-msp-sess-softwire-count-info;
         }
         case multichassis-tag {
           anyxml multi-routing-engine-results;
         }
       }
     }
   }
   rpc get-service-msp-sess-softwire-dslite-info {
     description "Show ds-lite related softwire sessions";
     junos:command "show services sessions softwire ds-lite";
     input {
       leaf service-set {
         description "Name of service set";
         type string;
       }
       leaf interface {
         description "Name of adaptive services interface";
         type string;
       }
       leaf source-prefix {
         description "Source prefix to use as filter";
         type string;
       }
       leaf destination-prefix {
         description "Destination prefix to use as filter";
         type string;
       }
       leaf get-service-msp-sess-softwire-dslite-count-info {
         description "Show count of matching entries";
         type empty;
       }
       leaf aftr {
         description "AFTR IPV6 Address";
         type jt:ipv6addr;
       }
       leaf b4 {
         description "B4 IPV6 Address";
         type jt:ipv6addr;
       }
     }
     output {
       choice output_c {
         case output-tag {
           leaf output {
             type string;
           }
         }
         case actual-tag {
           anyxml msp-session-table;
         }
         case multichassis-tag {
           anyxml multi-routing-engine-results;
         }
       }
     }
   }
   rpc get-service-msp-session-analysis-information {
     description "Show service sessions statistics";
     junos:command "show services sessions analysis";
     input {
       leaf interface {
         description "Name of extension provider interface";
         type string;
       }
     }
     output {
       choice output_c {
         case output-tag {
           leaf output {
             type string;
           }
         }
         case actual-tag {
           anyxml show-service-msp-session-analysis-information;
         }
         case multichassis-tag {
           anyxml multi-routing-engine-results;
         }
       }
     }
   }
   rpc get-services-sessions-utilization {
     description "Show session utilization statistics";
     junos:command "show services sessions utilization";
     input {
       leaf interface {
         description "Name of extension provider interface";
         type string;
       }
     }
     output {
       choice output_c {
         case output-tag {
           leaf output {
             type string;
           }
         }
         case actual-tag {
           anyxml services-sessions-utilization-information;
         }
         case multichassis-tag {
           anyxml multi-routing-engine-results;
         }
       }
     }
   }
   rpc get-services-sessions-tcp-log {
     description "Show services sessions tcp-log";
     junos:command "show services sessions tcp-log";
     input {
       leaf interface {
         description "Name of extension provider interface";
         type string;
       }
     }
     output {
       choice output_c {
         case output-tag {
           leaf output {
             type string;
           }
         }
         case actual-tag {
           anyxml services-sessions-tcp-log-information;
         }
         case multichassis-tag {
           anyxml multi-routing-engine-results;
         }
       }
     }
   }
   rpc get-service-msp-alg-conversation-information {
     description "Show alg conversations";
     junos:command "show services alg conversations";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf display {
         default "brief";
         type enumeration {
           enum "extensive" {
             description "Display extensive output";
           }
           enum "brief" {
             description "Display brief output (default)";
           }
         }
       }
     }
     output {
       choice output_c {
         case output-tag {
           leaf output {
             type string;
           }
         }
         case actual-tag {
           anyxml service-msp-alg-conversation-information;
         }
         case multichassis-tag {
           anyxml multi-routing-engine-results;
         }
       }
     }
   }
   rpc get-service-msp-alg-stats-information {
     description "Show ALG Statistics";
     junos:command "show services alg statistics";
     input {
       leaf interface {
         description "Name of extension provider interface";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
     }
     output {
       choice output_c {
         case output-tag {
           leaf output {
             type string;
           }
         }
         case actual-tag {
           anyxml service-msp-alg-stats-information;
         }
         case multichassis-tag {
           anyxml multi-routing-engine-results;
         }
       }
     }
   }
   rpc get-service-msp-alg-sip-globals-information {
     description "Show SIP ALG global configurations";
     junos:command "show services alg sip-globals";
     input {
       leaf interface {
         description "Name of extension provider interface";
         type string;
       }
     }
     output {
       choice output_c {
         case output-tag {
           leaf output {
             type string;
           }
         }
         case actual-tag {
           anyxml service-msp-alg-sip-globals-information;
         }
         case multichassis-tag {
           anyxml multi-routing-engine-results;
         }
       }
     }
   }
   rpc get-service-ha-info {
     description "Show HA info and current status";
     junos:command "show services ha";
     input {
       leaf interface {
         description "Name of adaptive services interface";
         type string;
       }
       leaf level {
         default "brief";
         type enumeration {
           enum "brief" {
             description "Display brief output";
           }
           enum "detail" {
             description "Display detailed output";
           }
           enum "statistics" {
             description "Display statistics output";
           }
         }
       }
     }
     output {
       choice output_c {
         case output-tag {
           leaf output {
             type string;
           }
         }
         case actual-tag {
           anyxml service-ha-info;
         }
         case multichassis-tag {
           anyxml multi-routing-engine-results;
         }
       }
     }
   }
   rpc get-service-flow-analysis-information {
     description "Show flow table entries";
     junos:command "show services stateful-firewall flow-analysis";
     input {
       leaf interface {
         description "Name of adaptive services interface";
         type string;
       }
     }
     output {
       choice output_c {
         case output-tag {
           leaf output {
             type string;
           }
         }
         case actual-tag {
           anyxml service-flow-analysis-information;
         }
         case multichassis-tag {
           anyxml multi-routing-engine-results;
         }
       }
     }
   }
   rpc get-service-subs-analysis-information {
     description "Show subscriber table entries";
     junos:command "show services stateful-firewall subscriber-analysis";
     input {
       leaf interface {
         description "Name of adaptive services interface";
         type string;
       }
     }
     output {
       choice output_c {
         case output-tag {
           leaf output {
             type string;
           }
         }
         case actual-tag {
           anyxml service-subs-analysis-information;
         }
         case multichassis-tag {
           anyxml multi-routing-engine-results;
         }
       }
     }
   }
   rpc get-service-sfw-flow-table-information {
     description "Show flow table entries";
     junos:command "show services stateful-firewall flows";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
       leaf get-service-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-service-sfw-conversation-information {
     description "Show conversations";
     junos:command "show services stateful-firewall conversations";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf pgcp {
         description "Use pgcp flow type as filter";
         type empty;
       }
     }
     output {
       choice output_c {
         case output-tag {
           leaf output {
             type string;
           }
         }
         case actual-tag {
           anyxml service-sfw-conversation-information;
         }
         case multichassis-tag {
           anyxml multi-routing-engine-results;
         }
       }
     }
   }
   rpc get-service-sfw-sip-call-information {
     description "Show SIP call information";
     junos:command "show services stateful-firewall sip-call";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-call-count-information {
         description "Show count of matching entries";
         type empty;
       }
     }
     output {
       choice output_c {
         case output-tag {
           leaf output {
             type string;
           }
         }
         case actual-tag {
           anyxml service-sfw-sip-call-information;
         }
         case multichassis-tag {
           anyxml multi-routing-engine-results;
         }
       }
     }
   }
   rpc get-service-sfw-sip-register-information {
     description "Show SIP register information";
     junos:command "show services stateful-firewall sip-register";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf application-protocol {
         description "Application protocol type to use as filter";
         type enumeration {
           enum "bootp" {
             description "Bootstrap protocol";
           }
           enum "dce-rpc" {
             description "DCE RPC";
           }
           enum "dce-rpc-portmap" {
             description "DCE RPC portmap";
           }
           enum "dns" {
             description "Domain Name Service";
           }
           enum "exec" {
             description "Remote Execution Protocol";
           }
           enum "ftp" {
             description "File Transfer Protocol";
           }
           enum "ftp-data" {
             description "File Transfer Protocol Data Session";
           }
           enum "gprs-gtp-c" {
             description "GPRS Tunneling Control Plane";
           }
           enum "gprs-gtp-u" {
             description "GPRS Tunneling User Plane";
           }
           enum "gprs-gtp-v0" {
             description "GPRS Tunneling Version 0";
           }
           enum "gprs-sctp" {
             description "GPRS Stream Control Protocol";
           }
           enum "h323" {
             description "H.323";
           }
           enum "icmp" {
             description "ICMP";
           }
           enum "icmpv6" {
             description "ICMPv6";
           }
           enum "ignore" {
             description "Ignore application type";
           }
           enum "iiop" {
             description "Internet Inter-ORB Protocol";
           }
           enum "ike-esp-nat" {
             description "IKE/ESP with NAT";
           }
           enum "ip" {
             description "IP";
           }
           enum "login" {
             description "Login";
           }
           enum "mgcp-ca" {
             description "MGCP-CA";
           }
           enum "mgcp-ua" {
             description "MGCP-UA";
           }
           enum "ms-rpc" {
             description "Microsoft RPC";
           }
           enum "netbios" {
             description "NetBIOS";
           }
           enum "netshow" {
             description "NetShow";
           }
           enum "none" {
             description "None";
           }
           enum "pptp" {
             description "Point-to-Point Tunneling Protocol";
           }
           enum "q931" {
             description "Q.931";
           }
           enum "ras" {
             description "RAS";
           }
           enum "realaudio" {
             description "RealAudio";
           }
           enum "rpc" {
             description "RPC";
           }
           enum "rpc-portmap" {
             description "RPC portmap";
           }
           enum "rsh" {
             description "Remote Shell";
           }
           enum "rtsp" {
             description "Real Time Streaming Protocol";
           }
           enum "sccp" {
             description "Skinny Client Control Protocol";
           }
           enum "sip" {
             description "Session Initiation Protocol";
           }
           enum "shell" {
             description "Shell";
           }
           enum "snmp" {
             description "SNMP";
           }
           enum "sqlnet" {
             description "SQLNet";
           }
           enum "sqlnet-v2" {
             description "Oracle SQL*Net Version 2";
           }
           enum "sun-rpc" {
             description "Sun Microsystems RPC";
           }
           enum "talk" {
             description "Talk Program";
           }
           enum "tftp" {
             description "Trivial File Transfer Protocol";
           }
           enum "traceroute" {
             description "Traceroute";
           }
           enum "http" {
             description "Hypertext Transfer Protocol";
           }
           enum "winframe" {
             description "WinFrame";
           }
           enum "https" {
             description "Hypertext Transfer Protocol";
           }
           enum "imap" {
             description "Internet Mail Access Protocol";
           }
           enum "smtp" {
             description "Simple Mail Transfer Protocol";
           }
           enum "ssh" {
             description "Secure Shell Protocol";
           }
           enum "telnet" {
             description "Telnet Protocol";
           }
           enum "twamp" {
             description "Two Way Active Meaurement Protocol";
           }
           enum "pop3" {
             description "Post Office Protocol 3 Protocol";
           }
           enum "smtps" {
             description "Simple Mail Transfer Protocol Over TLS";
           }
           enum "imaps" {
             description "Internet Mail Access Protocol Over TLS";
           }
           enum "pop3s" {
             description "Post Office Protocol 3 Protocol Over TLS";
           }
         }
       }
       leaf service-set {
         description "Name of service set";
         type string;
       }
       leaf interface {
         description "Name of adaptive services interface";
         type string;
       }
       leaf get-service-sfw-sip-register-count-information {
         description "Show count of matching entries";
         type empty;
       }
     }
     output {
       choice output_c {
         case output-tag {
           leaf output {
             type string;
           }
         }
         case actual-tag {
           anyxml service-sfw-sip-register-information;
         }
         case multichassis-tag {
           anyxml multi-routing-engine-results;
         }
       }
     }
   }
   rpc get-service-sfw-statistics-information {
     description "Show statistics";
     junos:command "show services stateful-firewall statistics";
     input {
       leaf display {
         default "brief";
         type enumeration {
           enum "brief" {
             description "Display brief output (default)";
           }
           enum "detail" {
             description "Display detailed output";
           }
           enum "extensive" {
             description "Display extensive output";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-sfw-statistics-information;
         }
         case multichassis-tag {
           anyxml multi-routing-engine-results;
         }
       }
     }
   }
   rpc get-sfw-application-protocol-statistics {
     description "Application protocol type to use as filter";
     junos:command "show services stateful-firewall statistics application-protocol";
     input {
       leaf protocol {
         description "Application protocol type to use as filter";
         type enumeration {
           enum "sip" {
             description "Session Initiation Protocol";
           }
         }
       }
     }
     output {
       choice output_c {
         case output-tag {
           leaf output {
             type string;
           }
         }
         case actual-tag {
           anyxml service-sfw-statistics-information;
         }
         case multichassis-tag {
           anyxml multi-routing-engine-results;
         }
       }
     }
   }
   rpc get-service-sfw-redundancy-statistics {
     description "Show redundancy statistics";
     junos:command "show services stateful-firewall redundancy-statistics";
     input {
       leaf backup-data-pic {
         description "Query the backup data PIC";
         type empty;
       }
       leaf display {
         default "brief";
         type enumeration {
           enum "extensive" {
             description "Display extensive output";
           }
           enum "brief" {
             description "Display brief output (default)";
           }
         }
       }
     }
     output {
       choice output_c {
         case output-tag {
           leaf output {
             type string;
           }
         }
         case actual-tag {
           anyxml service-sfw-redundancy-statistics;
         }
         case multichassis-tag {
           anyxml multi-routing-engine-results;
         }
       }
     }
   }
   rpc get-service-capture {
     description "Show Services PIC packet capture";
     junos:command "show services capture";
     input {
       leaf file {
         type string;
         mandatory true;
       }
       leaf level {
         default "brief";
         type enumeration {
           enum "brief" {
             description "Display brief output";
           }
           enum "detail" {
             description "Display detailed output";
           }
           enum "extensive" {
             description "Display extensive output";
           }
         }
       }
       leaf packet-id {
         description "Packet-id to be used as filter";
         type string;
       }
     }
     output {
       choice output_c {
         case output-tag {
           leaf output {
             type string;
           }
         }
         case actual-tag {
           anyxml service-capture;
         }
         case multichassis-tag {
           anyxml multi-routing-engine-results;
         }
       }
     }
   }
   rpc get-service-softwire-table-information {
     description "Show softwire information";
     junos:command "show services softwire";
     input {
       leaf get-service-current-softwire-count-information {
         description "Show count of softwires created";
         type empty;
       }
     }
     output {
       choice output_c {
         case output-tag {
           leaf output {
             type string;
           }
         }
         case actual-tag {
           anyxml service-softwire-table-information;
         }
         case multichassis-tag {
           anyxml multi-routing-engine-results;
         }
       }
     }
   }
   rpc get-service-softwire-flow-table-information {
     description "Show flow table entries";
     junos:command "show services softwire flows";
     input {
       leaf service-set {
         description "Name of service set";
         type string;
       }
       leaf interface {
         description "Name of adaptive services interface";
         type string;
       }
       leaf get-service-softwire-count-information {
         description "Show count of matching entries";
         type empty;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-ds-lite-flow-table-information {
     description "Show ds-lite related softwire flows";
     junos:command "show services softwire flows ds-lite";
     input {
       leaf AFTR {
         description "AFTR IPV6 Address";
         type jt:ipv6addr;
       }
       leaf B4 {
         description "B4 IPV6 Address";
         type jt:ipv6addr;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-v6rd-flow-table-information {
     description "Show v6rd related softwire flows";
     junos:command "show services softwire flows v6rd";
     input {
       leaf concentrator {
         description "Softwire concentrator IPV4 Address";
         type jt:ipv4addr;
       }
       leaf initiator {
         description "Softwire initiator IPV4 Address";
         type jt:ipv4addr;
       }
     }
     output {
       choice output_c {
         case output-tag {
           leaf output {
             type string;
           }
         }
         case actual-tag {
           anyxml service-softwire-flow-table-information;
         }
         case multichassis-tag {
           anyxml multi-routing-engine-results;
         }
       }
     }
   }
   rpc get-service-softwire-session-table-information {
     description "Show session table entries";
     junos:command "show services softwire sessions";
     input {
       leaf service-set {
         description "Name of service set";
         type string;
       }
       leaf interface {
         description "Name of adaptive services interface";
         type string;
       }
       leaf get-service-softwire-session-count-info {
         description "Show count of matching entries";
         type empty;
       }
     }
     output {
       choice output_c {
         case output-tag {
           leaf output {
             type string;
           }
         }
         case actual-tag {
           anyxml msp-session-table;
         }
         case multichassis-tag {
           anyxml multi-routing-engine-results;
         }
       }
     }
   }
   rpc get-service-softwire-session-dslite-table-info {
     description "Show ds-lite related softwire sessions";
     junos:command "show services softwire sessions ds-lite";
     input {
       leaf service-set {
         description "Name of service set";
         type string;
       }
       leaf interface {
         description "Name of adaptive services interface";
         type string;
       }
       leaf get-service-softwire-session-count-info {
         description "Show count of matching entries";
         type empty;
       }
       leaf aftr {
         description "AFTR IPV6 Address";
         type jt:ipv6addr;
       }
       leaf b4 {
         description "B4 IPV6 Address";
         type jt:ipv6addr;
       }
     }
     output {
       choice output_c {
         case output-tag {
           leaf output {
             type string;
           }
         }
         case actual-tag {
           anyxml msp-session-table;
         }
         case multichassis-tag {
           anyxml multi-routing-engine-results;
         }
       }
     }
   }
   rpc get-service-softwire-statistics-information {
     description "Show global softwire statistics";
     junos:command "show services softwire statistics";
     input {
       leaf interface {
         description "Name of adaptive services interface";
         type string;
       }
       leaf display {
         type enumeration {
           enum "ds-lite" {
             description "Show softwire statistics for dslite";
           }
           enum "v6rd" {
             description "Show softwire statistics for v6rd";
           }
         }
       }
     }
     output {
       choice output_c {
         case output-tag {
           leaf output {
             type string;
           }
         }
         case actual-tag {
           anyxml service-softwire-statistics-information;
         }
         case multichassis-tag {
           anyxml multi-routing-engine-results;
         }
       }
     }
   }
   rpc get-inline-service-sw-statistics-information {
     description "Show global inline softwire statistics";
     junos:command "show services inline softwire statistics";
     input {
       leaf interface {
         description "Name of adaptive services interface";
         type string;
       }
       leaf display {
         type enumeration {
           enum "v6rd" {
             description "Softwire statistics for 6rd";
           }
           enum "mape" {
             description "Softwire statistics for MAPE";
           }
         }
       }
     }
     output {
       choice output_c {
         case output-tag {
           leaf output {
             type string;
           }
         }
         case actual-tag {
           anyxml inline-service-sw-statistics-information;
         }
         case multichassis-tag {
           anyxml multi-routing-engine-results;
         }
       }
     }
   }
   rpc get-inline-nat-statistics-information {
     description "Show global inline nat statistics";
     junos:command "show services inline nat statistics";
     input {
       leaf interface {
         description "Name of adaptive services interface";
         type string;
       }
     }
     output {
       choice output_c {
         case output-tag {
           leaf output {
             type string;
           }
         }
         case actual-tag {
           anyxml inline-nat-statistics-information;
         }
         case multichassis-tag {
           anyxml multi-routing-engine-results;
         }
       }
     }
   }
   rpc get-inline-nat-pool-information {
     description "Show NAT pools information";
     junos:command "show services inline nat pool";
     input {
       leaf pool-name {
         description "Name of pool";
         type string;
       }
     }
     output {
       choice output_c {
         case output-tag {
           leaf output {
             type string;
           }
         }
         case actual-tag {
           anyxml inline-nat-pool-information;
         }
         case multichassis-tag {
           anyxml multi-routing-engine-results;
         }
       }
     }
   }
   rpc get-inline-nat-mapping-nptv6-information {
     description "Show nptv6 translated address";
     junos:command "show services inline nat mappings nptv6";
     input {
       leaf address {
         description "IPV6 Address";
         type jt:ipv6addr;
         mandatory true;
       }
       leaf direction {
         type enumeration {
           enum "internal" {
             description "Internal-address";
           }
           enum "external" {
             description "External-address";
           }
         }
         mandatory true;
       }
     }
     output {
       choice output_c {
         case output-tag {
           leaf output {
             type string;
           }
         }
         case actual-tag {
           anyxml inline-nat-mapping-nptv6-information;
         }
         case multichassis-tag {
           anyxml multi-routing-engine-results;
         }
       }
     }
   }
   rpc get-inline-ip-reass-statistics {
     description "Show IP Reassembly statistics";
     junos:command "show services inline ip-reassembly statistics";
     output {
       choice output_c {
         case output-tag {
           leaf output {
             type string;
           }
         }
         case actual-tag {
           anyxml inline-ip-reass-statistics-information;
         }
         case multichassis-tag {
           anyxml multi-routing-engine-results;
         }
       }
     }
   }
   rpc get-inline-ip-reass-si-statistics-information {
     description "Show inline ip-reassembly statistics on si-ifl";
     junos:command "show services inline ip-reassembly statistics interface";
     input {
       leaf interface-name {
         description "Name of adaptive services interface";
         type string;
         mandatory true;
       }
     }
     output {
       choice output_c {
         case output-tag {
           leaf output {
             type string;
           }
         }
         case actual-tag {
           anyxml inline-ip-reass-statistics-information;
         }
         case multichassis-tag {
           anyxml multi-routing-engine-results;
         }
       }
     }
   }
   rpc get-inline-ip-reass-fpc-slot-information {
     description "FPC slot number";
     junos:command "show services inline ip-reassembly statistics fpc";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
     output {
       choice output_c {
         case output-tag {
           leaf output {
             type string;
           }
         }
         case actual-tag {
           anyxml inline-ip-reass-statistics-information;
         }
         case multichassis-tag {
           anyxml multi-routing-engine-results;
         }
       }
     }
   }
   rpc get-inline-ipv6-reass-statistics {
     description "Show IPv6 Reassembly statistics";
     junos:command "show services inline ipv6-reassembly statistics";
     output {
       choice output_c {
         case output-tag {
           leaf output {
             type string;
           }
         }
         case actual-tag {
           anyxml inline-ipv6-reass-statistics-information;
         }
         case multichassis-tag {
           anyxml multi-routing-engine-results;
         }
       }
     }
   }
   rpc get-ipv6-reassembly-interface-information {
     description "Inline-service interface related statistics";
     junos:command "show services inline ipv6-reassembly statistics interface";
     input {
       leaf interface-name {
         description "Name of inline service interface";
         type string;
         mandatory true;
       }
     }
     output {
       choice output_c {
         case output-tag {
           leaf output {
             type string;
           }
         }
         case actual-tag {
           anyxml inline-ipv6-reass-statistics-information;
         }
         case multichassis-tag {
           anyxml multi-routing-engine-results;
         }
       }
     }
   }
   rpc get-inline-ipv6-reass-fpc-slot-information {
     description "FPC slot number";
     junos:command "show services inline ipv6-reassembly statistics fpc";
     input {
       uses command-forwarding;
       leaf fpc-slot {
         description "FPC slot number";
         type union {
           type string {
             pattern "<.*>|$.*";
           }
           type uint32;
         }
         mandatory true;
       }
       leaf pfe-slot {
         description "PFE slot number";
         type union {
           type string {
             pattern "<.*>|$.*";
           }
           type uint32;
         }
       }
     }
     output {
       choice output_c {
         case output-tag {
           leaf output {
             type string;
           }
         }
         case actual-tag {
           anyxml inline-ipv6-reass-statistics-information;
         }
         case multichassis-tag {
           anyxml multi-routing-engine-results;
         }
       }
     }
   }
   rpc get-inline-sfw-flow-table-information {
     description "Show flow table entries";
     junos:command "show services inline stateful-firewall flows";
     input {
       leaf all {
         description "Display all the entries";
         type empty;
       }
       leaf limit {
         description "Maximum number of entries to display";
         type union {
           type string {
             pattern "<.*>|$.*";
           }
           type uint32 {
             range "1 .. 4294967295";
           }
         }
       }
       leaf display {
         default "brief";
         type enumeration {
           enum "extensive" {
             description "Display extensive output";
           }
           enum "brief" {
             description "Display brief output (default)";
           }
           enum "terse" {
             description "Display terse output";
           }
         }
       }
       leaf source-prefix {
         description "Source prefix to use as filter";
         type string;
       }
       leaf destination-prefix {
         description "Destination prefix to use as filter";
         type string;
       }
       leaf source-port {
         description "Source port to use as filter";
         type union {
           type uint16;
           type string {
             pattern "<.*>|$.*";
           }
         }
       }
       leaf destination-port {
         description "Destination port to use as filter";
         type union {
           type uint16;
           type string {
             pattern "<.*>|$.*";
           }
         }
       }
       leaf protocol {
         description "IP protocol type to use as filter";
         type string;
       }
       leaf service-set {
         description "Name of service set";
         type string;
       }
       leaf interface {
         description "Name of adaptive services interface";
         type string;
       }
       leaf get-inline-sfw-flow-count-information {
         description "Show count of matching entries";
         type empty;
       }
     }
     output {
       choice output_c {
         case output-tag {
           leaf output {
             type string;
           }
         }
         case actual-tag {
           anyxml service-sfw-flow-table-information;
         }
         case multichassis-tag {
           anyxml multi-routing-engine-results;
         }
       }
     }
   }
   rpc get-inline-sfw-statistics-information {
     description "Show statistics";
     junos:command "show services inline stateful-firewall statistics";
     input {
       leaf display {
         default "brief";
         type enumeration {
           enum "brief" {
             description "Display brief output (default)";
           }
           enum "summary" {
             description "Display summary output";
           }
         }
       }
       leaf service-set {
         description "Name of service set";
         type string;
       }
       leaf interface {
         description "Name of adaptive services interface";
         type string;
       }
     }
     output {
       choice output_c {
         case output-tag {
           leaf output {
             type string;
           }
         }
         case actual-tag {
           anyxml service-sfw-statistics-information;
         }
         case multichassis-tag {
           anyxml multi-routing-engine-results;
         }
       }
     }
   }
   rpc get-service-ids-source-table-information {
     description "Show attack source address table";
     junos:command "show services ids source-table";
     input {
       leaf source-prefix {
         description "Source prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-ids-destination-table-information {
     description "Show attack destination address table";
     junos:command "show services ids destination-table";
     input {
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-ids-pair-table-information {
     description "Show attack source and destination address pair table";
     junos:command "show services ids pair-table";
     input {
       leaf source-prefix {
         description "Source prefix to use as filter";
         type string;
       }
       leaf destination-prefix {
         description "Destination prefix to use as filter";
         type string;
       }
       leaf service-set {
         description "Name of service set";
         type string;
       }
       leaf interface {
         description "Name of adaptive services interface";
         type string;
       }
       leaf order {
         description "Specify table ordering criteria";
         default "anomalies";
         type enumeration {
           enum "anomalies" {
             description "Order by number of anomalies (default)";
           }
           enum "bytes" {
             description "Order by bytes received";
           }
           enum "flows" {
             description "Order by number of flows";
           }
           enum "packets" {
             description "Order by packets received";
           }
         }
       }
       leaf threshold {
         description "Minimum threshold for table entries";
         type union {
           type int32;
           type string {
             pattern "<.*>|$.*";
           }
         }
       }
       leaf limit {
         description "Maximum number of entries to display";
         type union {
           type int32;
           type string {
             pattern "<.*>|$.*";
           }
         }
       }
       leaf display {
         default "brief";
         type enumeration {
           enum "extensive" {
             description "Display extensive output";
           }
           enum "brief" {
             description "Display brief output (default)";
           }
           enum "terse" {
             description "Display terse output";
           }
         }
       }
     }
     output {
       choice output_c {
         case output-tag {
           leaf output {
             type string;
           }
         }
         case actual-tag {
           anyxml service-ids-flow-table-information;
         }
         case multichassis-tag {
           anyxml multi-routing-engine-results;
         }
       }
     }
   }
   rpc get-service-identification-statistics-information {
     description "Show service identification statistics";
     junos:command "show services service-identification statistics";
     input {
       leaf detail {
         description "Display detailed statistics";
         type empty;
       }
     }
     output {
       choice output_c {
         case output-tag {
           leaf output {
             type string;
           }
         }
         case actual-tag {
           anyxml service-identification-statistics-information;
         }
         case multichassis-tag {
           anyxml multi-routing-engine-results;
         }
       }
     }
   }
   rpc get-header-redirect-set-statistics-information {
     description "Show header redirect set statistics";
     junos:command "show services service-identification header-redirect statistics";
     input {
       leaf detail {
         description "Display detailed statistics";
         type empty;
       }
     }
     output {
       choice output_c {
         case output-tag {
           leaf output {
             type string;
           }
         }
         case actual-tag {
           anyxml header-redirect-set-statistics-information;
         }
         case multichassis-tag {
           anyxml multi-routing-engine-results;
         }
       }
     }
   }
   rpc get-uri-redirect-set-statistics-information {
     description "Show URI redirect set statistics";
     junos:command "show services service-identification uri-redirect statistics";
     input {
       leaf detail {
         description "Display detailed statistics";
         type empty;
       }
     }
     output {
       choice output_c {
         case output-tag {
           leaf output {
             type string;
           }
         }
         case actual-tag {
           anyxml uri-redirect-set-statistics-information;
         }
         case multichassis-tag {
           anyxml multi-routing-engine-results;
         }
       }
     }
   }
   rpc get-flow-table-statistics-information {
     description "Show flow table statistics";
     junos:command "show services flow-table statistics";
     input {
       leaf detail {
         description "Show detailed statistics information";
         type empty;
       }
     }
     output {
       choice output_c {
         case output-tag {
           leaf output {
             type string;
           }
         }
         case actual-tag {
           anyxml flow-table-statistics-information;
         }
         case multichassis-tag {
           anyxml multi-routing-engine-results;
         }
       }
     }
   }
   rpc get-soft-gre-tunnel-database {
     description "Show active soft gre active tunnels";
     junos:command "show services soft-gre tunnel";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case interface {
           leaf interface {
             description "Interface name to use as filter";
             type string;
           }
         }
         case tunnel-group {
           leaf tunnel-group {
             description "Tunnel group to use as filter";
             type string;
           }
         }
         case local-ip {
           leaf local-ip {
             description "Local ip address to use as filter";
             type jt:ipv4addr;
           }
         }
         case remote-ip {
           leaf remote-ip {
             description "Remote ip address to use as filter";
             type jt:ipv4addr;
           }
         }
       }
     }
     output {
       choice output_c {
         case output-tag {
           leaf output {
             type string;
           }
         }
         case actual-tag {
           anyxml soft-gre-tunnel-database;
         }
         case multichassis-tag {
           anyxml multi-routing-engine-results;
         }
       }
     }
   }
   rpc get-l2tp-destination-information {
     description "Show L2TP destination information";
     junos:command "show services l2tp destination";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       choice output_c {
         case output-tag {
           leaf output {
             type string;
           }
         }
         case actual-tag {
           anyxml service-l2tp-destination-information;
         }
         case multichassis-tag {
           anyxml multi-routing-engine-results;
         }
       }
     }
   }
   rpc get-services-l2tp-destination-lockout {
     description "Display locked out destinations";
     junos:command "show services l2tp destination lockout";
     output {
       choice output_c {
         case output-tag {
           leaf output {
             type string;
           }
         }
         case actual-tag {
           anyxml service-l2tp-destination-lockout-information;
         }
         case multichassis-tag {
           anyxml multi-routing-engine-results;
         }
       }
     }
   }
   rpc get-l2tp-tunnel-information {
     description "Show active L2TP tunnel list";
     junos:command "show services l2tp tunnel";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       choice output_c {
         case output-tag {
           leaf output {
             type string;
           }
         }
         case actual-tag {
           anyxml service-l2tp-tunnel-information;
         }
         case multichassis-tag {
           anyxml multi-routing-engine-results;
         }
       }
     }
   }
   rpc get-l2tp-session-information {
     description "Show active L2TP session list";
     junos:command "show services l2tp session";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-client-information {
     description "Show active L2TP clients list";
     junos:command "show services l2tp client";
     input {
       leaf client-name {
         description "Client name";
         type string;
       }
     }
     output {
       choice output_c {
         case output-tag {
           leaf output {
             type string;
           }
         }
         case actual-tag {
           anyxml service-l2tp-client-information;
         }
         case multichassis-tag {
           anyxml multi-routing-engine-results;
         }
       }
     }
   }
   rpc get-l2tp-tunnel-group-information {
     description "Show tunnel-group list";
     junos:command "show services l2tp tunnel-group";
     input {
       leaf tunnel-group-name {
         description "Tunnel group name";
         type string;
       }
     }
     output {
       choice output_c {
         case output-tag {
           leaf output {
             type string;
           }
         }
         case actual-tag {
           anyxml service-l2tp-tunnel-group-information;
         }
         case multichassis-tag {
           anyxml multi-routing-engine-results;
         }
       }
     }
   }
   rpc get-l2tp-session-limit-group-information {
     description "Show session-limit-group list";
     junos:command "show services l2tp session-limit-group";
     input {
       leaf session-limit-group-name {
         description "Session limit group name";
         type string;
       }
     }
     output {
       choice output_c {
         case output-tag {
           leaf output {
             type string;
           }
         }
         case actual-tag {
           anyxml service-l2tp-session-limit-group-information;
         }
         case multichassis-tag {
           anyxml multi-routing-engine-results;
         }
       }
     }
   }
   rpc get-l2tp-tunnel-switch-information {
     description "Show table of tunnel switched sessions";
     junos:command "show services l2tp tunnel-switch summary";
     output {
       choice output_c {
         case output-tag {
           leaf output {
             type string;
           }
         }
         case actual-tag {
           anyxml service-l2tp-tunnel-switch-information;
         }
         case multichassis-tag {
           anyxml multi-routing-engine-results;
         }
       }
     }
   }
   rpc get-l2tp-tunnel-switch-session-information {
     description "Show tunnel switched sessions";
     junos:command "show services l2tp tunnel-switch session";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case local-session-id {
           leaf local-session-id {
             description "Local session ID to use as filter";
             type string;
           }
         }
         case user {
           leaf user {
             description "Username to use as filter";
             type string;
           }
         }
         case interface {
           leaf interface {
             description "Interface name to use as filter";
             type string;
           }
         }
         case routing-instance {
           leaf routing-instance {
             description "Name of routing instance";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-tunnel-switch-tunnel-information {
     description "Show switched tunnels";
     junos:command "show services l2tp tunnel-switch tunnel";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case tunnel-group {
           leaf tunnel-group {
             description "Tunnel group to use as filter";
             type string;
           }
         }
         case local-tunnel-id {
           leaf local-tunnel-id {
             description "Local tunnel ID to use as filter";
             type string;
           }
         }
         case local-gateway {
           leaf local-gateway {
             description "Local gateway address to use as filter";
             type jt:ipv4addr;
           }
         }
         case local-gateway-name {
           leaf local-gateway-name {
             description "Local gateway name to use as filter";
             type string;
           }
         }
         case peer-gateway {
           leaf peer-gateway {
             description "Peer gateway address to use as filter";
             type jt:ipv4addr;
           }
         }
         case peer-gateway-name {
           leaf peer-gateway-name {
             description "Peer gateway name to use as filter";
             type string;
           }
         }
         case interface {
           leaf interface {
             description "Interface name to use as filter";
             type string;
           }
         }
       }
     }
     output {
       choice output_c {
         case output-tag {
           leaf output {
             type string;
           }
         }
         case actual-tag {
           anyxml service-l2tp-tunnel-information;
         }
         case multichassis-tag {
           anyxml multi-routing-engine-results;
         }
       }
     }
   }
   rpc get-l2tp-tunnel-switch-destination-information {
     description "Show tunnel switched destinations";
     junos:command "show services l2tp tunnel-switch destination";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case local-gateway {
           leaf local-gateway {
             description "Local gateway address to use as filter";
             type jt:ipv4addr;
           }
         }
         case peer-gateway {
           leaf peer-gateway {
             description "Peer gateway address to use as filter";
             type jt:ipv4addr;
           }
         }
       }
     }
     output {
       choice output_c {
         case output-tag {
           leaf output {
             type string;
           }
         }
         case actual-tag {
           anyxml service-l2tp-destination-information;
         }
         case multichassis-tag {
           anyxml multi-routing-engine-results;
         }
       }
     }
   }
   rpc get-l2tp-disconnect-cause-summary {
     description "Show L2TP disconnect cause summary";
     junos:command "show services l2tp disconnect-cause-summary";
     output {
       choice output_c {
         case output-tag {
           leaf output {
             type string;
           }
         }
         case actual-tag {
           anyxml service-l2tp-disconnect-cause-summary;
         }
         case multichassis-tag {
           anyxml multi-routing-engine-results;
         }
       }
     }
   }
   rpc get-l2tp-user-information {
     description "Show active L2TP user list";
     junos:command "show services l2tp user";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case user {
           leaf user {
             description "Filter by username";
             type string;
           }
         }
       }
     }
     output {
       choice output_c {
         case output-tag {
           leaf output {
             type string;
           }
         }
         case actual-tag {
           anyxml service-l2tp-session-information;
         }
         case multichassis-tag {
           anyxml multi-routing-engine-results;
         }
       }
     }
   }
   rpc get-l2tp-multilink-information {
     description "Show active L2TP multilink list";
     junos:command "show services l2tp multilink";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       choice filter {
         case bundle-id {
           leaf bundle-id {
             description "Filter by multilink bundle ID";
             type string;
           }
         }
       }
     }
     output {
       choice output_c {
         case output-tag {
           leaf output {
             type string;
           }
         }
         case actual-tag {
           anyxml services-l2tp-multilink-information;
         }
         case multichassis-tag {
           anyxml multi-routing-engine-results;
         }
       }
     }
   }
   rpc get-l2tp-summary-information {
     description "Show L2TP summary information";
     junos:command "show services l2tp summary";
     input {
       leaf display {
         default "brief";
         type enumeration {
           enum "extensive" {
             description "Display extensive output";
           }
           enum "brief" {
             description "Display brief output (default)";
           }
           enum "detail" {
             description "Display detailed output";
           }
           enum "statistics" {
             description "Display statistics";
           }
         }
       }
       leaf interface {
         description "Name of adaptive services interface";
         type string;
       }
     }
     output {
       choice output_c {
         case output-tag {
           leaf output {
             type string;
           }
         }
         case actual-tag {
           anyxml service-l2tp-summary-information;
         }
         case multichassis-tag {
           anyxml multi-routing-engine-results;
         }
       }
     }
   }
   rpc get-services-l2tp-radius-authentication-accounting-servers-information {
     description "Show RADIUS authentication and accounting servers information";
     junos:command "show services l2tp radius servers";
     output {
       choice output_c {
         case output-tag {
           leaf output {
             type string;
           }
         }
         case actual-tag {
           anyxml services-l2tp-radius-authentication-accounting-servers-information;
         }
         case multichassis-tag {
           anyxml multi-routing-engine-results;
         }
       }
     }
   }
   rpc get-services-l2tp-radius-authentication-accounting-statistics-information {
     description "Show RADIUS authentication and accounting statistics information";
     junos:command "show services l2tp radius statistics";
     output {
       choice output_c {
         case output-tag {
           leaf output {
             type string;
           }
         }
         case actual-tag {
           anyxml services-l2tp-radius-authentication-accounting-statistics-information;
         }
         case multichassis-tag {
           anyxml multi-routing-engine-results;
         }
       }
     }
   }
   rpc get-services-l2tp-radius-authentication-servers-information {
     description "Show RADIUS authentication servers information";
     junos:command "show services l2tp radius authentication servers";
     output {
       choice output_c {
         case output-tag {
           leaf output {
             type string;
           }
         }
         case actual-tag {
           anyxml services-l2tp-radius-authentication-servers-information;
         }
         case multichassis-tag {
           anyxml multi-routing-engine-results;
         }
       }
     }
   }
   rpc get-services-l2tp-radius-authentication-statistics-information {
     description "Show RADIUS authentication statistics information";
     junos:command "show services l2tp radius authentication statistics";
     output {
       choice output_c {
         case output-tag {
           leaf output {
             type string;
           }
         }
         case actual-tag {
           anyxml services-l2tp-radius-authentication-statistics-information;
         }
         case multichassis-tag {
           anyxml multi-routing-engine-results;
         }
       }
     }
   }
   rpc get-services-l2tp-radius-accounting-servers-information {
     description "Show RADIUS accounting servers information";
     junos:command "show services l2tp radius accounting servers";
     output {
       choice output_c {
         case output-tag {
           leaf output {
             type string;
           }
         }
         case actual-tag {
           anyxml services-l2tp-radius-accounting-servers-information;
         }
         case multichassis-tag {
           anyxml multi-routing-engine-results;
         }
       }
     }
   }
   rpc get-services-l2tp-radius-accounting-statistics-information {
     description "Show RADIUS accounting statistics information";
     junos:command "show services l2tp radius accounting statistics";
     output {
       choice output_c {
         case output-tag {
           leaf output {
             type string;
           }
         }
         case actual-tag {
           anyxml services-l2tp-radius-accounting-statistics-information;
         }
         case multichassis-tag {
           anyxml multi-routing-engine-results;
         }
       }
     }
   }
   rpc get-service-crtp-params-information {
     description "Show Compressed Real-Time Protocol information";
     junos:command "show services crtp";
     input {
       leaf interface {
         description "Name of link services interface";
         type string;
       }
     }
     output {
       choice output_c {
         case output-tag {
           leaf output {
             type string;
           }
         }
         case actual-tag {
           anyxml service-crtp-params-information;
         }
         case multichassis-tag {
           anyxml multi-routing-engine-results;
         }
       }
     }
   }
   rpc get-service-crtp-extensive-information {
     description "Show CRTP extensive output";
     junos:command "show services crtp extensive";
     input {
       leaf interface {
         description "Name of link services interface";
         type string;
       }
     }
     output {
       choice output_c {
         case output-tag {
           leaf output {
             type string;
           }
         }
         case actual-tag {
           anyxml service-crtp-extensive-information;
         }
         case multichassis-tag {
           anyxml multi-routing-engine-results;
         }
       }
     }
   }
   rpc get-service-crtp-flow-table-information {
     description "Show CRTP flow table entries";
     junos:command "show services crtp flows";
     input {
       leaf interface {
         description "Name of link services interface";
         type string;
       }
     }
     output {
       choice output_c {
         case output-tag {
           leaf output {
             type string;
           }
         }
         case actual-tag {
           anyxml service-crtp-flow-table-information;
         }
         case multichassis-tag {
           anyxml multi-routing-engine-results;
         }
       }
     }
   }
   rpc get-link-services-cpu-usage {
     description "Show cpu usage as a percentage for the specified PIC";
     junos:command "show services link-services cpu-usage";
     input {
       leaf interface {
         description "Name of link services interface";
         type string;
         mandatory true;
       }
       leaf level {
         default "brief";
         type enumeration {
           enum "brief" {
             description "Display brief output (1 and 5 second average)";
           }
           enum "detail" {
             description "Display detailed output (per cpu average)";
           }
         }
       }
     }
     output {
       choice output_c {
         case output-tag {
           leaf output {
             type string;
           }
         }
         case actual-tag {
           anyxml lsqinfo-cpu-usage-information;
         }
         case multichassis-tag {
           anyxml multi-routing-engine-results;
         }
       }
     }
   }
   rpc get-global-pcp-statistics-information {
     description "Show global PCP statistics";
     junos:command "show services pcp statistics";
     input {
       leaf interface {
         description "Name of adaptive services interface";
         type string;
       }
       leaf level {
         type enumeration {
           enum "protocol" {
             description "Display PCP protocol statistics";
           }
         }
       }
     }
     output {
       choice output_c {
         case output-tag {
           leaf output {
             type string;
           }
         }
         case actual-tag {
           anyxml global-pcp-statistics-information;
         }
         case multichassis-tag {
           anyxml multi-routing-engine-results;
         }
       }
     }
   }
   rpc get-msp-ssubscriber-table {
     description "Show subscriber table entries";
     junos:command "show services subscriber";
     output {
       choice output_c {
         case output-tag {
           leaf output {
             type string;
           }
         }
         case actual-tag {
           anyxml msp-subscriber-table;
         }
         case multichassis-tag {
           anyxml multi-routing-engine-results;
         }
       }
     }
   }
   rpc get-service-subscriber-analysis-information {
     description "Show service subscribers statistics";
     junos:command "show services subscriber analysis";
     input {
       leaf interface {
         description "Name of extension provider interface";
         type string;
       }
     }
     output {
       choice output_c {
         case output-tag {
           leaf output {
             type string;
           }
         }
         case actual-tag {
           anyxml service-subscriber-analysis-information;
         }
         case multichassis-tag {
           anyxml multi-routing-engine-results;
         }
       }
     }
   }
   rpc get-tcp-log-connection-information {
     description "Show connections related to TCP logging";
     junos:command "show services tcp-log connections";
     input {
       leaf interface {
         description "Name of extension provider interface";
         type string;
       }
     }
     output {
       choice output_c {
         case output-tag {
           leaf output {
             type string;
           }
         }
         case actual-tag {
           anyxml tcp-log-connection-information;
         }
         case multichassis-tag {
           anyxml multi-routing-engine-results;
         }
       }
     }
   }
   rpc get-services-redundancy-group-information {
     description "Show services redundancy-group information";
     junos:command "show services redundancy-group";
     input {
       leaf verbose {
         default "terse";
         type enumeration {
           enum "terse" {
             description "Display terse output(default)";
           }
           enum "brief" {
             description "Display brief output";
           }
           enum "extensive" {
             description "Display detailed output";
           }
         }
       }
     }
     output {
       choice output_c {
         case output-tag {
           leaf output {
             type string;
           }
         }
         case actual-tag {
           anyxml services-redundancy-group-information;
         }
         case multichassis-tag {
           anyxml multi-routing-engine-results;
         }
       }
     }
   }
   rpc get-services-redundancy-group-id-information {
     description "Show redundancy group-id information";
     junos:command "show services redundancy-group rg-id";
     input {
       leaf verbose {
         default "terse";
         type enumeration {
           enum "terse" {
             description "Display terse output(default)";
           }
           enum "brief" {
             description "Display brief output";
           }
           enum "extensive" {
             description "Display detailed output";
           }
         }
       }
       leaf id {
         description "Show redundancy group-id information";
         type union {
           type uint32;
           type string {
             pattern "<.*>|$.*";
           }
         }
         mandatory true;
       }
     }
     output {
       choice output_c {
         case output-tag {
           leaf output {
             type string;
           }
         }
         case actual-tag {
           anyxml services-redundancy-group-id-information;
         }
         case multichassis-tag {
           anyxml multi-routing-engine-results;
         }
       }
     }
   }
   rpc get-ip-monitoring-status {
     description "Ip monitoring status";
     junos:command "show services ip-monitoring status";
     input {
       leaf policy {
         description "Policy name";
         type string;
       }
     }
     output {
       choice output_c {
         case output-tag {
           leaf output {
             type string;
           }
         }
         case actual-tag {
           anyxml ip-monitoring;
         }
         case multichassis-tag {
           anyxml multi-routing-engine-results;
         }
       }
     }
   }
   rpc get-traffic-load-balance-statistics {
     description "Traffic load balance statistics";
     junos:command "show services traffic-load-balance statistics";
     input {
       leaf verbose {
         type enumeration {
           enum "summary" {
             description "Display summary output";
           }
           enum "extensive" {
             description "Display extensive output";
           }
         }
       }
       leaf group {
         description "Group name";
         default "all";
         type string;
       }
       leaf instance {
         description "Instance name";
         default "all";
         type string;
       }
       leaf real-service {
         description "Real service name";
         default "all";
         type string;
       }
       leaf virtual-service {
         description "Virtual service name";
         default "all";
         type string;
       }
       leaf num-instances {
         description "Number of instances to be displayed";
         default "200";
         type union {
           type uint32;
           type string {
             pattern "<.*>|$.*";
           }
         }
       }
     }
     output {
       choice output_c {
         case output-tag {
           leaf output {
             type string;
           }
         }
         case actual-tag {
           anyxml service-traffic-load-balance-statistics;
         }
         case multichassis-tag {
           anyxml multi-routing-engine-results;
         }
       }
     }
   }
   rpc get-flb-statistics {
     description "FLB  statistics";
     junos:command "show services traffic-load-balance flb-statistics";
     input {
       leaf all {
         description "All flb instances";
         type empty;
       }
     }
     output {
       choice output_c {
         case output-tag {
           leaf output {
             type string;
           }
         }
         case actual-tag {
           anyxml flb-statistics;
         }
         case multichassis-tag {
           anyxml multi-routing-engine-results;
         }
       }
     }
   }
   rpc traffic-load-balance-commit-status {
     description "Display commit status";
     junos:command "show services traffic-load-balance commit-status";
     output {
       choice output_c {
         case output-tag {
           leaf output {
             type string;
           }
         }
         case actual-tag {
           anyxml tdir-commit-status;
         }
         case multichassis-tag {
           anyxml multi-routing-engine-results;
         }
       }
     }
   }
   rpc get-url-filter-statistics {
     description "Show web filter statistics";
     junos:command "show services web-filter statistics";
     input {
       leaf profile {
         description "Web filter profile specific statistics";
         type string;
         mandatory true;
       }
       leaf url-filter-template {
         description "Url filter template specific statistics";
         type string;
       }
       leaf dns-filter-template {
         description "DNS filter template specific statistics";
         type string;
       }
       leaf dns-filter-term {
         description "DNS filter term specific statistics";
         type string;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
       leaf level {
         default "brief";
         type enumeration {
           enum "brief" {
             description "Brief Information";
           }
           enum "detail" {
             description "Detailed Information";
           }
           enum "extensive" {
             description "Extensive Information";
           }
         }
       }
     }
     output {
       choice output_c {
         case output-tag {
           leaf output {
             type string;
           }
         }
         case actual-tag {
           anyxml url-filter-statistics;
         }
         case multichassis-tag {
           anyxml multi-routing-engine-results;
         }
       }
     }
   }
   rpc get-web-filter-dns-feed-statistics {
     description "Show web filter dns feed statistics";
     junos:command "show services web-filter dns-feed-statistics";
     input {
       leaf feed-name {
         description "Web filter DNS feed  specific statistics";
         type string;
         mandatory true;
       }
       leaf fpc-slot {
         description "FPC slot number";
         type union {
           type uint32;
           type string {
             pattern "<.*>|$.*";
           }
         }
       }
       leaf pic-slot {
         description "PIC slot number";
         type union {
           type uint32;
           type string {
             pattern "<.*>|$.*";
           }
         }
       }
     }
     output {
       choice output_c {
         case output-tag {
           leaf output {
             type string;
           }
         }
         case actual-tag {
           anyxml web-filter-dns-feed-statistics;
         }
         case multichassis-tag {
           anyxml multi-routing-engine-results;
         }
       }
     }
   }
   rpc get-url-filter-dns-resolution {
     description "Show url-filter dns-resolution";
     junos:command "show services web-filter dns-resolution";
     input {
       leaf profile {
         description "Url-filter profile specific DNS resolution information";
         type string;
         mandatory true;
       }
       leaf url-filter-template {
         description "Url-filter template specific DNS resolution information";
         type string;
       }
     }
     output {
       choice output_c {
         case output-tag {
           leaf output {
             type string;
           }
         }
         case actual-tag {
           anyxml url-filter-dns-resolution;
         }
         case multichassis-tag {
           anyxml multi-routing-engine-results;
         }
       }
     }
   }
   rpc get-url-filter-dns-resolution-statistics {
     description "Show url-filter dns-resolution statistics";
     junos:command "show services web-filter dns-resolution-statistics";
     input {
       leaf profile {
         description "Url-filter profile specific DNS resolution information";
         type string;
         mandatory true;
       }
       leaf url-filter-template {
         description "Url-filter template specific DNS resolution information";
         type string;
         mandatory true;
       }
       leaf verbosity_level {
         type enumeration {
           enum "summary" {
             description "Display summary output";
           }
           enum "extensive" {
             description "Display extensive output";
           }
         }
         mandatory true;
       }
     }
     output {
       choice output_c {
         case output-tag {
           leaf output {
             type string;
           }
         }
         case actual-tag {
           anyxml url-filter-dns-resolution-statistics;
         }
         case multichassis-tag {
           anyxml multi-routing-engine-results;
         }
       }
     }
   }
   rpc get-url-filter-secintel-policy-status {
     description "Show secintel policy status";
     junos:command "show services web-filter secintel-policy-status";
     input {
       leaf profile {
         description "Url-filter profile specific secintel policy status";
         type string;
         mandatory true;
       }
       leaf url-filter-template {
         description "Url-filter template specific secintel policy status";
         type string;
       }
       leaf verbosity_level {
         type enumeration {
           enum "summary" {
             description "Display summary output";
           }
           enum "extensive" {
             description "Display extensive output";
           }
         }
       }
     }
     output {
       choice output_c {
         case output-tag {
           leaf output {
             type string;
           }
         }
         case actual-tag {
           anyxml url-filter-secintel-policy-status;
         }
         case multichassis-tag {
           anyxml multi-routing-engine-results;
         }
       }
     }
   }
   rpc get-url-filter-secintel-policy-db {
     description "Web filtering secintel policy db";
     junos:command "show services web-filter secintel-policy-db";
     input {
       leaf ip-prefix-information {
         description "Web filtering secintel IP prefix information";
         type string;
         mandatory true;
       }
       leaf profile {
         description "Web filtering secintel profile IP prefix information";
         type string;
         mandatory true;
       }
       leaf template {
         description "Web filtering secintel template IP prefix information";
         type string;
       }
     }
     output {
       choice output_c {
         case output-tag {
           leaf output {
             type string;
           }
         }
         case actual-tag {
           anyxml url-filter-secintel-policy-db;
         }
         case multichassis-tag {
           anyxml multi-routing-engine-results;
         }
       }
     }
   }
   grouping command-forwarding {
     choice chassis-selector {
       case case_1 {
         leaf all-chassis {
           description "All chassis";
           type empty;
         }
       }
       case case_2 {
         leaf all-lcc {
           description "All LCC chassis";
           type empty;
         }
       }
       case case_3 {
         leaf scc {
           description "SCC";
           type empty;
         }
       }
       case case_4 {
         leaf sfc {
           description "SFC";
           type union {
             type string {
               pattern "<.*>|$.*";
             }
             type uint32;
           }
         }
       }
       case case_5 {
         leaf lcc {
           description "Specific LCC";
           type union {
             type string {
               pattern "<.*>|$.*";
             }
             type uint32;
           }
         }
       }
       case case_6 {
         leaf node {
           description "Specific node";
           type string;
         }
       }
       case case_7 {
         leaf bsys {
           description "Base system";
           type empty;
         }
       }
       case case_8 {
         leaf gnf {
           description "Specific guest network function";
           type union {
             type string {
               pattern "<.*>|$.*";
             }
             type uint32 {
               range "1 .. 10";
             }
           }
         }
       }
       case case_9 {
         leaf all-gnfs {
           description "All guest network functions";
           type empty;
         }
       }
       case case_10 {
         leaf all-system {
           description "All system (BSYS and GNFs)";
           type empty;
         }
       }
       case case_11 {
         leaf server {
           description "Specific server slot";
           type union {
             type string {
               pattern "<.*>|$.*";
             }
             type uint32 {
               range "0 .. 1";
             }
           }
         }
       }
       case case_12 {
         leaf all-servers {
           description "All servers";
           type empty;
         }
       }
       case case_13 {
         leaf vnf {
           description "Specific virtual-network-function";
           type string;
         }
       }
       case case_14 {
         leaf all-vnfs {
           description "All virtual-network-functions";
           type empty;
         }
       }
     }
     choice re-selector {
       case case_1 {
         leaf re0 {
           description "RE0";
           type empty;
         }
       }
       case case_2 {
         leaf re1 {
           description "RE1";
           type empty;
         }
       }
       case case_3 {
         leaf routing-engine {
           description "Specific routing engine";
           type enumeration {
             enum "local" {
               description "Local routing engine";
             }
             enum "other" {
               description "Other routing engine";
             }
             enum "master" {
               description "Master routing engine";
             }
             enum "backup" {
               description "Backup routing engine";
             }
             enum "both" {
               description "Both routing engines";
             }
           }
         }
       }
     }
     choice lr-selector {
       case case_1 {
         leaf logical-system {
           description "Name of logical system, or 'all'";
           type string;
         }
       }
     }
     choice tenant-selector {
       case case_1 {
         leaf tenant {
           description "Name of tenant, or 'all'";
           type string;
         }
       }
     }
     choice vc-selector {
       case case_1 {
         leaf local {
           description "Local virtual chassis member";
           type empty;
         }
       }
       case case_2 {
         leaf all-members {
           description "All virtual chassis members";
           type empty;
         }
       }
       case case_3 {
         leaf member {
           description "Specific virtual chassis member";
           type union {
             type string {
               pattern "<.*>|$.*";
             }
             type uint32;
           }
         }
       }
     }
   }
 }
