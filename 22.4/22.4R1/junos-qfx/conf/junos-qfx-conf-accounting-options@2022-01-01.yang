/*
 * Copyright (c) 2022 Juniper Networks, Inc.
 * All rights reserved.
 */
 module junos-qfx-conf-accounting-options {
   namespace "http://yang.juniper.net/junos-qfx/conf/accounting-options";

   prefix jc-accounting-options;

   import junos-common-types {
     prefix jt;
     revision-date 2022-01-01;
   }

   import junos-qfx-conf-root {
     prefix jc;
     revision-date 2022-01-01;
   }

   organization "Juniper Networks, Inc.";

   contact "yang-support@juniper.net";

   description "Junos accounting-options configuration module";

   revision 2022-01-01 {
     description "Junos: 22.4R1.10";
   }

   augment /jc:configuration {
     uses accounting-options-group;
   }
   augment /jc:configuration/jc:groups {
     uses accounting-options-group;
   }
   grouping accounting-options-group {
     container accounting-options {
       description "Accounting data configuration";
       uses juniper_accounting_options;
     }
   }
   grouping juniper_accounting_options {
     description "Accounting data configuration";
     uses apply-advanced;
     container periodic-refresh {
       description "Toggle periodic statistics collection";
       choice enable-disable {
         case case_1 {
           leaf disable {
             description "Disable statistics refresh";
             type empty;
           }
         }
       }
     }
     container detailed-transit-interface-stats {
       description "Display Layer 3 Transit Statistics";
       choice enable-disable {
         case case_1 {
           leaf disable {
             description "Disable detailed transit interface statistics";
             type empty;
           }
         }
       }
     }
     list file {
       key name;
       ordered-by user;
       description "Accounting data file configuration";
       leaf name {
         description "Name of file in which to write accounting data";
         type string {
         }
       }
       uses apply-advanced;
       leaf size {
         description "Maximum accounting data file size";
         type string;
       }
       leaf files {
         description "Maximum number of files for this profile";
         default "10";
         type union {
           type string {
             pattern "<.*>|$.*";
           }
           type uint32 {
             range "3 .. 1000";
           }
         }
       }
       leaf transfer-interval {
         description "Frequency at which to transfer files to archive sites";
         default "30";
         units "minutes";
         type union {
           type string {
             pattern "<.*>|$.*";
           }
           type uint32 {
             range "5 .. 2880";
           }
         }
       }
       leaf start-time {
         description "Start time for file transmission (yyyy-mm-dd.hh:mm) in local time format";
         type jt:time;
       }
       leaf compress {
         description "Transfer file in compressed format";
         type empty;
       }
       container backup-on-failure {
         description "Backup on transfer failure";
         uses apply-advanced;
         choice backuponfailure {
           case case_1 {
             leaf master-only {
               description "Backup on master only";
               type empty;
             }
           }
           case case_2 {
             leaf master-and-slave {
               description "Backup on both master and slave";
               type empty;
             }
           }
         }
       }
       leaf push-backup-to-master {
         description "Push backup files to master RE";
         type empty;
       }
       list archive-sites {
         key name;
         ordered-by user;
         description "List of archive destinations";
         leaf name {
           description "Primary and failover URLs to receive archive files";
           type string;
         }
         leaf password {
           description "Password for login into the archive site";
           type jt:unreadable;
         }
       }
     }
     list interface-profile {
       key name;
       ordered-by user;
       description "Interface profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       container fields {
         description "Statistics to log to file";
         uses apply-advanced;
         leaf input-bytes {
           description "Input bytes";
           type empty;
         }
         leaf output-bytes {
           description "Output bytes";
           type empty;
         }
         leaf input-packets {
           description "Input packets";
           type empty;
         }
         leaf output-packets {
           description "Output packets";
           type empty;
         }
         leaf input-errors {
           description "Generic input error packets";
           type empty;
         }
         leaf output-errors {
           description "Generic output error packets";
           type empty;
         }
         leaf input-multicast {
           description "Input packets arriving by multicast";
           type empty;
         }
         leaf output-multicast {
           description "Output packets sent by multicast";
           type empty;
         }
         leaf input-unicast {
           description "Input unicast packets";
           type empty;
         }
         leaf output-unicast {
           description "Output unicast packets";
           type empty;
         }
         leaf unsupported-protocol {
           description "Packets for unsupported protocol";
           type empty;
         }
         leaf rpf-check-bytes {
           description "Bytes failing IPv4 reverse-path-forwarding check";
           type empty;
         }
         leaf rpf-check-packets {
           description "Packets failing IPv4 reverse-path-forwarding check";
           type empty;
         }
         leaf rpf-check6-bytes {
           description "Bytes failing IPv6 reverse-path-forwarding check";
           type empty;
         }
         leaf rpf-check6-packets {
           description "Packets failing IPv6 reverse-path-forwarding check";
           type empty;
         }
         leaf rpf-check-total-bytes {
           description "Total Bytes failing reverse-path-forwarding check";
           type empty;
         }
         leaf rpf-check-total-packets {
           description "Total Packets failing reverse-path-forwarding check";
           type empty;
         }
       }
     }
     list filter-profile {
       key name;
       ordered-by user;
       description "Filter profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 1048576";
           }
         }
       }
       list counters {
         key name;
         ordered-by user;
         description "Name of counter";
         uses counter-object;
       }
       leaf start-time {
         description "Profile start time (yyyy-mm-dd.hh:mm) in local time format";
         type jt:time;
       }
     }
     list class-usage-profile {
       key name;
       ordered-by user;
       description "Class usage profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 1048576";
           }
         }
       }
       leaf start-time {
         description "Profile start time (yyyy-mm-dd.hh:mm) in local time format";
         type jt:time;
       }
       choice class-name {
         case case_1 {
           list destination-classes {
             key name;
             ordered-by user;
             description "Name of destination class";
             uses dest-class-name-object;
           }
         }
         case case_2 {
           list source-classes {
             key name;
             ordered-by user;
             description "Name of source class";
             uses source-class-name-object;
           }
         }
       }
     }
     list routing-engine-profile {
       key name;
       ordered-by user;
       description "Routing Engine profile for accounting data";
       leaf name {
         description "Name of profile";
         type string;
       }
       uses apply-advanced;
       leaf file {
         description "Name of file for accounting data";
         type string;
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       container fields {
         description "Information to log to file";
         uses apply-advanced;
         leaf host-name {
           description "Hostname for this router";
           type empty;
         }
         leaf date {
           description "Date";
           units "YYYYMMDD";
           type empty;
         }
         leaf time-of-day {
           description "Time of day";
           units "HHMMSS";
           type empty;
         }
         leaf uptime {
           description "Time since last reboot";
           units "seconds";
           type empty;
         }
         leaf cpu-load-1 {
           description "Average system load over last 1 minute";
           type empty;
         }
         leaf cpu-load-5 {
           description "Average system load over last 5 minutes";
           type empty;
         }
         leaf cpu-load-15 {
           description "Average system load over last 15 minutes";
           type empty;
         }
         leaf memory-usage {
           description "Instantaneous active memory usage";
           type empty;
         }
         leaf total-cpu-usage {
           description "Total CPU usage percentage";
           type empty;
         }
         leaf cpu-usage-5sec {
           description "System CPU usage for last 5 seconds";
           type empty;
         }
         leaf cpu-usage-1min {
           description "System CPU usage for the last minute";
           type empty;
         }
         leaf cpu-usage-5min {
           description "System CPU usage for the 5 minutes";
           type empty;
         }
         leaf free-mem {
           description "Total free memory available";
           type empty;
         }
         leaf total-mem {
           description "Total memory available";
           type empty;
         }
       }
     }
     list mib-profile {
       key name;
       ordered-by user;
       description "MIB profile for accounting data";
       leaf name {
         description "Name of profile";
         type string;
       }
       uses apply-advanced;
       leaf file {
         description "Name of file for accounting data";
         type string {
         }
       }
       leaf interval {
         description "Polling interval";
         default "30";
         units "minutes";
         type union {
           type string {
             pattern "<.*>|$.*";
           }
           type uint32 {
             range "1 .. 2880";
           }
         }
       }
       leaf start-time {
         description "Profile start time (yyyy-mm-dd.hh:mm) in local time format";
         type jt:time;
       }
       leaf operation {
         description "SNMP operation";
         default "walk";
         type enumeration {
           enum "get" {
             description "Get SNMP object value";
           }
           enum "get-next" {
             description "Get next SNMP object value";
           }
           enum "walk" {
             description "Walk SNMP object values";
           }
         }
       }
       list object-names {
         key name;
         ordered-by user;
         description "Names of MIB objects";
         uses mib-variable-name-object;
       }
     }
     list flat-file-profile {
       key name;
       ordered-by user;
       description "Flat file profile for accounting data";
       leaf name {
         description "Name of profile";
         type string;
       }
       uses apply-advanced;
       leaf file {
         description "Name of file for accounting data";
         type string;
       }
       leaf interval {
         description "Polling interval";
         default "15";
         units "minutes";
         type union {
           type string {
             pattern "<.*>|$.*";
           }
           type uint32 {
             range "1 .. 2880";
           }
         }
       }
       leaf schema-version {
         description "Name of the schema";
         type string;
       }
       leaf start-time {
         description "Profile start time (yyyy-mm-dd.hh:mm) in local time format";
         type jt:time;
       }
       leaf use-fc-ingress-stats {
         description "Use Ingress stats for reporting forwarding class counters";
         type empty;
       }
       container fields {
         description "Statistics to log to file";
         uses apply-advanced;
         leaf all-fields {
           description "All parameters";
           type empty;
         }
         leaf service-accounting {
           description "Service accounting for filters - obsolete config";
           status deprecated;
           type empty;
         }
         container general-param {
           presence "enable general-param";
           description "General interface parameters";
           uses apply-advanced;
           leaf all-fields {
             description "All general interface parameters";
             type empty;
           }
           leaf timestamp {
             description "Timestamp";
             type empty;
           }
           leaf accounting-type {
             description "Accounting status type";
             type empty;
           }
           leaf descr {
             description "Description";
             type empty;
           }
           leaf routing-instances {
             description "Routing Instances where interface belongs";
             type empty;
           }
           leaf nas-port-id {
             description "NAS port id";
             type empty;
           }
           leaf line-id {
             description "Line id";
             type empty;
           }
           leaf vlan-id {
             description "Vlan-id";
             type empty;
           }
           leaf logical-interface {
             description "Logical-Interface";
             type empty;
           }
           leaf physical-interface {
             description "Physical Interface name";
             type empty;
           }
           leaf user-name {
             description "User name of the subscriber";
             type empty;
           }
         }
         container overall-packet {
           presence "enable overall-packet";
           description "Overall packet statistics";
           uses apply-advanced;
           leaf all-fields {
             description "All overall packet statistics";
             type empty;
           }
           leaf input-bytes {
             description "Input bytes";
             type empty;
           }
           leaf input-packets {
             description "Input packets";
             type empty;
           }
           leaf input-v6-bytes {
             description "Input IPV6 bytes";
             type empty;
           }
           leaf input-v6-packets {
             description "Input IPV6 packets";
             type empty;
           }
           leaf output-bytes {
             description "Output bytes";
             type empty;
           }
           leaf output-packets {
             description "Output packets";
             type empty;
           }
           leaf output-v6-bytes {
             description "Output IPV6 bytes";
             type empty;
           }
           leaf output-v6-packets {
             description "Output IPV6 packets";
             type empty;
           }
           leaf input-errors {
             description "Total input errors";
             type empty;
           }
           leaf output-errors {
             description "Total output errors";
             type empty;
           }
           leaf input-discards {
             description "Total input discards";
             type empty;
           }
           leaf input-v4-bytes {
             description "Input IPV4 bytes";
             type empty;
           }
           leaf input-v4-packets {
             description "Input IPV4 packets";
             type empty;
           }
           leaf output-v4-bytes {
             description "Output IPV4 bytes";
             type empty;
           }
           leaf output-v4-packets {
             description "Output IPV4 packets";
             type empty;
           }
           leaf input-bytes-per-sec {
             description "Input bytes per second";
             type empty;
           }
           leaf input-packets-per-sec {
             description "Input packets per second";
             type empty;
           }
         }
         container l2-stats {
           presence "enable l2-stats";
           description "Layer2 statistics";
           uses apply-advanced;
           leaf all-fields {
             description "All Layer2 statistics";
             type empty;
           }
           leaf input-mcast-bytes {
             description "L2 multicast bytes from input side";
             type empty;
           }
           leaf input-mcast-packets {
             description "L2 multicast packets from input side";
             type empty;
           }
         }
         container ingress-stats {
           presence "enable ingress-stats";
           description "Ingress queue statistics";
           uses apply-advanced;
           leaf all-fields {
             description "All ingress queue statistics";
             type empty;
           }
           leaf queue-id {
             description "Queue ID";
             type empty;
           }
           leaf input-packets {
             description "Total input packets on the queue";
             type empty;
           }
           leaf input-bytes {
             description "Total input bytes on the queue";
             type empty;
           }
           leaf output-packets {
             description "Total output packet on the queue";
             type empty;
           }
           leaf output-bytes {
             description "Total output bytes on the queue";
             type empty;
           }
           leaf drop-packets {
             description "Ingress queue dropped packets";
             type empty;
           }
         }
         container egress-stats {
           presence "enable egress-stats";
           description "Egress queue statistics";
           uses apply-advanced;
           leaf all-fields {
             description "All egress queue statistics";
             type empty;
           }
           leaf queue-id {
             description "Queue ID";
             type empty;
           }
           leaf input-packets {
             description "Total input packets on the queue";
             type empty;
           }
           leaf input-bytes {
             description "Total input bytes on the queue";
             type empty;
           }
           leaf output-packets {
             description "Total output packet on the queue";
             type empty;
           }
           leaf output-bytes {
             description "Total output bytes on the queue";
             type empty;
           }
           leaf tail-drop-packets {
             description "Egress queue tail dropped packets";
             type empty;
           }
           leaf red-drop-packets {
             description "Egress queue red dropped packets";
             type empty;
           }
           leaf red-drop-bytes {
             description "Egress queue red drop bytes";
             type empty;
           }
           leaf total-drop-packets {
             description "Egress queue total drop packets";
             type empty;
           }
         }
       }
       container format {
         description "Flat file accounting format";
         uses apply-advanced;
         choice flatfileformat {
           case case_1 {
             leaf ipdr {
               description "IPDR format";
               type empty;
             }
           }
           case case_2 {
             leaf csv {
               description "CSV format";
               type empty;
             }
           }
         }
       }
     }
     container cleanup-interval {
       presence "enable cleanup-interval";
       description "Backup files cleanup interval";
       uses apply-advanced;
       leaf interval {
         description "Cleanup interval in days";
         default "1";
         units "day";
         type union {
           type string {
             pattern "<.*>|$.*";
           }
           type uint32 {
             range "1 .. 31";
           }
         }
       }
     }
   }
   grouping apply-advanced {
     description "Apply advanced configuration logic";
     leaf-list apply-groups {
       ordered-by user;
       description "Groups from which to inherit configuration data";
       type string;
     }
     leaf-list apply-groups-except {
       ordered-by user;
       description "Don't inherit configuration data from these groups";
       type string;
     }
     list apply-macro {
       key name;
       ordered-by user;
       description "Macro and parameters for commit script expansion";
       uses apply-macro-type;
     }
   }
   grouping apply-macro-type {
     description "Macro data for commit-script expansion";
     leaf name {
       description "Name of the macro to be expanded";
       type string;
     }
     list data {
       key name;
       uses macro-data-type;
     }
   }
   grouping counter-object {
     leaf name {
       description "Name of counter";
       type string;
     }
   }
   grouping dest-class-name-object {
     leaf name {
       description "Class name";
       type string;
     }
   }
   grouping macro-data-type {
     leaf name {
       description "Keyword part of the keyword-value pair";
       type string;
     }
     leaf value {
       description "Value part of the keyword-value pair";
       type string;
     }
   }
   grouping mib-variable-name-object {
     leaf name {
       description "MIB variable name";
       type string {
       }
     }
   }
   grouping source-class-name-object {
     leaf name {
       description "Class name";
       type string;
     }
   }
 }
